AC-KPI-MIB DEFINITIONS ::= BEGIN


    IMPORTS


        OBJECT-TYPE,
        MODULE-IDENTITY                             FROM SNMPv2-SMI
        TAddress,
        DisplayString,
        DateAndTime, TEXTUAL-CONVENTION             FROM SNMPv2-TC
        IpAddress                                   FROM RFC1155-SMI
        Unsigned32,
        Integer32,
        enterprises                                 FROM SNMPv2-SMI
        SnmpAdminString                             FROM SNMP-FRAMEWORK-MIB
        audioCodes,
        acRegistrations,
        acGeneric,
        acProducts,acBoardMibs,acPerformance        FROM AUDIOCODES-TYPES-MIB;


acKpi  MODULE-IDENTITY
    LAST-UPDATED "202403190408Z"          --Tuesday, March 19 2024
    ORGANIZATION "AudioCodes Ltd"
    CONTACT-INFO
    "Postal: Support
             AudioCodes LTD
             1 Hayarden Street
             Airport City
             Lod, ISRAEL 70151
     Tel:    972-3-9764000
     Fax:    972-3-9764040
     Email:  support@audiocodes.com
     Web:    www.audiocodes.com"


    DESCRIPTION
    "The AC-KPI MIB offers next generation performance monitoring
For the SBC related elements in Audiocodes' devices.


Note  - for the entire MIB the value (-1) means the value
Asked for is either not supported or currently not relevant
(this is for when values asked for are for intervals not yet
recorded."



    ::= {audioCodes 15}








     acKpiInterval OBJECT IDENTIFIER ::= {acKpi 1}


     acKpiIntervalStats OBJECT IDENTIFIER ::= {acKpiInterval 1}


     acKpiIntervalStatsLastInterval OBJECT-TYPE
       SYNTAX Unsigned32 (1..16384)
       MAX-ACCESS read-only
       STATUS current
       DESCRIPTION
           "Defines the ID of last interval that the system exposed.
AC INI-Param: N/A"
       ::= {acKpiIntervalStats 1}



     -- ****************************************
     -- acKpiIntervalStatusInformation table declaration
     -- ****************************************
     acKpiIntervalStatusInformationTable OBJECT-TYPE
       SYNTAX SEQUENCE OF AcKpiIntervalStatusInformationEntry
       MAX-ACCESS not-accessible
       STATUS current
       DESCRIPTION
           ""
       ::= {acKpiIntervalStats 21}



     -- ****************************************
     -- acKpiIntervalStatusInformation table entry
     -- ****************************************
     acKpiIntervalStatusInformationEntry OBJECT-TYPE
       SYNTAX AcKpiIntervalStatusInformationEntry
       MAX-ACCESS not-accessible
       STATUS current
       DESCRIPTION
           ""
       INDEX {acKpiIntervalStatusInformationIndex}
       ::= {acKpiIntervalStatusInformationTable 1}



     -- ****************************************
     -- acKpiIntervalStatusInformation TABLE
     -- ****************************************
     AcKpiIntervalStatusInformationEntry ::= SEQUENCE {
       acKpiIntervalStatusInformationIndex             Unsigned32,
       acKpiIntervalStatusInformationValid             INTEGER,
       acKpiIntervalStatusInformationStartTime         SnmpAdminString,
       acKpiIntervalStatusInformationEndTime           SnmpAdminString
     }



     acKpiIntervalStatusInformationIndex OBJECT-TYPE
       SYNTAX Unsigned32 (1..16384)
       MAX-ACCESS not-accessible
       STATUS current
       DESCRIPTION
           "
AC INI-Param: N/A"
       ::= {acKpiIntervalStatusInformationEntry 1}



     acKpiIntervalStatusInformationValid OBJECT-TYPE
       SYNTAX INTEGER {
                  invalid(0)
,
                  valid(1)

                  }
       MAX-ACCESS read-only
       STATUS current
       DESCRIPTION
           "Interval Status Information Valid.
AC INI-Param: N/A"
       ::= {acKpiIntervalStatusInformationEntry 2}



     acKpiIntervalStatusInformationStartTime OBJECT-TYPE
       SYNTAX SnmpAdminString (SIZE (0..10))
       MAX-ACCESS read-only
       STATUS current
       DESCRIPTION
           "Interval Status Information Start Time.
AC INI-Param: N/A"
       ::= {acKpiIntervalStatusInformationEntry 3}



     acKpiIntervalStatusInformationEndTime OBJECT-TYPE
       SYNTAX SnmpAdminString (SIZE (0..10))
       MAX-ACCESS read-only
       STATUS current
       DESCRIPTION
           "Interval Status Information End Time.
AC INI-Param: N/A"
       ::= {acKpiIntervalStatusInformationEntry 4}



     acKpiSystem OBJECT IDENTIFIER ::= {acKpi 2}


     acKpiLicenseStats OBJECT IDENTIFIER ::= {acKpiSystem 1}


     acKpiLicenseStatsCurrent OBJECT IDENTIFIER ::= {acKpiLicenseStats 1}


     acKpiLicenseStatsCurrentGlobal OBJECT IDENTIFIER ::= {acKpiLicenseStatsCurrent 1}


     acKpiLicenseStatsCurrentGlobalLicenseSipRecUsage OBJECT-TYPE
       SYNTAX Gauge32
       MAX-ACCESS read-only
       STATUS current
       DESCRIPTION
           "SIP-REC license key usage (%).
AC INI-Param: N/A"
       ::= {acKpiLicenseStatsCurrentGlobal 1}



     acKpiLicenseStatsCurrentGlobalLicenseTranscodingUsage OBJECT-TYPE
       SYNTAX Gauge32
       MAX-ACCESS read-only
       STATUS current
       DESCRIPTION
           "CODER-TRANSCODING license key usage (%).
AC INI-Param: N/A"
       ::= {acKpiLicenseStatsCurrentGlobal 2}



     acKpiLicenseStatsCurrentGlobalLicenseSbcMediaUsage OBJECT-TYPE
       SYNTAX Gauge32
       MAX-ACCESS read-only
       STATUS current
       DESCRIPTION
           "SBC-MEDIA license key usage (%).
AC INI-Param: N/A"
       ::= {acKpiLicenseStatsCurrentGlobal 3}



     acKpiLicenseStatsCurrentGlobalLicenseSbcSignalingUsage OBJECT-TYPE
       SYNTAX Gauge32
       MAX-ACCESS read-only
       STATUS current
       DESCRIPTION
           "SBC-SIGNALING license key usage (%).
AC INI-Param: N/A"
       ::= {acKpiLicenseStatsCurrentGlobal 4}



     acKpiLicenseStatsCurrentGlobalLicenseFeuUsage OBJECT-TYPE
       SYNTAX Gauge32
       MAX-ACCESS read-only
       STATUS current
       DESCRIPTION
           "FEU license key usage (%).
AC INI-Param: N/A"
       ::= {acKpiLicenseStatsCurrentGlobal 5}



     acKpiLicenseStatsCurrentGlobalLicenseWebRTCUsage OBJECT-TYPE
       SYNTAX Gauge32
       MAX-ACCESS read-only
       STATUS current
       DESCRIPTION
           "WebRTC license key usage (%).
AC INI-Param: N/A"
       ::= {acKpiLicenseStatsCurrentGlobal 6}



     acKpiLicenseStatsInterval OBJECT IDENTIFIER ::= {acKpiLicenseStats 2}


     acKpiLicenseStatsIntervalGlobal OBJECT IDENTIFIER ::= {acKpiLicenseStatsInterval 1}


     -- ****************************************
     -- acKpiLicenseStatsIntervalGlobal table declaration
     -- ****************************************
     acKpiLicenseStatsIntervalGlobalTable OBJECT-TYPE
       SYNTAX SEQUENCE OF AcKpiLicenseStatsIntervalGlobalEntry
       MAX-ACCESS not-accessible
       STATUS current
       DESCRIPTION
           ""
       ::= {acKpiLicenseStatsIntervalGlobal 1}



     -- ****************************************
     -- acKpiLicenseStatsIntervalGlobal table entry
     -- ****************************************
     acKpiLicenseStatsIntervalGlobalEntry OBJECT-TYPE
       SYNTAX AcKpiLicenseStatsIntervalGlobalEntry
       MAX-ACCESS not-accessible
       STATUS current
       DESCRIPTION
           ""
       INDEX {acKpiLicenseStatsIntervalGlobalInterval}
       ::= {acKpiLicenseStatsIntervalGlobalTable 1}



     -- ****************************************
     -- acKpiLicenseStatsIntervalGlobal TABLE
     -- ****************************************
     AcKpiLicenseStatsIntervalGlobalEntry ::= SEQUENCE {
       acKpiLicenseStatsIntervalGlobalInterval         Unsigned32,
       acKpiLicenseStatsIntervalGlobalLicenseSipRecUsageMax 
                                                       Gauge32,
       acKpiLicenseStatsIntervalGlobalLicenseSipRecUsageAvg 
                                                       Gauge32,
       acKpiLicenseStatsIntervalGlobalLicenseTranscodingUsageMax 
                                                       Gauge32,
       acKpiLicenseStatsIntervalGlobalLicenseTranscodingUsageAvg 
                                                       Gauge32,
       acKpiLicenseStatsIntervalGlobalLicenseSbcMediaUsageMax 
                                                       Gauge32,
       acKpiLicenseStatsIntervalGlobalLicenseSbcMediaUsageAvg 
                                                       Gauge32,
       acKpiLicenseStatsIntervalGlobalLicenseSbcSignalingUsageMax 
                                                       Gauge32,
       acKpiLicenseStatsIntervalGlobalLicenseSbcSignalingUsageAvg 
                                                       Gauge32,
       acKpiLicenseStatsIntervalGlobalLicenseFeuUsageMax 
                                                       Gauge32,
       acKpiLicenseStatsIntervalGlobalLicenseFeuUsageAvg 
                                                       Gauge32,
       acKpiLicenseStatsIntervalGlobalLicenseWebRTCUsageMax 
                                                       Gauge32,
       acKpiLicenseStatsIntervalGlobalLicenseWebRTCUsageAvg 
                                                       Gauge32
     }



     acKpiLicenseStatsIntervalGlobalInterval OBJECT-TYPE
       SYNTAX Unsigned32 (1..200)
       MAX-ACCESS not-accessible
       STATUS current
       DESCRIPTION
           "
AC INI-Param: N/A"
       ::= {acKpiLicenseStatsIntervalGlobalEntry 1}



     acKpiLicenseStatsIntervalGlobalLicenseSipRecUsageMax OBJECT-TYPE
       SYNTAX Gauge32
       MAX-ACCESS read-only
       STATUS current
       DESCRIPTION
           "Maximum SIP-REC license key usage (%).
AC INI-Param: N/A"
       ::= {acKpiLicenseStatsIntervalGlobalEntry 2}



     acKpiLicenseStatsIntervalGlobalLicenseSipRecUsageAvg OBJECT-TYPE
       SYNTAX Gauge32
       MAX-ACCESS read-only
       STATUS current
       DESCRIPTION
           "Average SIP-REC license key usage (%).
AC INI-Param: N/A"
       ::= {acKpiLicenseStatsIntervalGlobalEntry 3}



     acKpiLicenseStatsIntervalGlobalLicenseTranscodingUsageMax OBJECT-TYPE
       SYNTAX Gauge32
       MAX-ACCESS read-only
       STATUS current
       DESCRIPTION
           "Maximum CODER-TRANSCODING license key usage (%).
AC INI-Param: N/A"
       ::= {acKpiLicenseStatsIntervalGlobalEntry 4}



     acKpiLicenseStatsIntervalGlobalLicenseTranscodingUsageAvg OBJECT-TYPE
       SYNTAX Gauge32
       MAX-ACCESS read-only
       STATUS current
       DESCRIPTION
           "Average CODER-TRANSCODING license key usage (%).
AC INI-Param: N/A"
       ::= {acKpiLicenseStatsIntervalGlobalEntry 5}



     acKpiLicenseStatsIntervalGlobalLicenseSbcMediaUsageMax OBJECT-TYPE
       SYNTAX Gauge32
       MAX-ACCESS read-only
       STATUS current
       DESCRIPTION
           "Maximum SBC-MEDIA license key usage (%).
AC INI-Param: N/A"
       ::= {acKpiLicenseStatsIntervalGlobalEntry 6}



     acKpiLicenseStatsIntervalGlobalLicenseSbcMediaUsageAvg OBJECT-TYPE
       SYNTAX Gauge32
       MAX-ACCESS read-only
       STATUS current
       DESCRIPTION
           "Average SBC-MEDIA license key usage (%).
AC INI-Param: N/A"
       ::= {acKpiLicenseStatsIntervalGlobalEntry 7}



     acKpiLicenseStatsIntervalGlobalLicenseSbcSignalingUsageMax OBJECT-TYPE
       SYNTAX Gauge32
       MAX-ACCESS read-only
       STATUS current
       DESCRIPTION
           "Maximum SBC-SIGNALING license key usage (%).
AC INI-Param: N/A"
       ::= {acKpiLicenseStatsIntervalGlobalEntry 8}



     acKpiLicenseStatsIntervalGlobalLicenseSbcSignalingUsageAvg OBJECT-TYPE
       SYNTAX Gauge32
       MAX-ACCESS read-only
       STATUS current
       DESCRIPTION
           "Average SBC-SIGNALING license key usage (%).
AC INI-Param: N/A"
       ::= {acKpiLicenseStatsIntervalGlobalEntry 9}



     acKpiLicenseStatsIntervalGlobalLicenseFeuUsageMax OBJECT-TYPE
       SYNTAX Gauge32
       MAX-ACCESS read-only
       STATUS current
       DESCRIPTION
           "Maximum FEU license key usage (%).
AC INI-Param: N/A"
       ::= {acKpiLicenseStatsIntervalGlobalEntry 10}



     acKpiLicenseStatsIntervalGlobalLicenseFeuUsageAvg OBJECT-TYPE
       SYNTAX Gauge32
       MAX-ACCESS read-only
       STATUS current
       DESCRIPTION
           "Average FEU license key usage (%).
AC INI-Param: N/A"
       ::= {acKpiLicenseStatsIntervalGlobalEntry 11}



     acKpiLicenseStatsIntervalGlobalLicenseWebRTCUsageMax OBJECT-TYPE
       SYNTAX Gauge32
       MAX-ACCESS read-only
       STATUS current
       DESCRIPTION
           "Maximum WebRTC license key usage (%).
AC INI-Param: N/A"
       ::= {acKpiLicenseStatsIntervalGlobalEntry 12}



     acKpiLicenseStatsIntervalGlobalLicenseWebRTCUsageAvg OBJECT-TYPE
       SYNTAX Gauge32
       MAX-ACCESS read-only
       STATUS current
       DESCRIPTION
           "Average WebRTC license key usage (%).
AC INI-Param: N/A"
       ::= {acKpiLicenseStatsIntervalGlobalEntry 13}



     acKpiSystemStats OBJECT IDENTIFIER ::= {acKpiSystem 2}


     acKpiSystemStatsCurrent OBJECT IDENTIFIER ::= {acKpiSystemStats 1}


     acKpiSystemStatsCurrentGlobal OBJECT IDENTIFIER ::= {acKpiSystemStatsCurrent 1}


     acKpiSystemStatsCurrentGlobalMemoryUtilization OBJECT-TYPE
       SYNTAX Gauge32
       MAX-ACCESS read-only
       STATUS current
       DESCRIPTION
           "Memory utilization (%).
AC INI-Param: N/A"
       ::= {acKpiSystemStatsCurrentGlobal 1}



     acKpiSystemStatsInterval OBJECT IDENTIFIER ::= {acKpiSystemStats 2}


     acKpiSystemStatsIntervalGlobal OBJECT IDENTIFIER ::= {acKpiSystemStatsInterval 1}


     -- ****************************************
     -- acKpiSystemStatsIntervalGlobal table declaration
     -- ****************************************
     acKpiSystemStatsIntervalGlobalTable OBJECT-TYPE
       SYNTAX SEQUENCE OF AcKpiSystemStatsIntervalGlobalEntry
       MAX-ACCESS not-accessible
       STATUS current
       DESCRIPTION
           ""
       ::= {acKpiSystemStatsIntervalGlobal 1}



     -- ****************************************
     -- acKpiSystemStatsIntervalGlobal table entry
     -- ****************************************
     acKpiSystemStatsIntervalGlobalEntry OBJECT-TYPE
       SYNTAX AcKpiSystemStatsIntervalGlobalEntry
       MAX-ACCESS not-accessible
       STATUS current
       DESCRIPTION
           ""
       INDEX {acKpiSystemStatsIntervalGlobalInterval}
       ::= {acKpiSystemStatsIntervalGlobalTable 1}



     -- ****************************************
     -- acKpiSystemStatsIntervalGlobal TABLE
     -- ****************************************
     AcKpiSystemStatsIntervalGlobalEntry ::= SEQUENCE {
       acKpiSystemStatsIntervalGlobalInterval          Unsigned32,
       acKpiSystemStatsIntervalGlobalMemoryUtilizationMax 
                                                       Gauge32,
       acKpiSystemStatsIntervalGlobalMemoryUtilizationAvg 
                                                       Gauge32
     }



     acKpiSystemStatsIntervalGlobalInterval OBJECT-TYPE
       SYNTAX Unsigned32 (1..200)
       MAX-ACCESS not-accessible
       STATUS current
       DESCRIPTION
           "
AC INI-Param: N/A"
       ::= {acKpiSystemStatsIntervalGlobalEntry 1}



     acKpiSystemStatsIntervalGlobalMemoryUtilizationMax OBJECT-TYPE
       SYNTAX Gauge32
       MAX-ACCESS read-only
       STATUS current
       DESCRIPTION
           "Maximum memory utilization (%).
AC INI-Param: N/A"
       ::= {acKpiSystemStatsIntervalGlobalEntry 2}



     acKpiSystemStatsIntervalGlobalMemoryUtilizationAvg OBJECT-TYPE
       SYNTAX Gauge32
       MAX-ACCESS read-only
       STATUS current
       DESCRIPTION
           "Average memory utilization (%).
AC INI-Param: N/A"
       ::= {acKpiSystemStatsIntervalGlobalEntry 3}



     acKpiStorageStats OBJECT IDENTIFIER ::= {acKpiSystem 3}


     acKpiStorageStatsCurrent OBJECT IDENTIFIER ::= {acKpiStorageStats 1}


     acKpiStorageStatsCurrentGlobal OBJECT IDENTIFIER ::= {acKpiStorageStatsCurrent 1}


     acKpiStorageStatsCurrentTables OBJECT IDENTIFIER ::= {acKpiStorageStatsCurrent 2}


     -- ****************************************
     -- acKpiStorageStatsCurrentPartition table declaration
     -- ****************************************
     acKpiStorageStatsCurrentPartitionTable OBJECT-TYPE
       SYNTAX SEQUENCE OF AcKpiStorageStatsCurrentPartitionEntry
       MAX-ACCESS not-accessible
       STATUS current
       DESCRIPTION
           ""
       ::= {acKpiStorageStatsCurrentTables 1}



     -- ****************************************
     -- acKpiStorageStatsCurrentPartition table entry
     -- ****************************************
     acKpiStorageStatsCurrentPartitionEntry OBJECT-TYPE
       SYNTAX AcKpiStorageStatsCurrentPartitionEntry
       MAX-ACCESS not-accessible
       STATUS current
       DESCRIPTION
           ""
       INDEX {acKpiStorageStatsCurrentPartitionIndex}
       ::= {acKpiStorageStatsCurrentPartitionTable 1}



     -- ****************************************
     -- acKpiStorageStatsCurrentPartition TABLE
     -- ****************************************
     AcKpiStorageStatsCurrentPartitionEntry ::= SEQUENCE {
       acKpiStorageStatsCurrentPartitionIndex          Unsigned32,
       acKpiStorageStatsCurrentPartitionStorageUtilization 
                                                       Gauge32,
       acKpiStorageStatsCurrentPartitionStorageUsage   Gauge32
     }



     acKpiStorageStatsCurrentPartitionIndex OBJECT-TYPE
       SYNTAX Unsigned32 (0..32767)
       MAX-ACCESS not-accessible
       STATUS current
       DESCRIPTION
           "
AC INI-Param: N/A"
       ::= {acKpiStorageStatsCurrentPartitionEntry 1}



     acKpiStorageStatsCurrentPartitionStorageUtilization OBJECT-TYPE
       SYNTAX Gauge32
       MAX-ACCESS read-only
       STATUS current
       DESCRIPTION
           "Storage utilization (%).
AC INI-Param: N/A"
       ::= {acKpiStorageStatsCurrentPartitionEntry 2}



     acKpiStorageStatsCurrentPartitionStorageUsage OBJECT-TYPE
       SYNTAX Gauge32
       MAX-ACCESS read-only
       STATUS current
       DESCRIPTION
           "Storage usage (Kbytes).
AC INI-Param: N/A"
       ::= {acKpiStorageStatsCurrentPartitionEntry 3}



     acKpiStorageStatsInterval OBJECT IDENTIFIER ::= {acKpiStorageStats 2}


     acKpiStorageStatsIntervalGlobal OBJECT IDENTIFIER ::= {acKpiStorageStatsInterval 1}


     acKpiStorageStatsIntervalTables OBJECT IDENTIFIER ::= {acKpiStorageStatsInterval 2}


     -- ****************************************
     -- acKpiStorageStatsIntervalPartition table declaration
     -- ****************************************
     acKpiStorageStatsIntervalPartitionTable OBJECT-TYPE
       SYNTAX SEQUENCE OF AcKpiStorageStatsIntervalPartitionEntry
       MAX-ACCESS not-accessible
       STATUS current
       DESCRIPTION
           ""
       ::= {acKpiStorageStatsIntervalTables 1}



     -- ****************************************
     -- acKpiStorageStatsIntervalPartition table entry
     -- ****************************************
     acKpiStorageStatsIntervalPartitionEntry OBJECT-TYPE
       SYNTAX AcKpiStorageStatsIntervalPartitionEntry
       MAX-ACCESS not-accessible
       STATUS current
       DESCRIPTION
           ""
       INDEX {acKpiStorageStatsIntervalPartitionIndex,acKpiStorageStatsIntervalPartitionInterval}
       ::= {acKpiStorageStatsIntervalPartitionTable 1}



     -- ****************************************
     -- acKpiStorageStatsIntervalPartition TABLE
     -- ****************************************
     AcKpiStorageStatsIntervalPartitionEntry ::= SEQUENCE {
       acKpiStorageStatsIntervalPartitionIndex         Unsigned32,
       acKpiStorageStatsIntervalPartitionInterval      Unsigned32,
       acKpiStorageStatsIntervalPartitionStorageUtilizationMax 
                                                       Gauge32,
       acKpiStorageStatsIntervalPartitionStorageUtilizationAvg 
                                                       Gauge32,
       acKpiStorageStatsIntervalPartitionStorageUsageAvg 
                                                       Gauge32,
       acKpiStorageStatsIntervalPartitionStorageUsageMax 
                                                       Gauge32
     }



     acKpiStorageStatsIntervalPartitionIndex OBJECT-TYPE
       SYNTAX Unsigned32 (0..32767)
       MAX-ACCESS not-accessible
       STATUS current
       DESCRIPTION
           "
AC INI-Param: N/A"
       ::= {acKpiStorageStatsIntervalPartitionEntry 1}



     acKpiStorageStatsIntervalPartitionInterval OBJECT-TYPE
       SYNTAX Unsigned32 (1..200)
       MAX-ACCESS not-accessible
       STATUS current
       DESCRIPTION
           "
AC INI-Param: N/A"
       ::= {acKpiStorageStatsIntervalPartitionEntry 2}



     acKpiStorageStatsIntervalPartitionStorageUtilizationMax OBJECT-TYPE
       SYNTAX Gauge32
       MAX-ACCESS read-only
       STATUS current
       DESCRIPTION
           "Maximum storage utilization (%).
AC INI-Param: N/A"
       ::= {acKpiStorageStatsIntervalPartitionEntry 3}



     acKpiStorageStatsIntervalPartitionStorageUtilizationAvg OBJECT-TYPE
       SYNTAX Gauge32
       MAX-ACCESS read-only
       STATUS current
       DESCRIPTION
           "Average storage utilization (%).
AC INI-Param: N/A"
       ::= {acKpiStorageStatsIntervalPartitionEntry 4}



     acKpiStorageStatsIntervalPartitionStorageUsageAvg OBJECT-TYPE
       SYNTAX Gauge32
       MAX-ACCESS read-only
       STATUS current
       DESCRIPTION
           "Average storage usage (Kbytes).
AC INI-Param: N/A"
       ::= {acKpiStorageStatsIntervalPartitionEntry 5}



     acKpiStorageStatsIntervalPartitionStorageUsageMax OBJECT-TYPE
       SYNTAX Gauge32
       MAX-ACCESS read-only
       STATUS current
       DESCRIPTION
           "Maximum storage usage (Kbytes).
AC INI-Param: N/A"
       ::= {acKpiStorageStatsIntervalPartitionEntry 6}



     acKpiCpuStats OBJECT IDENTIFIER ::= {acKpiSystem 4}


     acKpiCpuStatsCurrent OBJECT IDENTIFIER ::= {acKpiCpuStats 1}


     acKpiCpuStatsCurrentGlobal OBJECT IDENTIFIER ::= {acKpiCpuStatsCurrent 1}


     acKpiCpuStatsCurrentTables OBJECT IDENTIFIER ::= {acKpiCpuStatsCurrent 2}


     -- ****************************************
     -- acKpiCpuStatsCurrentCpu table declaration
     -- ****************************************
     acKpiCpuStatsCurrentCpuTable OBJECT-TYPE
       SYNTAX SEQUENCE OF AcKpiCpuStatsCurrentCpuEntry
       MAX-ACCESS not-accessible
       STATUS current
       DESCRIPTION
           ""
       ::= {acKpiCpuStatsCurrentTables 1}



     -- ****************************************
     -- acKpiCpuStatsCurrentCpu table entry
     -- ****************************************
     acKpiCpuStatsCurrentCpuEntry OBJECT-TYPE
       SYNTAX AcKpiCpuStatsCurrentCpuEntry
       MAX-ACCESS not-accessible
       STATUS current
       DESCRIPTION
           ""
       INDEX {acKpiCpuStatsCurrentCpuIndex}
       ::= {acKpiCpuStatsCurrentCpuTable 1}



     -- ****************************************
     -- acKpiCpuStatsCurrentCpu TABLE
     -- ****************************************
     AcKpiCpuStatsCurrentCpuEntry ::= SEQUENCE {
       acKpiCpuStatsCurrentCpuIndex                    Unsigned32,
       acKpiCpuStatsCurrentCpuCpuUtilization           Gauge32
     }



     acKpiCpuStatsCurrentCpuIndex OBJECT-TYPE
       SYNTAX Unsigned32 (0..32767)
       MAX-ACCESS not-accessible
       STATUS current
       DESCRIPTION
           "
AC INI-Param: N/A"
       ::= {acKpiCpuStatsCurrentCpuEntry 1}



     acKpiCpuStatsCurrentCpuCpuUtilization OBJECT-TYPE
       SYNTAX Gauge32
       MAX-ACCESS read-only
       STATUS current
       DESCRIPTION
           "CPU utilization (%).
AC INI-Param: N/A"
       ::= {acKpiCpuStatsCurrentCpuEntry 2}



     acKpiCpuStatsInterval OBJECT IDENTIFIER ::= {acKpiCpuStats 2}


     acKpiCpuStatsIntervalGlobal OBJECT IDENTIFIER ::= {acKpiCpuStatsInterval 1}


     acKpiCpuStatsIntervalTables OBJECT IDENTIFIER ::= {acKpiCpuStatsInterval 2}


     -- ****************************************
     -- acKpiCpuStatsIntervalCpu table declaration
     -- ****************************************
     acKpiCpuStatsIntervalCpuTable OBJECT-TYPE
       SYNTAX SEQUENCE OF AcKpiCpuStatsIntervalCpuEntry
       MAX-ACCESS not-accessible
       STATUS current
       DESCRIPTION
           ""
       ::= {acKpiCpuStatsIntervalTables 1}



     -- ****************************************
     -- acKpiCpuStatsIntervalCpu table entry
     -- ****************************************
     acKpiCpuStatsIntervalCpuEntry OBJECT-TYPE
       SYNTAX AcKpiCpuStatsIntervalCpuEntry
       MAX-ACCESS not-accessible
       STATUS current
       DESCRIPTION
           ""
       INDEX {acKpiCpuStatsIntervalCpuIndex,acKpiCpuStatsIntervalCpuInterval}
       ::= {acKpiCpuStatsIntervalCpuTable 1}



     -- ****************************************
     -- acKpiCpuStatsIntervalCpu TABLE
     -- ****************************************
     AcKpiCpuStatsIntervalCpuEntry ::= SEQUENCE {
       acKpiCpuStatsIntervalCpuIndex                   Unsigned32,
       acKpiCpuStatsIntervalCpuInterval                Unsigned32,
       acKpiCpuStatsIntervalCpuCpuUtilizationMax       Gauge32,
       acKpiCpuStatsIntervalCpuCpuUtilizationAvg       Gauge32
     }



     acKpiCpuStatsIntervalCpuIndex OBJECT-TYPE
       SYNTAX Unsigned32 (0..32767)
       MAX-ACCESS not-accessible
       STATUS current
       DESCRIPTION
           "
AC INI-Param: N/A"
       ::= {acKpiCpuStatsIntervalCpuEntry 1}



     acKpiCpuStatsIntervalCpuInterval OBJECT-TYPE
       SYNTAX Unsigned32 (1..200)
       MAX-ACCESS not-accessible
       STATUS current
       DESCRIPTION
           "
AC INI-Param: N/A"
       ::= {acKpiCpuStatsIntervalCpuEntry 2}



     acKpiCpuStatsIntervalCpuCpuUtilizationMax OBJECT-TYPE
       SYNTAX Gauge32
       MAX-ACCESS read-only
       STATUS current
       DESCRIPTION
           "Maximum CPU utilization (%).
AC INI-Param: N/A"
       ::= {acKpiCpuStatsIntervalCpuEntry 3}



     acKpiCpuStatsIntervalCpuCpuUtilizationAvg OBJECT-TYPE
       SYNTAX Gauge32
       MAX-ACCESS read-only
       STATUS current
       DESCRIPTION
           "Average CPU utilization (%).
AC INI-Param: N/A"
       ::= {acKpiCpuStatsIntervalCpuEntry 4}



     acKpiSbc OBJECT IDENTIFIER ::= {acKpi 3}


     acKpiSbcCallStats OBJECT IDENTIFIER ::= {acKpiSbc 1}


     acKpiSbcCallStatsCurrent OBJECT IDENTIFIER ::= {acKpiSbcCallStats 1}


     acKpiSbcCallStatsCurrentGlobal OBJECT IDENTIFIER ::= {acKpiSbcCallStatsCurrent 1}


     acKpiSbcCallStatsCurrentGlobalAverageCallDuration OBJECT-TYPE
       SYNTAX Gauge32
       MAX-ACCESS read-only
       STATUS current
       DESCRIPTION
           "Average call duration (ACD, seconds) over 1 min sliding window.
AC INI-Param: N/A"
       ::= {acKpiSbcCallStatsCurrentGlobal 1}



     acKpiSbcCallStatsCurrentGlobalActiveCallsIn OBJECT-TYPE
       SYNTAX Gauge32
       MAX-ACCESS read-only
       STATUS current
       DESCRIPTION
           "Number of active inbound calls (INVITE dialogs in all states).
AC INI-Param: N/A"
       ::= {acKpiSbcCallStatsCurrentGlobal 2}



     acKpiSbcCallStatsCurrentGlobalActiveCallsOut OBJECT-TYPE
       SYNTAX Gauge32
       MAX-ACCESS read-only
       STATUS current
       DESCRIPTION
           "Number of active outbound calls (INVITE dialogs in all states).
AC INI-Param: N/A"
       ::= {acKpiSbcCallStatsCurrentGlobal 3}



     acKpiSbcCallStatsCurrentGlobalAttemptedCallsInTotal OBJECT-TYPE
       SYNTAX Counter64
       MAX-ACCESS read-only
       STATUS current
       DESCRIPTION
           "Total number of attempted inbound calls (INVITE dialogs).
AC INI-Param: N/A"
       ::= {acKpiSbcCallStatsCurrentGlobal 4}



     acKpiSbcCallStatsCurrentGlobalAttemptedCallsOutTotal OBJECT-TYPE
       SYNTAX Counter64
       MAX-ACCESS read-only
       STATUS current
       DESCRIPTION
           "Total number of attempted outbound calls (INVITE dialogs).
AC INI-Param: N/A"
       ::= {acKpiSbcCallStatsCurrentGlobal 5}



     acKpiSbcCallStatsCurrentGlobalAttemptedCallsRateIn OBJECT-TYPE
       SYNTAX Gauge32
       MAX-ACCESS read-only
       STATUS current
       DESCRIPTION
           "Rate of attempted inbound calls (call attempts per second).
AC INI-Param: N/A"
       ::= {acKpiSbcCallStatsCurrentGlobal 6}



     acKpiSbcCallStatsCurrentGlobalAttemptedCallsRateOut OBJECT-TYPE
       SYNTAX Gauge32
       MAX-ACCESS read-only
       STATUS current
       DESCRIPTION
           "Rate of attempted outbound calls (call attempts per second).
AC INI-Param: N/A"
       ::= {acKpiSbcCallStatsCurrentGlobal 7}



     acKpiSbcCallStatsCurrentGlobalEstablishedCallsInTotal OBJECT-TYPE
       SYNTAX Counter64
       MAX-ACCESS read-only
       STATUS current
       DESCRIPTION
           "Total number of established inbound calls (INVITE dialogs).
AC INI-Param: N/A"
       ::= {acKpiSbcCallStatsCurrentGlobal 8}



     acKpiSbcCallStatsCurrentGlobalEstablishedCallsOutTotal OBJECT-TYPE
       SYNTAX Counter64
       MAX-ACCESS read-only
       STATUS current
       DESCRIPTION
           "Total number of established outbound calls (INVITE dialogs).
AC INI-Param: N/A"
       ::= {acKpiSbcCallStatsCurrentGlobal 9}



     acKpiSbcCallStatsCurrentGlobalEstablishedCallsRateIn OBJECT-TYPE
       SYNTAX Gauge32
       MAX-ACCESS read-only
       STATUS current
       DESCRIPTION
           "Rate of established inbound calls (call establish per second).
AC INI-Param: N/A"
       ::= {acKpiSbcCallStatsCurrentGlobal 10}



     acKpiSbcCallStatsCurrentGlobalEstablishedCallsRateOut OBJECT-TYPE
       SYNTAX Gauge32
       MAX-ACCESS read-only
       STATUS current
       DESCRIPTION
           "Rate of established outbound calls (call establish per second).
AC INI-Param: N/A"
       ::= {acKpiSbcCallStatsCurrentGlobal 11}



     acKpiSbcCallStatsCurrentGlobalAnswerSeizureRatio OBJECT-TYPE
       SYNTAX Gauge32
       MAX-ACCESS read-only
       STATUS current
       DESCRIPTION
           "Answer/seizure ratio (ASR, %) over 1 min sliding window.
AC INI-Param: N/A"
       ::= {acKpiSbcCallStatsCurrentGlobal 12}



     acKpiSbcCallStatsCurrentGlobalNetworkEffectivenessRatio OBJECT-TYPE
       SYNTAX Gauge32
       MAX-ACCESS read-only
       STATUS current
       DESCRIPTION
           "Network effectiveness ratio (NER, %) over 1 min sliding window.
AC INI-Param: N/A"
       ::= {acKpiSbcCallStatsCurrentGlobal 13}



     acKpiSbcCallStatsCurrentGlobalForwardedCallsInTotal OBJECT-TYPE
       SYNTAX Counter64
       MAX-ACCESS read-only
       STATUS current
       DESCRIPTION
           "Total number of forwarded inbound calls (INVITE dialogs).
AC INI-Param: N/A"
       ::= {acKpiSbcCallStatsCurrentGlobal 14}



     acKpiSbcCallStatsCurrentGlobalForwardedCallsOutTotal OBJECT-TYPE
       SYNTAX Counter64
       MAX-ACCESS read-only
       STATUS current
       DESCRIPTION
           "Total number of forwarded outbound calls (INVITE dialogs).
AC INI-Param: N/A"
       ::= {acKpiSbcCallStatsCurrentGlobal 15}



     acKpiSbcCallStatsCurrentGlobalMediaBrokenConnectionCallsTotal OBJECT-TYPE
       SYNTAX Counter64
       MAX-ACCESS read-only
       STATUS current
       DESCRIPTION
           "Total number of calls that failed due to broken connection.
AC INI-Param: N/A"
       ::= {acKpiSbcCallStatsCurrentGlobal 16}



     acKpiSbcCallStatsCurrentGlobalNotEstablishSuccessCallsInTotal OBJECT-TYPE
       SYNTAX Counter64
       MAX-ACCESS read-only
       STATUS current
       DESCRIPTION
           "Total number of not established inbound calls configured as
success.
AC INI-Param: N/A"
       ::= {acKpiSbcCallStatsCurrentGlobal 17}



     acKpiSbcCallStatsCurrentGlobalNotEstablishSuccessCallsOutTotal OBJECT-TYPE
       SYNTAX Counter64
       MAX-ACCESS read-only
       STATUS current
       DESCRIPTION
           "Total number of not established outbound calls configured as
success.
AC INI-Param: N/A"
       ::= {acKpiSbcCallStatsCurrentGlobal 18}



     acKpiSbcCallStatsCurrentGlobalNotEstablishFailedCallsInTotal OBJECT-TYPE
       SYNTAX Counter64
       MAX-ACCESS read-only
       STATUS current
       DESCRIPTION
           "Total number of not established inbound calls configured as
failed.
AC INI-Param: N/A"
       ::= {acKpiSbcCallStatsCurrentGlobal 19}



     acKpiSbcCallStatsCurrentGlobalNotEstablishFailedCallsOutTotal OBJECT-TYPE
       SYNTAX Counter64
       MAX-ACCESS read-only
       STATUS current
       DESCRIPTION
           "Total number of not established outbound calls configured as
failed.
AC INI-Param: N/A"
       ::= {acKpiSbcCallStatsCurrentGlobal 20}



     acKpiSbcCallStatsCurrentGlobalBusyCallsInTotal OBJECT-TYPE
       SYNTAX Counter64
       MAX-ACCESS read-only
       STATUS current
       DESCRIPTION
           "Total number of released inbound calls due to callee being busy.
AC INI-Param: N/A"
       ::= {acKpiSbcCallStatsCurrentGlobal 21}



     acKpiSbcCallStatsCurrentGlobalBusyCallsOutTotal OBJECT-TYPE
       SYNTAX Counter64
       MAX-ACCESS read-only
       STATUS current
       DESCRIPTION
           "Total number of outbound calls closed due to callee being busy.
AC INI-Param: N/A"
       ::= {acKpiSbcCallStatsCurrentGlobal 22}



     acKpiSbcCallStatsCurrentGlobalNoAnswerCallsInTotal OBJECT-TYPE
       SYNTAX Counter64
       MAX-ACCESS read-only
       STATUS current
       DESCRIPTION
           "Total number of inbound calls closed due to no answer from callee.
AC INI-Param: N/A"
       ::= {acKpiSbcCallStatsCurrentGlobal 23}



     acKpiSbcCallStatsCurrentGlobalNoAnswerCallsOutTotal OBJECT-TYPE
       SYNTAX Counter64
       MAX-ACCESS read-only
       STATUS current
       DESCRIPTION
           "Total number of outbound calls closed due to no answer from
callee.
AC INI-Param: N/A"
       ::= {acKpiSbcCallStatsCurrentGlobal 24}



     acKpiSbcCallStatsCurrentGlobalNoResourcesCallsInTotal OBJECT-TYPE
       SYNTAX Counter64
       MAX-ACCESS read-only
       STATUS current
       DESCRIPTION
           "Total number of inbound calls closed due to lack of internal
resources.
AC INI-Param: N/A"
       ::= {acKpiSbcCallStatsCurrentGlobal 25}



     acKpiSbcCallStatsCurrentGlobalNoResourcesCallsOutTotal OBJECT-TYPE
       SYNTAX Counter64
       MAX-ACCESS read-only
       STATUS current
       DESCRIPTION
           "Total number of outbound calls closed due to lack of internal
resource.
AC INI-Param: N/A"
       ::= {acKpiSbcCallStatsCurrentGlobal 26}



     acKpiSbcCallStatsCurrentGlobalMediaMismatchCallsInTotal OBJECT-TYPE
       SYNTAX Counter64
       MAX-ACCESS read-only
       STATUS current
       DESCRIPTION
           "Total number of inbound calls closed due to media mismatch.
AC INI-Param: N/A"
       ::= {acKpiSbcCallStatsCurrentGlobal 27}



     acKpiSbcCallStatsCurrentGlobalMediaMismatchCallsOutTotal OBJECT-TYPE
       SYNTAX Counter64
       MAX-ACCESS read-only
       STATUS current
       DESCRIPTION
           "Total number of outbound calls closed due to media mismatch.
AC INI-Param: N/A"
       ::= {acKpiSbcCallStatsCurrentGlobal 28}



     acKpiSbcCallStatsCurrentGlobalAdmissionFailedCallsInTotal OBJECT-TYPE
       SYNTAX Counter64
       MAX-ACCESS read-only
       STATUS current
       DESCRIPTION
           "Total number of inbound calls closed due to admission control
(CAC).
AC INI-Param: N/A"
       ::= {acKpiSbcCallStatsCurrentGlobal 29}



     acKpiSbcCallStatsCurrentGlobalAdmissionFailedCallsOutTotal OBJECT-TYPE
       SYNTAX Counter64
       MAX-ACCESS read-only
       STATUS current
       DESCRIPTION
           "Total number of outbound calls closed due to admission control
(CAC).
AC INI-Param: N/A"
       ::= {acKpiSbcCallStatsCurrentGlobal 30}



     acKpiSbcCallStatsCurrentGlobalNoRouteCallsInTotal OBJECT-TYPE
       SYNTAX Counter64
       MAX-ACCESS read-only
       STATUS current
       DESCRIPTION
           "Total number of inbound calls closed due to routing failure.
AC INI-Param: N/A"
       ::= {acKpiSbcCallStatsCurrentGlobal 31}



     acKpiSbcCallStatsCurrentGlobalClassificationFailedCallsInTotal OBJECT-TYPE
       SYNTAX Counter64
       MAX-ACCESS read-only
       STATUS current
       DESCRIPTION
           "Total number of inbound calls closed due to classification failure.
AC INI-Param: N/A"
       ::= {acKpiSbcCallStatsCurrentGlobal 32}



     acKpiSbcCallStatsCurrentGlobalOtherReasonCallsInTotal OBJECT-TYPE
       SYNTAX Counter64
       MAX-ACCESS read-only
       STATUS current
       DESCRIPTION
           "Total number of inbound calls closed due to other reasons.
AC INI-Param: N/A"
       ::= {acKpiSbcCallStatsCurrentGlobal 33}



     acKpiSbcCallStatsCurrentGlobalOtherReasonCallsOutTotal OBJECT-TYPE
       SYNTAX Counter64
       MAX-ACCESS read-only
       STATUS current
       DESCRIPTION
           "Total number of outbound calls closed due to other reasons.
AC INI-Param: N/A"
       ::= {acKpiSbcCallStatsCurrentGlobal 34}



     acKpiSbcCallStatsCurrentGlobalAbnormalTerminatedCallsInTotal OBJECT-TYPE
       SYNTAX Counter64
       MAX-ACCESS read-only
       STATUS current
       DESCRIPTION
           "Total number of abnormally terminated inbound calls (after connect).
AC INI-Param: N/A"
       ::= {acKpiSbcCallStatsCurrentGlobal 35}



     acKpiSbcCallStatsCurrentGlobalAbnormalTerminatedCallsOutTotal OBJECT-TYPE
       SYNTAX Counter64
       MAX-ACCESS read-only
       STATUS current
       DESCRIPTION
           "Total number of abnormally terminated outbound calls (after
connect).
AC INI-Param: N/A"
       ::= {acKpiSbcCallStatsCurrentGlobal 36}



     acKpiSbcCallStatsCurrentGlobalPostDialDelay OBJECT-TYPE
       SYNTAX Gauge32
       MAX-ACCESS read-only
       STATUS current
       DESCRIPTION
           "Number of seconds from INVITE to response (over 1 min sliding
window).
AC INI-Param: N/A"
       ::= {acKpiSbcCallStatsCurrentGlobal 37}



     acKpiSbcCallStatsCurrentGlobalMinutesOfUsageTotal OBJECT-TYPE
       SYNTAX Gauge32
       MAX-ACCESS read-only
       STATUS current
       DESCRIPTION
           "Total sum in minutes of call duration.
AC INI-Param: N/A"
       ::= {acKpiSbcCallStatsCurrentGlobal 38}



     acKpiSbcCallStatsCurrentGlobalShortCallsCounterTotal OBJECT-TYPE
       SYNTAX Counter64
       MAX-ACCESS read-only
       STATUS current
       DESCRIPTION
           "Total number of calls with duration shorter than pre-set threshold.
AC INI-Param: N/A"
       ::= {acKpiSbcCallStatsCurrentGlobal 39}



     acKpiSbcCallStatsCurrentGlobalLongCallsCounterTotal OBJECT-TYPE
       SYNTAX Counter64
       MAX-ACCESS read-only
       STATUS current
       DESCRIPTION
           "Total number of calls with duration longer than pre-set threshold.
AC INI-Param: N/A"
       ::= {acKpiSbcCallStatsCurrentGlobal 40}



     acKpiSbcCallStatsCurrentGlobalNotEstablishCallsInTotal OBJECT-TYPE
       SYNTAX Counter64
       MAX-ACCESS read-only
       STATUS current
       DESCRIPTION
           "Total number of not established inbound calls (due to all reasons).
AC INI-Param: N/A"
       ::= {acKpiSbcCallStatsCurrentGlobal 41}



     acKpiSbcCallStatsCurrentGlobalNotEstablishCallsOutTotal OBJECT-TYPE
       SYNTAX Counter64
       MAX-ACCESS read-only
       STATUS current
       DESCRIPTION
           "Total number of not established outbound calls (due to all reasons).
AC INI-Param: N/A"
       ::= {acKpiSbcCallStatsCurrentGlobal 42}



     acKpiSbcCallStatsCurrentGlobalActiveSessions OBJECT-TYPE
       SYNTAX Gauge32
       MAX-ACCESS read-only
       STATUS current
       DESCRIPTION
           "Number of active SBC sessions.
AC INI-Param: N/A"
       ::= {acKpiSbcCallStatsCurrentGlobal 43}



     acKpiSbcCallStatsCurrentTables OBJECT IDENTIFIER ::= {acKpiSbcCallStatsCurrent 2}


     -- ****************************************
     -- acKpiSbcCallStatsCurrentIpGroup table declaration
     -- ****************************************
     acKpiSbcCallStatsCurrentIpGroupTable OBJECT-TYPE
       SYNTAX SEQUENCE OF AcKpiSbcCallStatsCurrentIpGroupEntry
       MAX-ACCESS not-accessible
       STATUS current
       DESCRIPTION
           ""
       ::= {acKpiSbcCallStatsCurrentTables 1}



     -- ****************************************
     -- acKpiSbcCallStatsCurrentIpGroup table entry
     -- ****************************************
     acKpiSbcCallStatsCurrentIpGroupEntry OBJECT-TYPE
       SYNTAX AcKpiSbcCallStatsCurrentIpGroupEntry
       MAX-ACCESS not-accessible
       STATUS current
       DESCRIPTION
           ""
       INDEX {acKpiSbcCallStatsCurrentIpGroupIndex}
       ::= {acKpiSbcCallStatsCurrentIpGroupTable 1}



     -- ****************************************
     -- acKpiSbcCallStatsCurrentIpGroup TABLE
     -- ****************************************
     AcKpiSbcCallStatsCurrentIpGroupEntry ::= SEQUENCE {
       acKpiSbcCallStatsCurrentIpGroupIndex            Unsigned32,
       acKpiSbcCallStatsCurrentIpGroupAverageCallDuration 
                                                       Gauge32,
       acKpiSbcCallStatsCurrentIpGroupActiveCallsIn    Gauge32,
       acKpiSbcCallStatsCurrentIpGroupActiveCallsOut   Gauge32,
       acKpiSbcCallStatsCurrentIpGroupAttemptedCallsInTotal 
                                                       Counter64,
       acKpiSbcCallStatsCurrentIpGroupAttemptedCallsOutTotal 
                                                       Counter64,
       acKpiSbcCallStatsCurrentIpGroupAttemptedCallsRateIn 
                                                       Gauge32,
       acKpiSbcCallStatsCurrentIpGroupAttemptedCallsRateOut 
                                                       Gauge32,
       acKpiSbcCallStatsCurrentIpGroupEstablishedCallsInTotal 
                                                       Counter64,
       acKpiSbcCallStatsCurrentIpGroupEstablishedCallsOutTotal 
                                                       Counter64,
       acKpiSbcCallStatsCurrentIpGroupEstablishedCallsRateIn 
                                                       Gauge32,
       acKpiSbcCallStatsCurrentIpGroupEstablishedCallsRateOut 
                                                       Gauge32,
       acKpiSbcCallStatsCurrentIpGroupAnswerSeizureRatio 
                                                       Gauge32,
       acKpiSbcCallStatsCurrentIpGroupNetworkEffectivenessRatio 
                                                       Gauge32,
       acKpiSbcCallStatsCurrentIpGroupForwardedCallsInTotal 
                                                       Counter64,
       acKpiSbcCallStatsCurrentIpGroupForwardedCallsOutTotal 
                                                       Counter64,
       acKpiSbcCallStatsCurrentIpGroupMediaBrokenConnectionCallsTotal 
                                                       Counter64,
       acKpiSbcCallStatsCurrentIpGroupNotEstablishSuccessCallsInTotal 
                                                       Counter64,
       acKpiSbcCallStatsCurrentIpGroupNotEstablishSuccessCallsOutTotal 
                                                       Counter64,
       acKpiSbcCallStatsCurrentIpGroupNotEstablishFailedCallsInTotal 
                                                       Counter64,
       acKpiSbcCallStatsCurrentIpGroupNotEstablishFailedCallsOutTotal 
                                                       Counter64,
       acKpiSbcCallStatsCurrentIpGroupBusyCallsInTotal Counter64,
       acKpiSbcCallStatsCurrentIpGroupBusyCallsOutTotal 
                                                       Counter64,
       acKpiSbcCallStatsCurrentIpGroupNoAnswerCallsInTotal 
                                                       Counter64,
       acKpiSbcCallStatsCurrentIpGroupNoAnswerCallsOutTotal 
                                                       Counter64,
       acKpiSbcCallStatsCurrentIpGroupNoResourcesCallsInTotal 
                                                       Counter64,
       acKpiSbcCallStatsCurrentIpGroupNoResourcesCallsOutTotal 
                                                       Counter64,
       acKpiSbcCallStatsCurrentIpGroupMediaMismatchCallsInTotal 
                                                       Counter64,
       acKpiSbcCallStatsCurrentIpGroupMediaMismatchCallsOutTotal 
                                                       Counter64,
       acKpiSbcCallStatsCurrentIpGroupAdmissionFailedCallsInTotal 
                                                       Counter64,
       acKpiSbcCallStatsCurrentIpGroupAdmissionFailedCallsOutTotal 
                                                       Counter64,
       acKpiSbcCallStatsCurrentIpGroupNoRouteCallsInTotal 
                                                       Counter64,
       acKpiSbcCallStatsCurrentIpGroupOtherReasonCallsInTotal 
                                                       Counter64,
       acKpiSbcCallStatsCurrentIpGroupOtherReasonCallsOutTotal 
                                                       Counter64,
       acKpiSbcCallStatsCurrentIpGroupAbnormalTerminatedCallsInTotal 
                                                       Counter64,
       acKpiSbcCallStatsCurrentIpGroupAbnormalTerminatedCallsOutTotal 
                                                       Counter64,
       acKpiSbcCallStatsCurrentIpGroupPostDialDelay    Gauge32,
       acKpiSbcCallStatsCurrentIpGroupMinutesOfUsageTotal 
                                                       Gauge32,
       acKpiSbcCallStatsCurrentIpGroupShortCallsCounterTotal 
                                                       Counter64,
       acKpiSbcCallStatsCurrentIpGroupLongCallsCounterTotal 
                                                       Counter64,
       acKpiSbcCallStatsCurrentIpGroupNotEstablishCallsOutTotal 
                                                       Counter64,
       acKpiSbcCallStatsCurrentIpGroupNotEstablishCallsInTotal 
                                                       Counter64
     }



     acKpiSbcCallStatsCurrentIpGroupIndex OBJECT-TYPE
       SYNTAX Unsigned32 (0..32767)
       MAX-ACCESS not-accessible
       STATUS current
       DESCRIPTION
           "
AC INI-Param: N/A"
       ::= {acKpiSbcCallStatsCurrentIpGroupEntry 1}



     acKpiSbcCallStatsCurrentIpGroupAverageCallDuration OBJECT-TYPE
       SYNTAX Gauge32
       MAX-ACCESS read-only
       STATUS current
       DESCRIPTION
           "Average call duration (ACD, seconds) over 1 min sliding window.
AC INI-Param: N/A"
       ::= {acKpiSbcCallStatsCurrentIpGroupEntry 2}



     acKpiSbcCallStatsCurrentIpGroupActiveCallsIn OBJECT-TYPE
       SYNTAX Gauge32
       MAX-ACCESS read-only
       STATUS current
       DESCRIPTION
           "Number of active inbound calls (INVITE dialogs in all states).
AC INI-Param: N/A"
       ::= {acKpiSbcCallStatsCurrentIpGroupEntry 3}



     acKpiSbcCallStatsCurrentIpGroupActiveCallsOut OBJECT-TYPE
       SYNTAX Gauge32
       MAX-ACCESS read-only
       STATUS current
       DESCRIPTION
           "Number of active outbound calls (INVITE dialogs in all states).
AC INI-Param: N/A"
       ::= {acKpiSbcCallStatsCurrentIpGroupEntry 4}



     acKpiSbcCallStatsCurrentIpGroupAttemptedCallsInTotal OBJECT-TYPE
       SYNTAX Counter64
       MAX-ACCESS read-only
       STATUS current
       DESCRIPTION
           "Total number of attempted inbound calls (INVITE dialogs).
AC INI-Param: N/A"
       ::= {acKpiSbcCallStatsCurrentIpGroupEntry 5}



     acKpiSbcCallStatsCurrentIpGroupAttemptedCallsOutTotal OBJECT-TYPE
       SYNTAX Counter64
       MAX-ACCESS read-only
       STATUS current
       DESCRIPTION
           "Total number of attempted outbound calls (INVITE dialogs).
AC INI-Param: N/A"
       ::= {acKpiSbcCallStatsCurrentIpGroupEntry 6}



     acKpiSbcCallStatsCurrentIpGroupAttemptedCallsRateIn OBJECT-TYPE
       SYNTAX Gauge32
       MAX-ACCESS read-only
       STATUS current
       DESCRIPTION
           "Rate of attempted inbound calls (call attempts per second).
AC INI-Param: N/A"
       ::= {acKpiSbcCallStatsCurrentIpGroupEntry 7}



     acKpiSbcCallStatsCurrentIpGroupAttemptedCallsRateOut OBJECT-TYPE
       SYNTAX Gauge32
       MAX-ACCESS read-only
       STATUS current
       DESCRIPTION
           "Rate of attempted outbound calls (call attempts per second).
AC INI-Param: N/A"
       ::= {acKpiSbcCallStatsCurrentIpGroupEntry 8}



     acKpiSbcCallStatsCurrentIpGroupEstablishedCallsInTotal OBJECT-TYPE
       SYNTAX Counter64
       MAX-ACCESS read-only
       STATUS current
       DESCRIPTION
           "Total number of established inbound calls (INVITE dialogs).
AC INI-Param: N/A"
       ::= {acKpiSbcCallStatsCurrentIpGroupEntry 9}



     acKpiSbcCallStatsCurrentIpGroupEstablishedCallsOutTotal OBJECT-TYPE
       SYNTAX Counter64
       MAX-ACCESS read-only
       STATUS current
       DESCRIPTION
           "Total number of established outbound calls (INVITE dialogs).
AC INI-Param: N/A"
       ::= {acKpiSbcCallStatsCurrentIpGroupEntry 10}



     acKpiSbcCallStatsCurrentIpGroupEstablishedCallsRateIn OBJECT-TYPE
       SYNTAX Gauge32
       MAX-ACCESS read-only
       STATUS current
       DESCRIPTION
           "Rate of established inbound calls (call establish per second).
AC INI-Param: N/A"
       ::= {acKpiSbcCallStatsCurrentIpGroupEntry 11}



     acKpiSbcCallStatsCurrentIpGroupEstablishedCallsRateOut OBJECT-TYPE
       SYNTAX Gauge32
       MAX-ACCESS read-only
       STATUS current
       DESCRIPTION
           "Rate of established outbound calls (call establish per second).
AC INI-Param: N/A"
       ::= {acKpiSbcCallStatsCurrentIpGroupEntry 12}



     acKpiSbcCallStatsCurrentIpGroupAnswerSeizureRatio OBJECT-TYPE
       SYNTAX Gauge32
       MAX-ACCESS read-only
       STATUS current
       DESCRIPTION
           "Answer/seizure ratio (ASR, %) over 1 min sliding window.
AC INI-Param: N/A"
       ::= {acKpiSbcCallStatsCurrentIpGroupEntry 13}



     acKpiSbcCallStatsCurrentIpGroupNetworkEffectivenessRatio OBJECT-TYPE
       SYNTAX Gauge32
       MAX-ACCESS read-only
       STATUS current
       DESCRIPTION
           "Network effectiveness ratio (NER, %) over 1 min sliding window.
AC INI-Param: N/A"
       ::= {acKpiSbcCallStatsCurrentIpGroupEntry 14}



     acKpiSbcCallStatsCurrentIpGroupForwardedCallsInTotal OBJECT-TYPE
       SYNTAX Counter64
       MAX-ACCESS read-only
       STATUS current
       DESCRIPTION
           "Total number of forwarded inbound calls (INVITE dialogs).
AC INI-Param: N/A"
       ::= {acKpiSbcCallStatsCurrentIpGroupEntry 15}



     acKpiSbcCallStatsCurrentIpGroupForwardedCallsOutTotal OBJECT-TYPE
       SYNTAX Counter64
       MAX-ACCESS read-only
       STATUS current
       DESCRIPTION
           "Total number of forwarded outbound calls (INVITE dialogs).
AC INI-Param: N/A"
       ::= {acKpiSbcCallStatsCurrentIpGroupEntry 16}



     acKpiSbcCallStatsCurrentIpGroupMediaBrokenConnectionCallsTotal OBJECT-TYPE
       SYNTAX Counter64
       MAX-ACCESS read-only
       STATUS current
       DESCRIPTION
           "Total number of calls that failed due to broken connection.
AC INI-Param: N/A"
       ::= {acKpiSbcCallStatsCurrentIpGroupEntry 17}



     acKpiSbcCallStatsCurrentIpGroupNotEstablishSuccessCallsInTotal OBJECT-TYPE
       SYNTAX Counter64
       MAX-ACCESS read-only
       STATUS current
       DESCRIPTION
           "Total number of not established inbound calls configured as
success.
AC INI-Param: N/A"
       ::= {acKpiSbcCallStatsCurrentIpGroupEntry 18}



     acKpiSbcCallStatsCurrentIpGroupNotEstablishSuccessCallsOutTotal OBJECT-TYPE
       SYNTAX Counter64
       MAX-ACCESS read-only
       STATUS current
       DESCRIPTION
           "Total number of not established outbound calls configured as
success.
AC INI-Param: N/A"
       ::= {acKpiSbcCallStatsCurrentIpGroupEntry 19}



     acKpiSbcCallStatsCurrentIpGroupNotEstablishFailedCallsInTotal OBJECT-TYPE
       SYNTAX Counter64
       MAX-ACCESS read-only
       STATUS current
       DESCRIPTION
           "Total number of not established inbound calls configured as
failed.
AC INI-Param: N/A"
       ::= {acKpiSbcCallStatsCurrentIpGroupEntry 20}



     acKpiSbcCallStatsCurrentIpGroupNotEstablishFailedCallsOutTotal OBJECT-TYPE
       SYNTAX Counter64
       MAX-ACCESS read-only
       STATUS current
       DESCRIPTION
           "Total number of not established outbound calls configured as
failed.
AC INI-Param: N/A"
       ::= {acKpiSbcCallStatsCurrentIpGroupEntry 21}



     acKpiSbcCallStatsCurrentIpGroupBusyCallsInTotal OBJECT-TYPE
       SYNTAX Counter64
       MAX-ACCESS read-only
       STATUS current
       DESCRIPTION
           "Total number of released inbound calls due to callee being busy.
AC INI-Param: N/A"
       ::= {acKpiSbcCallStatsCurrentIpGroupEntry 22}



     acKpiSbcCallStatsCurrentIpGroupBusyCallsOutTotal OBJECT-TYPE
       SYNTAX Counter64
       MAX-ACCESS read-only
       STATUS current
       DESCRIPTION
           "Total number of outbound calls closed due to callee being busy.
AC INI-Param: N/A"
       ::= {acKpiSbcCallStatsCurrentIpGroupEntry 23}



     acKpiSbcCallStatsCurrentIpGroupNoAnswerCallsInTotal OBJECT-TYPE
       SYNTAX Counter64
       MAX-ACCESS read-only
       STATUS current
       DESCRIPTION
           "Total number of inbound calls closed due to no answer from callee.
AC INI-Param: N/A"
       ::= {acKpiSbcCallStatsCurrentIpGroupEntry 24}



     acKpiSbcCallStatsCurrentIpGroupNoAnswerCallsOutTotal OBJECT-TYPE
       SYNTAX Counter64
       MAX-ACCESS read-only
       STATUS current
       DESCRIPTION
           "Total number of outbound calls closed due to no answer from
callee.
AC INI-Param: N/A"
       ::= {acKpiSbcCallStatsCurrentIpGroupEntry 25}



     acKpiSbcCallStatsCurrentIpGroupNoResourcesCallsInTotal OBJECT-TYPE
       SYNTAX Counter64
       MAX-ACCESS read-only
       STATUS current
       DESCRIPTION
           "Total number of inbound calls closed due to lack of internal
resources.
AC INI-Param: N/A"
       ::= {acKpiSbcCallStatsCurrentIpGroupEntry 26}



     acKpiSbcCallStatsCurrentIpGroupNoResourcesCallsOutTotal OBJECT-TYPE
       SYNTAX Counter64
       MAX-ACCESS read-only
       STATUS current
       DESCRIPTION
           "Total number of outbound calls closed due to lack of internal
resource.
AC INI-Param: N/A"
       ::= {acKpiSbcCallStatsCurrentIpGroupEntry 27}



     acKpiSbcCallStatsCurrentIpGroupMediaMismatchCallsInTotal OBJECT-TYPE
       SYNTAX Counter64
       MAX-ACCESS read-only
       STATUS current
       DESCRIPTION
           "Total number of inbound calls closed due to media mismatch.
AC INI-Param: N/A"
       ::= {acKpiSbcCallStatsCurrentIpGroupEntry 28}



     acKpiSbcCallStatsCurrentIpGroupMediaMismatchCallsOutTotal OBJECT-TYPE
       SYNTAX Counter64
       MAX-ACCESS read-only
       STATUS current
       DESCRIPTION
           "Total number of outbound calls closed due to media mismatch.
AC INI-Param: N/A"
       ::= {acKpiSbcCallStatsCurrentIpGroupEntry 29}



     acKpiSbcCallStatsCurrentIpGroupAdmissionFailedCallsInTotal OBJECT-TYPE
       SYNTAX Counter64
       MAX-ACCESS read-only
       STATUS current
       DESCRIPTION
           "Total number of inbound calls closed due to admission control
(CAC).
AC INI-Param: N/A"
       ::= {acKpiSbcCallStatsCurrentIpGroupEntry 30}



     acKpiSbcCallStatsCurrentIpGroupAdmissionFailedCallsOutTotal OBJECT-TYPE
       SYNTAX Counter64
       MAX-ACCESS read-only
       STATUS current
       DESCRIPTION
           "Total number of outbound calls closed due to admission control
(CAC).
AC INI-Param: N/A"
       ::= {acKpiSbcCallStatsCurrentIpGroupEntry 31}



     acKpiSbcCallStatsCurrentIpGroupNoRouteCallsInTotal OBJECT-TYPE
       SYNTAX Counter64
       MAX-ACCESS read-only
       STATUS current
       DESCRIPTION
           "Total number of inbound calls closed due to routing failure.
AC INI-Param: N/A"
       ::= {acKpiSbcCallStatsCurrentIpGroupEntry 32}



     acKpiSbcCallStatsCurrentIpGroupOtherReasonCallsInTotal OBJECT-TYPE
       SYNTAX Counter64
       MAX-ACCESS read-only
       STATUS current
       DESCRIPTION
           "Total number of inbound calls closed due to other reasons.
AC INI-Param: N/A"
       ::= {acKpiSbcCallStatsCurrentIpGroupEntry 33}



     acKpiSbcCallStatsCurrentIpGroupOtherReasonCallsOutTotal OBJECT-TYPE
       SYNTAX Counter64
       MAX-ACCESS read-only
       STATUS current
       DESCRIPTION
           "Total number of outbound calls closed due to other reasons.
AC INI-Param: N/A"
       ::= {acKpiSbcCallStatsCurrentIpGroupEntry 34}



     acKpiSbcCallStatsCurrentIpGroupAbnormalTerminatedCallsInTotal OBJECT-TYPE
       SYNTAX Counter64
       MAX-ACCESS read-only
       STATUS current
       DESCRIPTION
           "Total number of abnormally terminated inbound calls (after connect).
AC INI-Param: N/A"
       ::= {acKpiSbcCallStatsCurrentIpGroupEntry 35}



     acKpiSbcCallStatsCurrentIpGroupAbnormalTerminatedCallsOutTotal OBJECT-TYPE
       SYNTAX Counter64
       MAX-ACCESS read-only
       STATUS current
       DESCRIPTION
           "Total number of abnormally terminated outbound calls (after
connect).
AC INI-Param: N/A"
       ::= {acKpiSbcCallStatsCurrentIpGroupEntry 36}



     acKpiSbcCallStatsCurrentIpGroupPostDialDelay OBJECT-TYPE
       SYNTAX Gauge32
       MAX-ACCESS read-only
       STATUS current
       DESCRIPTION
           "Number of seconds from INVITE to response (over 1 min sliding
window).
AC INI-Param: N/A"
       ::= {acKpiSbcCallStatsCurrentIpGroupEntry 37}



     acKpiSbcCallStatsCurrentIpGroupMinutesOfUsageTotal OBJECT-TYPE
       SYNTAX Gauge32
       MAX-ACCESS read-only
       STATUS current
       DESCRIPTION
           "Total sum in minutes of call duration.
AC INI-Param: N/A"
       ::= {acKpiSbcCallStatsCurrentIpGroupEntry 38}



     acKpiSbcCallStatsCurrentIpGroupShortCallsCounterTotal OBJECT-TYPE
       SYNTAX Counter64
       MAX-ACCESS read-only
       STATUS current
       DESCRIPTION
           "Total number of calls with duration shorter than pre-set threshold.
AC INI-Param: N/A"
       ::= {acKpiSbcCallStatsCurrentIpGroupEntry 39}



     acKpiSbcCallStatsCurrentIpGroupLongCallsCounterTotal OBJECT-TYPE
       SYNTAX Counter64
       MAX-ACCESS read-only
       STATUS current
       DESCRIPTION
           "Total number of calls with duration longer than pre-set threshold.
AC INI-Param: N/A"
       ::= {acKpiSbcCallStatsCurrentIpGroupEntry 40}



     acKpiSbcCallStatsCurrentIpGroupNotEstablishCallsOutTotal OBJECT-TYPE
       SYNTAX Counter64
       MAX-ACCESS read-only
       STATUS current
       DESCRIPTION
           "Total number of not established outbound calls (due to all reasons).
AC INI-Param: N/A"
       ::= {acKpiSbcCallStatsCurrentIpGroupEntry 41}



     acKpiSbcCallStatsCurrentIpGroupNotEstablishCallsInTotal OBJECT-TYPE
       SYNTAX Counter64
       MAX-ACCESS read-only
       STATUS current
       DESCRIPTION
           "Total number of not established inbound calls (due to all reasons).
AC INI-Param: N/A"
       ::= {acKpiSbcCallStatsCurrentIpGroupEntry 42}



     -- ****************************************
     -- acKpiSbcCallStatsCurrentSrd table declaration
     -- ****************************************
     acKpiSbcCallStatsCurrentSrdTable OBJECT-TYPE
       SYNTAX SEQUENCE OF AcKpiSbcCallStatsCurrentSrdEntry
       MAX-ACCESS not-accessible
       STATUS current
       DESCRIPTION
           ""
       ::= {acKpiSbcCallStatsCurrentTables 2}



     -- ****************************************
     -- acKpiSbcCallStatsCurrentSrd table entry
     -- ****************************************
     acKpiSbcCallStatsCurrentSrdEntry OBJECT-TYPE
       SYNTAX AcKpiSbcCallStatsCurrentSrdEntry
       MAX-ACCESS not-accessible
       STATUS current
       DESCRIPTION
           ""
       INDEX {acKpiSbcCallStatsCurrentSrdIndex}
       ::= {acKpiSbcCallStatsCurrentSrdTable 1}



     -- ****************************************
     -- acKpiSbcCallStatsCurrentSrd TABLE
     -- ****************************************
     AcKpiSbcCallStatsCurrentSrdEntry ::= SEQUENCE {
       acKpiSbcCallStatsCurrentSrdIndex                Unsigned32,
       acKpiSbcCallStatsCurrentSrdAverageCallDuration  Gauge32,
       acKpiSbcCallStatsCurrentSrdActiveCallsIn        Gauge32,
       acKpiSbcCallStatsCurrentSrdActiveCallsOut       Gauge32,
       acKpiSbcCallStatsCurrentSrdAttemptedCallsInTotal 
                                                       Counter64,
       acKpiSbcCallStatsCurrentSrdAttemptedCallsOutTotal 
                                                       Counter64,
       acKpiSbcCallStatsCurrentSrdAttemptedCallsRateIn Gauge32,
       acKpiSbcCallStatsCurrentSrdAttemptedCallsRateOut 
                                                       Gauge32,
       acKpiSbcCallStatsCurrentSrdEstablishedCallsInTotal 
                                                       Counter64,
       acKpiSbcCallStatsCurrentSrdEstablishedCallsOutTotal 
                                                       Counter64,
       acKpiSbcCallStatsCurrentSrdEstablishedCallsRateIn 
                                                       Gauge32,
       acKpiSbcCallStatsCurrentSrdEstablishedCallsRateOut 
                                                       Gauge32,
       acKpiSbcCallStatsCurrentSrdAnswerSeizureRatio   Gauge32,
       acKpiSbcCallStatsCurrentSrdNetworkEffectivenessRatio 
                                                       Gauge32,
       acKpiSbcCallStatsCurrentSrdForwardedCallsInTotal 
                                                       Counter64,
       acKpiSbcCallStatsCurrentSrdForwardedCallsOutTotal 
                                                       Counter64,
       acKpiSbcCallStatsCurrentSrdMediaBrokenConnectionCallsTotal 
                                                       Counter64,
       acKpiSbcCallStatsCurrentSrdNotEstablishSuccessCallsInTotal 
                                                       Counter64,
       acKpiSbcCallStatsCurrentSrdNotEstablishSuccessCallsOutTotal 
                                                       Counter64,
       acKpiSbcCallStatsCurrentSrdNotEstablishFailedCallsInTotal 
                                                       Counter64,
       acKpiSbcCallStatsCurrentSrdNotEstablishFailedCallsOutTotal 
                                                       Counter64,
       acKpiSbcCallStatsCurrentSrdBusyCallsInTotal     Counter64,
       acKpiSbcCallStatsCurrentSrdBusyCallsOutTotal    Counter64,
       acKpiSbcCallStatsCurrentSrdNoAnswerCallsInTotal Counter64,
       acKpiSbcCallStatsCurrentSrdNoAnswerCallsOutTotal 
                                                       Counter64,
       acKpiSbcCallStatsCurrentSrdNoResourcesCallsInTotal 
                                                       Counter64,
       acKpiSbcCallStatsCurrentSrdNoResourcesCallsOutTotal 
                                                       Counter64,
       acKpiSbcCallStatsCurrentSrdMediaMismatchCallsInTotal 
                                                       Counter64,
       acKpiSbcCallStatsCurrentSrdMediaMismatchCallsOutTotal 
                                                       Counter64,
       acKpiSbcCallStatsCurrentSrdAdmissionFailedCallsInTotal 
                                                       Counter64,
       acKpiSbcCallStatsCurrentSrdAdmissionFailedCallsOutTotal 
                                                       Counter64,
       acKpiSbcCallStatsCurrentSrdNoRouteCallsInTotal  Counter64,
       acKpiSbcCallStatsCurrentSrdClassificationFailedCallsInTotal 
                                                       Counter64,
       acKpiSbcCallStatsCurrentSrdOtherReasonCallsInTotal 
                                                       Counter64,
       acKpiSbcCallStatsCurrentSrdOtherReasonCallsOutTotal 
                                                       Counter64,
       acKpiSbcCallStatsCurrentSrdAbnormalTerminatedCallsInTotal 
                                                       Counter64,
       acKpiSbcCallStatsCurrentSrdAbnormalTerminatedCallsOutTotal 
                                                       Counter64,
       acKpiSbcCallStatsCurrentSrdPostDialDelay        Gauge32,
       acKpiSbcCallStatsCurrentSrdMinutesOfUsageTotal  Gauge32,
       acKpiSbcCallStatsCurrentSrdShortCallsCounterTotal 
                                                       Counter64,
       acKpiSbcCallStatsCurrentSrdLongCallsCounterTotal 
                                                       Counter64,
       acKpiSbcCallStatsCurrentSrdNotEstablishCallsOutTotal 
                                                       Counter64,
       acKpiSbcCallStatsCurrentSrdNotEstablishCallsInTotal 
                                                       Counter64
     }



     acKpiSbcCallStatsCurrentSrdIndex OBJECT-TYPE
       SYNTAX Unsigned32 (0..32767)
       MAX-ACCESS not-accessible
       STATUS current
       DESCRIPTION
           "
AC INI-Param: N/A"
       ::= {acKpiSbcCallStatsCurrentSrdEntry 1}



     acKpiSbcCallStatsCurrentSrdAverageCallDuration OBJECT-TYPE
       SYNTAX Gauge32
       MAX-ACCESS read-only
       STATUS current
       DESCRIPTION
           "Average call duration (ACD, seconds) over 1 min sliding window.
AC INI-Param: N/A"
       ::= {acKpiSbcCallStatsCurrentSrdEntry 2}



     acKpiSbcCallStatsCurrentSrdActiveCallsIn OBJECT-TYPE
       SYNTAX Gauge32
       MAX-ACCESS read-only
       STATUS current
       DESCRIPTION
           "Number of active inbound calls (INVITE dialogs in all states).
AC INI-Param: N/A"
       ::= {acKpiSbcCallStatsCurrentSrdEntry 3}



     acKpiSbcCallStatsCurrentSrdActiveCallsOut OBJECT-TYPE
       SYNTAX Gauge32
       MAX-ACCESS read-only
       STATUS current
       DESCRIPTION
           "Number of active outbound calls (INVITE dialogs in all states).
AC INI-Param: N/A"
       ::= {acKpiSbcCallStatsCurrentSrdEntry 4}



     acKpiSbcCallStatsCurrentSrdAttemptedCallsInTotal OBJECT-TYPE
       SYNTAX Counter64
       MAX-ACCESS read-only
       STATUS current
       DESCRIPTION
           "Total number of attempted inbound calls (INVITE dialogs).
AC INI-Param: N/A"
       ::= {acKpiSbcCallStatsCurrentSrdEntry 5}



     acKpiSbcCallStatsCurrentSrdAttemptedCallsOutTotal OBJECT-TYPE
       SYNTAX Counter64
       MAX-ACCESS read-only
       STATUS current
       DESCRIPTION
           "Total number of attempted outbound calls (INVITE dialogs).
AC INI-Param: N/A"
       ::= {acKpiSbcCallStatsCurrentSrdEntry 6}



     acKpiSbcCallStatsCurrentSrdAttemptedCallsRateIn OBJECT-TYPE
       SYNTAX Gauge32
       MAX-ACCESS read-only
       STATUS current
       DESCRIPTION
           "Rate of attempted inbound calls (call attempts per second).
AC INI-Param: N/A"
       ::= {acKpiSbcCallStatsCurrentSrdEntry 7}



     acKpiSbcCallStatsCurrentSrdAttemptedCallsRateOut OBJECT-TYPE
       SYNTAX Gauge32
       MAX-ACCESS read-only
       STATUS current
       DESCRIPTION
           "Rate of attempted outbound calls (call attempts per second).
AC INI-Param: N/A"
       ::= {acKpiSbcCallStatsCurrentSrdEntry 8}



     acKpiSbcCallStatsCurrentSrdEstablishedCallsInTotal OBJECT-TYPE
       SYNTAX Counter64
       MAX-ACCESS read-only
       STATUS current
       DESCRIPTION
           "Total number of established inbound calls (INVITE dialogs).
AC INI-Param: N/A"
       ::= {acKpiSbcCallStatsCurrentSrdEntry 9}



     acKpiSbcCallStatsCurrentSrdEstablishedCallsOutTotal OBJECT-TYPE
       SYNTAX Counter64
       MAX-ACCESS read-only
       STATUS current
       DESCRIPTION
           "Total number of established outbound calls (INVITE dialogs).
AC INI-Param: N/A"
       ::= {acKpiSbcCallStatsCurrentSrdEntry 10}



     acKpiSbcCallStatsCurrentSrdEstablishedCallsRateIn OBJECT-TYPE
       SYNTAX Gauge32
       MAX-ACCESS read-only
       STATUS current
       DESCRIPTION
           "Rate of established inbound calls (call establish per second).
AC INI-Param: N/A"
       ::= {acKpiSbcCallStatsCurrentSrdEntry 11}



     acKpiSbcCallStatsCurrentSrdEstablishedCallsRateOut OBJECT-TYPE
       SYNTAX Gauge32
       MAX-ACCESS read-only
       STATUS current
       DESCRIPTION
           "Rate of established outbound calls (call establish per second).
AC INI-Param: N/A"
       ::= {acKpiSbcCallStatsCurrentSrdEntry 12}



     acKpiSbcCallStatsCurrentSrdAnswerSeizureRatio OBJECT-TYPE
       SYNTAX Gauge32
       MAX-ACCESS read-only
       STATUS current
       DESCRIPTION
           "Answer/seizure ratio (ASR, %) over 1 min sliding window.
AC INI-Param: N/A"
       ::= {acKpiSbcCallStatsCurrentSrdEntry 13}



     acKpiSbcCallStatsCurrentSrdNetworkEffectivenessRatio OBJECT-TYPE
       SYNTAX Gauge32
       MAX-ACCESS read-only
       STATUS current
       DESCRIPTION
           "Network effectiveness ratio (NER, %) over 1 min sliding window.
AC INI-Param: N/A"
       ::= {acKpiSbcCallStatsCurrentSrdEntry 14}



     acKpiSbcCallStatsCurrentSrdForwardedCallsInTotal OBJECT-TYPE
       SYNTAX Counter64
       MAX-ACCESS read-only
       STATUS current
       DESCRIPTION
           "Total number of forwarded inbound calls (INVITE dialogs).
AC INI-Param: N/A"
       ::= {acKpiSbcCallStatsCurrentSrdEntry 15}



     acKpiSbcCallStatsCurrentSrdForwardedCallsOutTotal OBJECT-TYPE
       SYNTAX Counter64
       MAX-ACCESS read-only
       STATUS current
       DESCRIPTION
           "Total number of forwarded outbound calls (INVITE dialogs).
AC INI-Param: N/A"
       ::= {acKpiSbcCallStatsCurrentSrdEntry 16}



     acKpiSbcCallStatsCurrentSrdMediaBrokenConnectionCallsTotal OBJECT-TYPE
       SYNTAX Counter64
       MAX-ACCESS read-only
       STATUS current
       DESCRIPTION
           "Total number of calls that failed due to broken connection.
AC INI-Param: N/A"
       ::= {acKpiSbcCallStatsCurrentSrdEntry 17}



     acKpiSbcCallStatsCurrentSrdNotEstablishSuccessCallsInTotal OBJECT-TYPE
       SYNTAX Counter64
       MAX-ACCESS read-only
       STATUS current
       DESCRIPTION
           "Total number of not established inbound calls configured as
success.
AC INI-Param: N/A"
       ::= {acKpiSbcCallStatsCurrentSrdEntry 18}



     acKpiSbcCallStatsCurrentSrdNotEstablishSuccessCallsOutTotal OBJECT-TYPE
       SYNTAX Counter64
       MAX-ACCESS read-only
       STATUS current
       DESCRIPTION
           "Total number of not established outbound calls configured as
success.
AC INI-Param: N/A"
       ::= {acKpiSbcCallStatsCurrentSrdEntry 19}



     acKpiSbcCallStatsCurrentSrdNotEstablishFailedCallsInTotal OBJECT-TYPE
       SYNTAX Counter64
       MAX-ACCESS read-only
       STATUS current
       DESCRIPTION
           "Total number of not established inbound calls configured as
failed.
AC INI-Param: N/A"
       ::= {acKpiSbcCallStatsCurrentSrdEntry 20}



     acKpiSbcCallStatsCurrentSrdNotEstablishFailedCallsOutTotal OBJECT-TYPE
       SYNTAX Counter64
       MAX-ACCESS read-only
       STATUS current
       DESCRIPTION
           "Total number of not established outbound calls configured as
failed.
AC INI-Param: N/A"
       ::= {acKpiSbcCallStatsCurrentSrdEntry 21}



     acKpiSbcCallStatsCurrentSrdBusyCallsInTotal OBJECT-TYPE
       SYNTAX Counter64
       MAX-ACCESS read-only
       STATUS current
       DESCRIPTION
           "Total number of released inbound calls due to callee being busy.
AC INI-Param: N/A"
       ::= {acKpiSbcCallStatsCurrentSrdEntry 22}



     acKpiSbcCallStatsCurrentSrdBusyCallsOutTotal OBJECT-TYPE
       SYNTAX Counter64
       MAX-ACCESS read-only
       STATUS current
       DESCRIPTION
           "Total number of outbound calls closed due to callee being busy.
AC INI-Param: N/A"
       ::= {acKpiSbcCallStatsCurrentSrdEntry 23}



     acKpiSbcCallStatsCurrentSrdNoAnswerCallsInTotal OBJECT-TYPE
       SYNTAX Counter64
       MAX-ACCESS read-only
       STATUS current
       DESCRIPTION
           "Total number of inbound calls closed due to no answer from callee.
AC INI-Param: N/A"
       ::= {acKpiSbcCallStatsCurrentSrdEntry 24}



     acKpiSbcCallStatsCurrentSrdNoAnswerCallsOutTotal OBJECT-TYPE
       SYNTAX Counter64
       MAX-ACCESS read-only
       STATUS current
       DESCRIPTION
           "Total number of outbound calls closed due to no answer from
callee.
AC INI-Param: N/A"
       ::= {acKpiSbcCallStatsCurrentSrdEntry 25}



     acKpiSbcCallStatsCurrentSrdNoResourcesCallsInTotal OBJECT-TYPE
       SYNTAX Counter64
       MAX-ACCESS read-only
       STATUS current
       DESCRIPTION
           "Total number of inbound calls closed due to lack of internal
resources.
AC INI-Param: N/A"
       ::= {acKpiSbcCallStatsCurrentSrdEntry 26}



     acKpiSbcCallStatsCurrentSrdNoResourcesCallsOutTotal OBJECT-TYPE
       SYNTAX Counter64
       MAX-ACCESS read-only
       STATUS current
       DESCRIPTION
           "Total number of outbound calls closed due to lack of internal
resource.
AC INI-Param: N/A"
       ::= {acKpiSbcCallStatsCurrentSrdEntry 27}



     acKpiSbcCallStatsCurrentSrdMediaMismatchCallsInTotal OBJECT-TYPE
       SYNTAX Counter64
       MAX-ACCESS read-only
       STATUS current
       DESCRIPTION
           "Total number of inbound calls closed due to media mismatch.
AC INI-Param: N/A"
       ::= {acKpiSbcCallStatsCurrentSrdEntry 28}



     acKpiSbcCallStatsCurrentSrdMediaMismatchCallsOutTotal OBJECT-TYPE
       SYNTAX Counter64
       MAX-ACCESS read-only
       STATUS current
       DESCRIPTION
           "Total number of outbound calls closed due to media mismatch.
AC INI-Param: N/A"
       ::= {acKpiSbcCallStatsCurrentSrdEntry 29}



     acKpiSbcCallStatsCurrentSrdAdmissionFailedCallsInTotal OBJECT-TYPE
       SYNTAX Counter64
       MAX-ACCESS read-only
       STATUS current
       DESCRIPTION
           "Total number of inbound calls closed due to admission control
(CAC).
AC INI-Param: N/A"
       ::= {acKpiSbcCallStatsCurrentSrdEntry 30}



     acKpiSbcCallStatsCurrentSrdAdmissionFailedCallsOutTotal OBJECT-TYPE
       SYNTAX Counter64
       MAX-ACCESS read-only
       STATUS current
       DESCRIPTION
           "Total number of outbound calls closed due to admission control
(CAC).
AC INI-Param: N/A"
       ::= {acKpiSbcCallStatsCurrentSrdEntry 31}



     acKpiSbcCallStatsCurrentSrdNoRouteCallsInTotal OBJECT-TYPE
       SYNTAX Counter64
       MAX-ACCESS read-only
       STATUS current
       DESCRIPTION
           "Total number of inbound calls closed due to routing failure.
AC INI-Param: N/A"
       ::= {acKpiSbcCallStatsCurrentSrdEntry 32}



     acKpiSbcCallStatsCurrentSrdClassificationFailedCallsInTotal OBJECT-TYPE
       SYNTAX Counter64
       MAX-ACCESS read-only
       STATUS current
       DESCRIPTION
           "Total number of inbound calls closed due to classification failure.
AC INI-Param: N/A"
       ::= {acKpiSbcCallStatsCurrentSrdEntry 33}



     acKpiSbcCallStatsCurrentSrdOtherReasonCallsInTotal OBJECT-TYPE
       SYNTAX Counter64
       MAX-ACCESS read-only
       STATUS current
       DESCRIPTION
           "Total number of inbound calls closed due to other reasons.
AC INI-Param: N/A"
       ::= {acKpiSbcCallStatsCurrentSrdEntry 34}



     acKpiSbcCallStatsCurrentSrdOtherReasonCallsOutTotal OBJECT-TYPE
       SYNTAX Counter64
       MAX-ACCESS read-only
       STATUS current
       DESCRIPTION
           "Total number of outbound calls closed due to other reasons.
AC INI-Param: N/A"
       ::= {acKpiSbcCallStatsCurrentSrdEntry 35}



     acKpiSbcCallStatsCurrentSrdAbnormalTerminatedCallsInTotal OBJECT-TYPE
       SYNTAX Counter64
       MAX-ACCESS read-only
       STATUS current
       DESCRIPTION
           "Total number of abnormally terminated inbound calls (after connect).
AC INI-Param: N/A"
       ::= {acKpiSbcCallStatsCurrentSrdEntry 36}



     acKpiSbcCallStatsCurrentSrdAbnormalTerminatedCallsOutTotal OBJECT-TYPE
       SYNTAX Counter64
       MAX-ACCESS read-only
       STATUS current
       DESCRIPTION
           "Total number of abnormally terminated outbound calls (after
connect).
AC INI-Param: N/A"
       ::= {acKpiSbcCallStatsCurrentSrdEntry 37}



     acKpiSbcCallStatsCurrentSrdPostDialDelay OBJECT-TYPE
       SYNTAX Gauge32
       MAX-ACCESS read-only
       STATUS current
       DESCRIPTION
           "Number of seconds from INVITE to response (over 1 min sliding
window).
AC INI-Param: N/A"
       ::= {acKpiSbcCallStatsCurrentSrdEntry 38}



     acKpiSbcCallStatsCurrentSrdMinutesOfUsageTotal OBJECT-TYPE
       SYNTAX Gauge32
       MAX-ACCESS read-only
       STATUS current
       DESCRIPTION
           "Total sum in minutes of call duration.
AC INI-Param: N/A"
       ::= {acKpiSbcCallStatsCurrentSrdEntry 39}



     acKpiSbcCallStatsCurrentSrdShortCallsCounterTotal OBJECT-TYPE
       SYNTAX Counter64
       MAX-ACCESS read-only
       STATUS current
       DESCRIPTION
           "Total number of calls with duration shorter than pre-set threshold.
AC INI-Param: N/A"
       ::= {acKpiSbcCallStatsCurrentSrdEntry 40}



     acKpiSbcCallStatsCurrentSrdLongCallsCounterTotal OBJECT-TYPE
       SYNTAX Counter64
       MAX-ACCESS read-only
       STATUS current
       DESCRIPTION
           "Total number of calls with duration longer than pre-set threshold.
AC INI-Param: N/A"
       ::= {acKpiSbcCallStatsCurrentSrdEntry 41}



     acKpiSbcCallStatsCurrentSrdNotEstablishCallsOutTotal OBJECT-TYPE
       SYNTAX Counter64
       MAX-ACCESS read-only
       STATUS current
       DESCRIPTION
           "Total number of not established outbound calls (due to all reasons).
AC INI-Param: N/A"
       ::= {acKpiSbcCallStatsCurrentSrdEntry 42}



     acKpiSbcCallStatsCurrentSrdNotEstablishCallsInTotal OBJECT-TYPE
       SYNTAX Counter64
       MAX-ACCESS read-only
       STATUS current
       DESCRIPTION
           "Total number of not established inbound calls (due to all reasons).
AC INI-Param: N/A"
       ::= {acKpiSbcCallStatsCurrentSrdEntry 43}



     acKpiSbcCallStatsInterval OBJECT IDENTIFIER ::= {acKpiSbcCallStats 2}


     acKpiSbcCallStatsIntervalGlobal OBJECT IDENTIFIER ::= {acKpiSbcCallStatsInterval 1}


     -- ****************************************
     -- acKpiSbcCallStatsIntervalGlobal table declaration
     -- ****************************************
     acKpiSbcCallStatsIntervalGlobalTable OBJECT-TYPE
       SYNTAX SEQUENCE OF AcKpiSbcCallStatsIntervalGlobalEntry
       MAX-ACCESS not-accessible
       STATUS current
       DESCRIPTION
           ""
       ::= {acKpiSbcCallStatsIntervalGlobal 1}



     -- ****************************************
     -- acKpiSbcCallStatsIntervalGlobal table entry
     -- ****************************************
     acKpiSbcCallStatsIntervalGlobalEntry OBJECT-TYPE
       SYNTAX AcKpiSbcCallStatsIntervalGlobalEntry
       MAX-ACCESS not-accessible
       STATUS current
       DESCRIPTION
           ""
       INDEX {acKpiSbcCallStatsIntervalGlobalInterval}
       ::= {acKpiSbcCallStatsIntervalGlobalTable 1}



     -- ****************************************
     -- acKpiSbcCallStatsIntervalGlobal TABLE
     -- ****************************************
     AcKpiSbcCallStatsIntervalGlobalEntry ::= SEQUENCE {
       acKpiSbcCallStatsIntervalGlobalInterval         Unsigned32,
       acKpiSbcCallStatsIntervalGlobalAverageCallDurationAvg 
                                                       Gauge32,
       acKpiSbcCallStatsIntervalGlobalActiveCallsInAvg Gauge32,
       acKpiSbcCallStatsIntervalGlobalActiveCallsInMax Gauge32,
       acKpiSbcCallStatsIntervalGlobalActiveCallsOutAvg 
                                                       Gauge32,
       acKpiSbcCallStatsIntervalGlobalActiveCallsOutMax 
                                                       Gauge32,
       acKpiSbcCallStatsIntervalGlobalAttemptedCallsIn Counter64,
       acKpiSbcCallStatsIntervalGlobalAttemptedCallsOut 
                                                       Counter64,
       acKpiSbcCallStatsIntervalGlobalAttemptedCallsRateInAvg 
                                                       Gauge32,
       acKpiSbcCallStatsIntervalGlobalAttemptedCallsRateInMax 
                                                       Gauge32,
       acKpiSbcCallStatsIntervalGlobalAttemptedCallsRateOutAvg 
                                                       Gauge32,
       acKpiSbcCallStatsIntervalGlobalAttemptedCallsRateOutMax 
                                                       Gauge32,
       acKpiSbcCallStatsIntervalGlobalEstablishedCallsIn 
                                                       Counter64,
       acKpiSbcCallStatsIntervalGlobalEstablishedCallsOut 
                                                       Counter64,
       acKpiSbcCallStatsIntervalGlobalEstablishedCallsRateInAvg 
                                                       Gauge32,
       acKpiSbcCallStatsIntervalGlobalEstablishedCallsRateInMax 
                                                       Gauge32,
       acKpiSbcCallStatsIntervalGlobalEstablishedCallsRateOutAvg 
                                                       Gauge32,
       acKpiSbcCallStatsIntervalGlobalEstablishedCallsRateOutMax 
                                                       Gauge32,
       acKpiSbcCallStatsIntervalGlobalAnswerSeizureRatioAvg 
                                                       Gauge32,
       acKpiSbcCallStatsIntervalGlobalNetworkEffectivenessRatioAvg 
                                                       Gauge32,
       acKpiSbcCallStatsIntervalGlobalForwardedCallsIn Counter64,
       acKpiSbcCallStatsIntervalGlobalForwardedCallsOut 
                                                       Counter64,
       acKpiSbcCallStatsIntervalGlobalMediaBrokenConnectionCalls 
                                                       Counter64,
       acKpiSbcCallStatsIntervalGlobalNotEstablishSuccessCallsIn 
                                                       Counter64,
       acKpiSbcCallStatsIntervalGlobalNotEstablishSuccessCallsOut 
                                                       Counter64,
       acKpiSbcCallStatsIntervalGlobalNotEstablishFailedCallsIn 
                                                       Counter64,
       acKpiSbcCallStatsIntervalGlobalNotEstablishFailedCallsOut 
                                                       Counter64,
       acKpiSbcCallStatsIntervalGlobalBusyCallsIn      Counter64,
       acKpiSbcCallStatsIntervalGlobalBusyCallsOut     Counter64,
       acKpiSbcCallStatsIntervalGlobalNoAnswerCallsIn  Counter64,
       acKpiSbcCallStatsIntervalGlobalNoAnswerCallsOut Counter64,
       acKpiSbcCallStatsIntervalGlobalNoResourcesCallsIn 
                                                       Counter64,
       acKpiSbcCallStatsIntervalGlobalNoResourcesCallsOut 
                                                       Counter64,
       acKpiSbcCallStatsIntervalGlobalMediaMismatchCallsIn 
                                                       Counter64,
       acKpiSbcCallStatsIntervalGlobalMediaMismatchCallsOut 
                                                       Counter64,
       acKpiSbcCallStatsIntervalGlobalAdmissionFailedCallsIn 
                                                       Counter64,
       acKpiSbcCallStatsIntervalGlobalAdmissionFailedCallsOut 
                                                       Counter64,
       acKpiSbcCallStatsIntervalGlobalNoRouteCallsIn   Counter64,
       acKpiSbcCallStatsIntervalGlobalClassificationFailedCallsIn 
                                                       Counter64,
       acKpiSbcCallStatsIntervalGlobalOtherReasonCallsIn 
                                                       Counter64,
       acKpiSbcCallStatsIntervalGlobalOtherReasonCallsOut 
                                                       Counter64,
       acKpiSbcCallStatsIntervalGlobalAbnormalTerminatedCallsIn 
                                                       Counter64,
       acKpiSbcCallStatsIntervalGlobalAbnormalTerminatedCallsOut 
                                                       Counter64,
       acKpiSbcCallStatsIntervalGlobalPostDialDelayAvg Gauge32,
       acKpiSbcCallStatsIntervalGlobalPostDialDelayMax Gauge32,
       acKpiSbcCallStatsIntervalGlobalPostDialDelayMin Gauge32,
       acKpiSbcCallStatsIntervalGlobalMinutesOfUsage   Counter64,
       acKpiSbcCallStatsIntervalGlobalShortCallsCounter 
                                                       Counter64,
       acKpiSbcCallStatsIntervalGlobalLongCallsCounter Counter64,
       acKpiSbcCallStatsIntervalGlobalActiveSessionsMax 
                                                       Gauge32,
       acKpiSbcCallStatsIntervalGlobalActiveSessionsAvg 
                                                       Gauge32,
       acKpiSbcCallStatsIntervalGlobalNotEstablishCallsOut 
                                                       Counter64,
       acKpiSbcCallStatsIntervalGlobalNotEstablishCallsIn 
                                                       Counter64
     }



     acKpiSbcCallStatsIntervalGlobalInterval OBJECT-TYPE
       SYNTAX Unsigned32 (1..200)
       MAX-ACCESS not-accessible
       STATUS current
       DESCRIPTION
           "
AC INI-Param: N/A"
       ::= {acKpiSbcCallStatsIntervalGlobalEntry 1}



     acKpiSbcCallStatsIntervalGlobalAverageCallDurationAvg OBJECT-TYPE
       SYNTAX Gauge32
       MAX-ACCESS read-only
       STATUS current
       DESCRIPTION
           "Average call duration (ACD, seconds).
AC INI-Param: N/A"
       ::= {acKpiSbcCallStatsIntervalGlobalEntry 2}



     acKpiSbcCallStatsIntervalGlobalActiveCallsInAvg OBJECT-TYPE
       SYNTAX Gauge32
       MAX-ACCESS read-only
       STATUS current
       DESCRIPTION
           "Average number of active inbound calls (INVITE dialogs in all
states).
AC INI-Param: N/A"
       ::= {acKpiSbcCallStatsIntervalGlobalEntry 3}



     acKpiSbcCallStatsIntervalGlobalActiveCallsInMax OBJECT-TYPE
       SYNTAX Gauge32
       MAX-ACCESS read-only
       STATUS current
       DESCRIPTION
           "Maximum number of active inbound calls (INVITE dialogs in all
states).
AC INI-Param: N/A"
       ::= {acKpiSbcCallStatsIntervalGlobalEntry 4}



     acKpiSbcCallStatsIntervalGlobalActiveCallsOutAvg OBJECT-TYPE
       SYNTAX Gauge32
       MAX-ACCESS read-only
       STATUS current
       DESCRIPTION
           "Average number of active outbound calls (INVITE dialogs in all
states).
AC INI-Param: N/A"
       ::= {acKpiSbcCallStatsIntervalGlobalEntry 5}



     acKpiSbcCallStatsIntervalGlobalActiveCallsOutMax OBJECT-TYPE
       SYNTAX Gauge32
       MAX-ACCESS read-only
       STATUS current
       DESCRIPTION
           "Maximum number of active outbound calls (INVITE dialogs in all
states).
AC INI-Param: N/A"
       ::= {acKpiSbcCallStatsIntervalGlobalEntry 6}



     acKpiSbcCallStatsIntervalGlobalAttemptedCallsIn OBJECT-TYPE
       SYNTAX Counter64
       MAX-ACCESS read-only
       STATUS current
       DESCRIPTION
           "Number of attempted inbound calls (INVITE dialogs).
AC INI-Param: N/A"
       ::= {acKpiSbcCallStatsIntervalGlobalEntry 7}



     acKpiSbcCallStatsIntervalGlobalAttemptedCallsOut OBJECT-TYPE
       SYNTAX Counter64
       MAX-ACCESS read-only
       STATUS current
       DESCRIPTION
           "Number of attempted outbound calls (INVITE dialogs).
AC INI-Param: N/A"
       ::= {acKpiSbcCallStatsIntervalGlobalEntry 8}



     acKpiSbcCallStatsIntervalGlobalAttemptedCallsRateInAvg OBJECT-TYPE
       SYNTAX Gauge32
       MAX-ACCESS read-only
       STATUS current
       DESCRIPTION
           "Average rate of attempted inbound calls (call attempts per second).
AC INI-Param: N/A"
       ::= {acKpiSbcCallStatsIntervalGlobalEntry 9}



     acKpiSbcCallStatsIntervalGlobalAttemptedCallsRateInMax OBJECT-TYPE
       SYNTAX Gauge32
       MAX-ACCESS read-only
       STATUS current
       DESCRIPTION
           "Maximum rate of attempted inbound calls (call attempts per second).
AC INI-Param: N/A"
       ::= {acKpiSbcCallStatsIntervalGlobalEntry 10}



     acKpiSbcCallStatsIntervalGlobalAttemptedCallsRateOutAvg OBJECT-TYPE
       SYNTAX Gauge32
       MAX-ACCESS read-only
       STATUS current
       DESCRIPTION
           "Average rate of attempted outbound calls (call attempts per
second).
AC INI-Param: N/A"
       ::= {acKpiSbcCallStatsIntervalGlobalEntry 11}



     acKpiSbcCallStatsIntervalGlobalAttemptedCallsRateOutMax OBJECT-TYPE
       SYNTAX Gauge32
       MAX-ACCESS read-only
       STATUS current
       DESCRIPTION
           "Maximum rate of attempted outbound calls (call attempts per
second).
AC INI-Param: N/A"
       ::= {acKpiSbcCallStatsIntervalGlobalEntry 12}



     acKpiSbcCallStatsIntervalGlobalEstablishedCallsIn OBJECT-TYPE
       SYNTAX Counter64
       MAX-ACCESS read-only
       STATUS current
       DESCRIPTION
           "Number of established inbound calls (INVITE dialogs).
AC INI-Param: N/A"
       ::= {acKpiSbcCallStatsIntervalGlobalEntry 13}



     acKpiSbcCallStatsIntervalGlobalEstablishedCallsOut OBJECT-TYPE
       SYNTAX Counter64
       MAX-ACCESS read-only
       STATUS current
       DESCRIPTION
           "Number of established outbound calls (INVITE dialogs).
AC INI-Param: N/A"
       ::= {acKpiSbcCallStatsIntervalGlobalEntry 14}



     acKpiSbcCallStatsIntervalGlobalEstablishedCallsRateInAvg OBJECT-TYPE
       SYNTAX Gauge32
       MAX-ACCESS read-only
       STATUS current
       DESCRIPTION
           "Average rate of established inbound calls (call establish per
second).
AC INI-Param: N/A"
       ::= {acKpiSbcCallStatsIntervalGlobalEntry 15}



     acKpiSbcCallStatsIntervalGlobalEstablishedCallsRateInMax OBJECT-TYPE
       SYNTAX Gauge32
       MAX-ACCESS read-only
       STATUS current
       DESCRIPTION
           "Maximum rate of established inbound calls (call establish per
second).
AC INI-Param: N/A"
       ::= {acKpiSbcCallStatsIntervalGlobalEntry 16}



     acKpiSbcCallStatsIntervalGlobalEstablishedCallsRateOutAvg OBJECT-TYPE
       SYNTAX Gauge32
       MAX-ACCESS read-only
       STATUS current
       DESCRIPTION
           "Average rate of established outbound calls (call establish per
second).
AC INI-Param: N/A"
       ::= {acKpiSbcCallStatsIntervalGlobalEntry 17}



     acKpiSbcCallStatsIntervalGlobalEstablishedCallsRateOutMax OBJECT-TYPE
       SYNTAX Gauge32
       MAX-ACCESS read-only
       STATUS current
       DESCRIPTION
           "Maximum rate of established outbound calls (call establish per
second).
AC INI-Param: N/A"
       ::= {acKpiSbcCallStatsIntervalGlobalEntry 18}



     acKpiSbcCallStatsIntervalGlobalAnswerSeizureRatioAvg OBJECT-TYPE
       SYNTAX Gauge32
       MAX-ACCESS read-only
       STATUS current
       DESCRIPTION
           "Average answer/seizure ratio (ASR, %).
AC INI-Param: N/A"
       ::= {acKpiSbcCallStatsIntervalGlobalEntry 19}



     acKpiSbcCallStatsIntervalGlobalNetworkEffectivenessRatioAvg OBJECT-TYPE
       SYNTAX Gauge32
       MAX-ACCESS read-only
       STATUS current
       DESCRIPTION
           "Average network effectiveness ratio (NER, %).
AC INI-Param: N/A"
       ::= {acKpiSbcCallStatsIntervalGlobalEntry 20}



     acKpiSbcCallStatsIntervalGlobalForwardedCallsIn OBJECT-TYPE
       SYNTAX Counter64
       MAX-ACCESS read-only
       STATUS current
       DESCRIPTION
           "Number of forwarded inbound calls (INVITE dialogs).
AC INI-Param: N/A"
       ::= {acKpiSbcCallStatsIntervalGlobalEntry 21}



     acKpiSbcCallStatsIntervalGlobalForwardedCallsOut OBJECT-TYPE
       SYNTAX Counter64
       MAX-ACCESS read-only
       STATUS current
       DESCRIPTION
           "Number of forwarded outbound calls (INVITE dialogs).
AC INI-Param: N/A"
       ::= {acKpiSbcCallStatsIntervalGlobalEntry 22}



     acKpiSbcCallStatsIntervalGlobalMediaBrokenConnectionCalls OBJECT-TYPE
       SYNTAX Counter64
       MAX-ACCESS read-only
       STATUS current
       DESCRIPTION
           "Number of calls that failed due to broken connection.
AC INI-Param: N/A"
       ::= {acKpiSbcCallStatsIntervalGlobalEntry 23}



     acKpiSbcCallStatsIntervalGlobalNotEstablishSuccessCallsIn OBJECT-TYPE
       SYNTAX Counter64
       MAX-ACCESS read-only
       STATUS current
       DESCRIPTION
           "Number of not established inbound calls configured as success.
AC INI-Param: N/A"
       ::= {acKpiSbcCallStatsIntervalGlobalEntry 24}



     acKpiSbcCallStatsIntervalGlobalNotEstablishSuccessCallsOut OBJECT-TYPE
       SYNTAX Counter64
       MAX-ACCESS read-only
       STATUS current
       DESCRIPTION
           "Number of not established outbound calls configured as success.
AC INI-Param: N/A"
       ::= {acKpiSbcCallStatsIntervalGlobalEntry 25}



     acKpiSbcCallStatsIntervalGlobalNotEstablishFailedCallsIn OBJECT-TYPE
       SYNTAX Counter64
       MAX-ACCESS read-only
       STATUS current
       DESCRIPTION
           "Number of not established inbound calls configured as failed.
AC INI-Param: N/A"
       ::= {acKpiSbcCallStatsIntervalGlobalEntry 26}



     acKpiSbcCallStatsIntervalGlobalNotEstablishFailedCallsOut OBJECT-TYPE
       SYNTAX Counter64
       MAX-ACCESS read-only
       STATUS current
       DESCRIPTION
           "Number of not established outbound calls configured as failed.
AC INI-Param: N/A"
       ::= {acKpiSbcCallStatsIntervalGlobalEntry 27}



     acKpiSbcCallStatsIntervalGlobalBusyCallsIn OBJECT-TYPE
       SYNTAX Counter64
       MAX-ACCESS read-only
       STATUS current
       DESCRIPTION
           "Number of inbound calls closed due to callee being busy.
AC INI-Param: N/A"
       ::= {acKpiSbcCallStatsIntervalGlobalEntry 28}



     acKpiSbcCallStatsIntervalGlobalBusyCallsOut OBJECT-TYPE
       SYNTAX Counter64
       MAX-ACCESS read-only
       STATUS current
       DESCRIPTION
           "Number of outbound calls closed due to callee being busy.
AC INI-Param: N/A"
       ::= {acKpiSbcCallStatsIntervalGlobalEntry 29}



     acKpiSbcCallStatsIntervalGlobalNoAnswerCallsIn OBJECT-TYPE
       SYNTAX Counter64
       MAX-ACCESS read-only
       STATUS current
       DESCRIPTION
           "Number of inbound calls closed due to no answer from callee.
AC INI-Param: N/A"
       ::= {acKpiSbcCallStatsIntervalGlobalEntry 30}



     acKpiSbcCallStatsIntervalGlobalNoAnswerCallsOut OBJECT-TYPE
       SYNTAX Counter64
       MAX-ACCESS read-only
       STATUS current
       DESCRIPTION
           "Number of outbound calls closed due to no answer from callee.
AC INI-Param: N/A"
       ::= {acKpiSbcCallStatsIntervalGlobalEntry 31}



     acKpiSbcCallStatsIntervalGlobalNoResourcesCallsIn OBJECT-TYPE
       SYNTAX Counter64
       MAX-ACCESS read-only
       STATUS current
       DESCRIPTION
           "Number of inbound calls closed due to lack of internal resources.
AC INI-Param: N/A"
       ::= {acKpiSbcCallStatsIntervalGlobalEntry 32}



     acKpiSbcCallStatsIntervalGlobalNoResourcesCallsOut OBJECT-TYPE
       SYNTAX Counter64
       MAX-ACCESS read-only
       STATUS current
       DESCRIPTION
           "Number of outbound calls closed due to lack of internal resources.
AC INI-Param: N/A"
       ::= {acKpiSbcCallStatsIntervalGlobalEntry 33}



     acKpiSbcCallStatsIntervalGlobalMediaMismatchCallsIn OBJECT-TYPE
       SYNTAX Counter64
       MAX-ACCESS read-only
       STATUS current
       DESCRIPTION
           "Number of inbound calls closed due to media mismatch.
AC INI-Param: N/A"
       ::= {acKpiSbcCallStatsIntervalGlobalEntry 34}



     acKpiSbcCallStatsIntervalGlobalMediaMismatchCallsOut OBJECT-TYPE
       SYNTAX Counter64
       MAX-ACCESS read-only
       STATUS current
       DESCRIPTION
           "Number of outbound calls closed due to media mismatch.
AC INI-Param: N/A"
       ::= {acKpiSbcCallStatsIntervalGlobalEntry 35}



     acKpiSbcCallStatsIntervalGlobalAdmissionFailedCallsIn OBJECT-TYPE
       SYNTAX Counter64
       MAX-ACCESS read-only
       STATUS current
       DESCRIPTION
           "Number of inbound calls closed due to admission control (CAC).
AC INI-Param: N/A"
       ::= {acKpiSbcCallStatsIntervalGlobalEntry 36}



     acKpiSbcCallStatsIntervalGlobalAdmissionFailedCallsOut OBJECT-TYPE
       SYNTAX Counter64
       MAX-ACCESS read-only
       STATUS current
       DESCRIPTION
           "Number of outbound calls closed due to admission control (CAC).
AC INI-Param: N/A"
       ::= {acKpiSbcCallStatsIntervalGlobalEntry 37}



     acKpiSbcCallStatsIntervalGlobalNoRouteCallsIn OBJECT-TYPE
       SYNTAX Counter64
       MAX-ACCESS read-only
       STATUS current
       DESCRIPTION
           "Number of inbound calls closed due to routing failure.
AC INI-Param: N/A"
       ::= {acKpiSbcCallStatsIntervalGlobalEntry 38}



     acKpiSbcCallStatsIntervalGlobalClassificationFailedCallsIn OBJECT-TYPE
       SYNTAX Counter64
       MAX-ACCESS read-only
       STATUS current
       DESCRIPTION
           "Number of inbound calls closed due to classification failure.
AC INI-Param: N/A"
       ::= {acKpiSbcCallStatsIntervalGlobalEntry 39}



     acKpiSbcCallStatsIntervalGlobalOtherReasonCallsIn OBJECT-TYPE
       SYNTAX Counter64
       MAX-ACCESS read-only
       STATUS current
       DESCRIPTION
           "Number of inbound calls closed due to other reasons.
AC INI-Param: N/A"
       ::= {acKpiSbcCallStatsIntervalGlobalEntry 40}



     acKpiSbcCallStatsIntervalGlobalOtherReasonCallsOut OBJECT-TYPE
       SYNTAX Counter64
       MAX-ACCESS read-only
       STATUS current
       DESCRIPTION
           "Number of outbound calls closed due to other reasons.
AC INI-Param: N/A"
       ::= {acKpiSbcCallStatsIntervalGlobalEntry 41}



     acKpiSbcCallStatsIntervalGlobalAbnormalTerminatedCallsIn OBJECT-TYPE
       SYNTAX Counter64
       MAX-ACCESS read-only
       STATUS current
       DESCRIPTION
           "Number of abnormally terminated inbound calls (after connect).
AC INI-Param: N/A"
       ::= {acKpiSbcCallStatsIntervalGlobalEntry 42}



     acKpiSbcCallStatsIntervalGlobalAbnormalTerminatedCallsOut OBJECT-TYPE
       SYNTAX Counter64
       MAX-ACCESS read-only
       STATUS current
       DESCRIPTION
           "Number of abnormally terminated outbound calls (after connect).
AC INI-Param: N/A"
       ::= {acKpiSbcCallStatsIntervalGlobalEntry 43}



     acKpiSbcCallStatsIntervalGlobalPostDialDelayAvg OBJECT-TYPE
       SYNTAX Gauge32
       MAX-ACCESS read-only
       STATUS current
       DESCRIPTION
           "Average number of seconds from INVITE to response.
AC INI-Param: N/A"
       ::= {acKpiSbcCallStatsIntervalGlobalEntry 44}



     acKpiSbcCallStatsIntervalGlobalPostDialDelayMax OBJECT-TYPE
       SYNTAX Gauge32
       MAX-ACCESS read-only
       STATUS current
       DESCRIPTION
           "Maximum number of seconds from INVITE to response.
AC INI-Param: N/A"
       ::= {acKpiSbcCallStatsIntervalGlobalEntry 45}



     acKpiSbcCallStatsIntervalGlobalPostDialDelayMin OBJECT-TYPE
       SYNTAX Gauge32
       MAX-ACCESS read-only
       STATUS current
       DESCRIPTION
           "Minimum number of seconds from INVITE to response.
AC INI-Param: N/A"
       ::= {acKpiSbcCallStatsIntervalGlobalEntry 46}



     acKpiSbcCallStatsIntervalGlobalMinutesOfUsage OBJECT-TYPE
       SYNTAX Counter64
       MAX-ACCESS read-only
       STATUS current
       DESCRIPTION
           "Sum in minutes of call duration.
AC INI-Param: N/A"
       ::= {acKpiSbcCallStatsIntervalGlobalEntry 47}



     acKpiSbcCallStatsIntervalGlobalShortCallsCounter OBJECT-TYPE
       SYNTAX Counter64
       MAX-ACCESS read-only
       STATUS current
       DESCRIPTION
           "Number of calls with duration shorter than pre-set threshold.
AC INI-Param: N/A"
       ::= {acKpiSbcCallStatsIntervalGlobalEntry 48}



     acKpiSbcCallStatsIntervalGlobalLongCallsCounter OBJECT-TYPE
       SYNTAX Counter64
       MAX-ACCESS read-only
       STATUS current
       DESCRIPTION
           "Number of calls with duration longer than pre-set threshold.
AC INI-Param: N/A"
       ::= {acKpiSbcCallStatsIntervalGlobalEntry 49}



     acKpiSbcCallStatsIntervalGlobalActiveSessionsMax OBJECT-TYPE
       SYNTAX Gauge32
       MAX-ACCESS read-only
       STATUS current
       DESCRIPTION
           "Maximum number of active SBC sessions.
AC INI-Param: N/A"
       ::= {acKpiSbcCallStatsIntervalGlobalEntry 50}



     acKpiSbcCallStatsIntervalGlobalActiveSessionsAvg OBJECT-TYPE
       SYNTAX Gauge32
       MAX-ACCESS read-only
       STATUS current
       DESCRIPTION
           "Average number of active SBC sessions.
AC INI-Param: N/A"
       ::= {acKpiSbcCallStatsIntervalGlobalEntry 51}



     acKpiSbcCallStatsIntervalGlobalNotEstablishCallsOut OBJECT-TYPE
       SYNTAX Counter64
       MAX-ACCESS read-only
       STATUS current
       DESCRIPTION
           "Number of not established outbound calls (due to all reasons).
AC INI-Param: N/A"
       ::= {acKpiSbcCallStatsIntervalGlobalEntry 52}



     acKpiSbcCallStatsIntervalGlobalNotEstablishCallsIn OBJECT-TYPE
       SYNTAX Counter64
       MAX-ACCESS read-only
       STATUS current
       DESCRIPTION
           "Number of not established inbound calls (due to all reasons).
AC INI-Param: N/A"
       ::= {acKpiSbcCallStatsIntervalGlobalEntry 53}



     acKpiSbcCallStatsIntervalTables OBJECT IDENTIFIER ::= {acKpiSbcCallStatsInterval 2}


     -- ****************************************
     -- acKpiSbcCallStatsIntervalIpGroup table declaration
     -- ****************************************
     acKpiSbcCallStatsIntervalIpGroupTable OBJECT-TYPE
       SYNTAX SEQUENCE OF AcKpiSbcCallStatsIntervalIpGroupEntry
       MAX-ACCESS not-accessible
       STATUS current
       DESCRIPTION
           ""
       ::= {acKpiSbcCallStatsIntervalTables 1}



     -- ****************************************
     -- acKpiSbcCallStatsIntervalIpGroup table entry
     -- ****************************************
     acKpiSbcCallStatsIntervalIpGroupEntry OBJECT-TYPE
       SYNTAX AcKpiSbcCallStatsIntervalIpGroupEntry
       MAX-ACCESS not-accessible
       STATUS current
       DESCRIPTION
           ""
       INDEX {acKpiSbcCallStatsIntervalIpGroupIndex,acKpiSbcCallStatsIntervalIpGroupInterval}
       ::= {acKpiSbcCallStatsIntervalIpGroupTable 1}



     -- ****************************************
     -- acKpiSbcCallStatsIntervalIpGroup TABLE
     -- ****************************************
     AcKpiSbcCallStatsIntervalIpGroupEntry ::= SEQUENCE {
       acKpiSbcCallStatsIntervalIpGroupIndex           Unsigned32,
       acKpiSbcCallStatsIntervalIpGroupInterval        Unsigned32,
       acKpiSbcCallStatsIntervalIpGroupAverageCallDurationAvg 
                                                       Gauge32,
       acKpiSbcCallStatsIntervalIpGroupActiveCallsInAvg 
                                                       Gauge32,
       acKpiSbcCallStatsIntervalIpGroupActiveCallsInMax 
                                                       Gauge32,
       acKpiSbcCallStatsIntervalIpGroupActiveCallsOutAvg 
                                                       Gauge32,
       acKpiSbcCallStatsIntervalIpGroupActiveCallsOutMax 
                                                       Gauge32,
       acKpiSbcCallStatsIntervalIpGroupAttemptedCallsIn 
                                                       Counter64,
       acKpiSbcCallStatsIntervalIpGroupAttemptedCallsOut 
                                                       Counter64,
       acKpiSbcCallStatsIntervalIpGroupAttemptedCallsRateInAvg 
                                                       Gauge32,
       acKpiSbcCallStatsIntervalIpGroupAttemptedCallsRateInMax 
                                                       Gauge32,
       acKpiSbcCallStatsIntervalIpGroupAttemptedCallsRateOutAvg 
                                                       Gauge32,
       acKpiSbcCallStatsIntervalIpGroupAttemptedCallsRateOutMax 
                                                       Gauge32,
       acKpiSbcCallStatsIntervalIpGroupEstablishedCallsIn 
                                                       Counter64,
       acKpiSbcCallStatsIntervalIpGroupEstablishedCallsOut 
                                                       Counter64,
       acKpiSbcCallStatsIntervalIpGroupEstablishedCallsRateInAvg 
                                                       Gauge32,
       acKpiSbcCallStatsIntervalIpGroupEstablishedCallsRateInMax 
                                                       Gauge32,
       acKpiSbcCallStatsIntervalIpGroupEstablishedCallsRateOutAvg 
                                                       Gauge32,
       acKpiSbcCallStatsIntervalIpGroupEstablishedCallsRateOutMax 
                                                       Gauge32,
       acKpiSbcCallStatsIntervalIpGroupAnswerSeizureRatioAvg 
                                                       Gauge32,
       acKpiSbcCallStatsIntervalIpGroupNetworkEffectivenessRatioAvg 
                                                       Gauge32,
       acKpiSbcCallStatsIntervalIpGroupForwardedCallsIn 
                                                       Counter64,
       acKpiSbcCallStatsIntervalIpGroupForwardedCallsOut 
                                                       Counter64,
       acKpiSbcCallStatsIntervalIpGroupMediaBrokenConnectionCalls 
                                                       Counter64,
       acKpiSbcCallStatsIntervalIpGroupNotEstablishSuccessCallsIn 
                                                       Counter64,
       acKpiSbcCallStatsIntervalIpGroupNotEstablishSuccessCallsOut 
                                                       Counter64,
       acKpiSbcCallStatsIntervalIpGroupNotEstablishFailedCallsIn 
                                                       Counter64,
       acKpiSbcCallStatsIntervalIpGroupNotEstablishFailedCallsOut 
                                                       Counter64,
       acKpiSbcCallStatsIntervalIpGroupBusyCallsIn     Counter64,
       acKpiSbcCallStatsIntervalIpGroupBusyCallsOut    Counter64,
       acKpiSbcCallStatsIntervalIpGroupNoAnswerCallsIn Counter64,
       acKpiSbcCallStatsIntervalIpGroupNoAnswerCallsOut 
                                                       Counter64,
       acKpiSbcCallStatsIntervalIpGroupNoResourcesCallsIn 
                                                       Counter64,
       acKpiSbcCallStatsIntervalIpGroupNoResourcesCallsOut 
                                                       Counter64,
       acKpiSbcCallStatsIntervalIpGroupMediaMismatchCallsIn 
                                                       Counter64,
       acKpiSbcCallStatsIntervalIpGroupMediaMismatchCallsOut 
                                                       Counter64,
       acKpiSbcCallStatsIntervalIpGroupAdmissionFailedCallsIn 
                                                       Counter64,
       acKpiSbcCallStatsIntervalIpGroupAdmissionFailedCallsOut 
                                                       Counter64,
       acKpiSbcCallStatsIntervalIpGroupNoRouteCallsIn  Counter64,
       acKpiSbcCallStatsIntervalIpGroupOtherReasonCallsIn 
                                                       Counter64,
       acKpiSbcCallStatsIntervalIpGroupOtherReasonCallsOut 
                                                       Counter64,
       acKpiSbcCallStatsIntervalIpGroupAbnormalTerminatedCallsIn 
                                                       Counter64,
       acKpiSbcCallStatsIntervalIpGroupAbnormalTerminatedCallsOut 
                                                       Counter64,
       acKpiSbcCallStatsIntervalIpGroupPostDialDelayAvg 
                                                       Gauge32,
       acKpiSbcCallStatsIntervalIpGroupPostDialDelayMax 
                                                       Gauge32,
       acKpiSbcCallStatsIntervalIpGroupPostDialDelayMin 
                                                       Gauge32,
       acKpiSbcCallStatsIntervalIpGroupMinutesOfUsage  Counter64,
       acKpiSbcCallStatsIntervalIpGroupShortCallsCounter 
                                                       Counter64,
       acKpiSbcCallStatsIntervalIpGroupLongCallsCounter 
                                                       Counter64,
       acKpiSbcCallStatsIntervalIpGroupNotEstablishCallsIn 
                                                       Counter64,
       acKpiSbcCallStatsIntervalIpGroupNotEstablishCallsOut 
                                                       Counter64
     }



     acKpiSbcCallStatsIntervalIpGroupIndex OBJECT-TYPE
       SYNTAX Unsigned32 (0..32767)
       MAX-ACCESS not-accessible
       STATUS current
       DESCRIPTION
           "
AC INI-Param: N/A"
       ::= {acKpiSbcCallStatsIntervalIpGroupEntry 1}



     acKpiSbcCallStatsIntervalIpGroupInterval OBJECT-TYPE
       SYNTAX Unsigned32 (1..200)
       MAX-ACCESS not-accessible
       STATUS current
       DESCRIPTION
           "
AC INI-Param: N/A"
       ::= {acKpiSbcCallStatsIntervalIpGroupEntry 2}



     acKpiSbcCallStatsIntervalIpGroupAverageCallDurationAvg OBJECT-TYPE
       SYNTAX Gauge32
       MAX-ACCESS read-only
       STATUS current
       DESCRIPTION
           "Average call duration (ACD, seconds).
AC INI-Param: N/A"
       ::= {acKpiSbcCallStatsIntervalIpGroupEntry 3}



     acKpiSbcCallStatsIntervalIpGroupActiveCallsInAvg OBJECT-TYPE
       SYNTAX Gauge32
       MAX-ACCESS read-only
       STATUS current
       DESCRIPTION
           "Average number of active inbound calls (INVITE dialogs in all
states).
AC INI-Param: N/A"
       ::= {acKpiSbcCallStatsIntervalIpGroupEntry 4}



     acKpiSbcCallStatsIntervalIpGroupActiveCallsInMax OBJECT-TYPE
       SYNTAX Gauge32
       MAX-ACCESS read-only
       STATUS current
       DESCRIPTION
           "Maximum number of active inbound calls (INVITE dialogs in all
states).
AC INI-Param: N/A"
       ::= {acKpiSbcCallStatsIntervalIpGroupEntry 5}



     acKpiSbcCallStatsIntervalIpGroupActiveCallsOutAvg OBJECT-TYPE
       SYNTAX Gauge32
       MAX-ACCESS read-only
       STATUS current
       DESCRIPTION
           "Average number of active outbound calls (INVITE dialogs in all
states).
AC INI-Param: N/A"
       ::= {acKpiSbcCallStatsIntervalIpGroupEntry 6}



     acKpiSbcCallStatsIntervalIpGroupActiveCallsOutMax OBJECT-TYPE
       SYNTAX Gauge32
       MAX-ACCESS read-only
       STATUS current
       DESCRIPTION
           "Maximum number of active outbound calls (INVITE dialogs in all
states).
AC INI-Param: N/A"
       ::= {acKpiSbcCallStatsIntervalIpGroupEntry 7}



     acKpiSbcCallStatsIntervalIpGroupAttemptedCallsIn OBJECT-TYPE
       SYNTAX Counter64
       MAX-ACCESS read-only
       STATUS current
       DESCRIPTION
           "Number of attempted inbound calls (INVITE dialogs).
AC INI-Param: N/A"
       ::= {acKpiSbcCallStatsIntervalIpGroupEntry 8}



     acKpiSbcCallStatsIntervalIpGroupAttemptedCallsOut OBJECT-TYPE
       SYNTAX Counter64
       MAX-ACCESS read-only
       STATUS current
       DESCRIPTION
           "Number of attempted outbound calls (INVITE dialogs).
AC INI-Param: N/A"
       ::= {acKpiSbcCallStatsIntervalIpGroupEntry 9}



     acKpiSbcCallStatsIntervalIpGroupAttemptedCallsRateInAvg OBJECT-TYPE
       SYNTAX Gauge32
       MAX-ACCESS read-only
       STATUS current
       DESCRIPTION
           "Average rate of attempted inbound calls (call attempts per second).
AC INI-Param: N/A"
       ::= {acKpiSbcCallStatsIntervalIpGroupEntry 10}



     acKpiSbcCallStatsIntervalIpGroupAttemptedCallsRateInMax OBJECT-TYPE
       SYNTAX Gauge32
       MAX-ACCESS read-only
       STATUS current
       DESCRIPTION
           "Maximum rate of attempted inbound calls (call attempts per second).
AC INI-Param: N/A"
       ::= {acKpiSbcCallStatsIntervalIpGroupEntry 11}



     acKpiSbcCallStatsIntervalIpGroupAttemptedCallsRateOutAvg OBJECT-TYPE
       SYNTAX Gauge32
       MAX-ACCESS read-only
       STATUS current
       DESCRIPTION
           "Average rate of attempted outbound calls (call attempts per
second).
AC INI-Param: N/A"
       ::= {acKpiSbcCallStatsIntervalIpGroupEntry 12}



     acKpiSbcCallStatsIntervalIpGroupAttemptedCallsRateOutMax OBJECT-TYPE
       SYNTAX Gauge32
       MAX-ACCESS read-only
       STATUS current
       DESCRIPTION
           "Maximum rate of attempted outbound calls (call attempts per
second).
AC INI-Param: N/A"
       ::= {acKpiSbcCallStatsIntervalIpGroupEntry 13}



     acKpiSbcCallStatsIntervalIpGroupEstablishedCallsIn OBJECT-TYPE
       SYNTAX Counter64
       MAX-ACCESS read-only
       STATUS current
       DESCRIPTION
           "Number of established inbound calls (INVITE dialogs).
AC INI-Param: N/A"
       ::= {acKpiSbcCallStatsIntervalIpGroupEntry 14}



     acKpiSbcCallStatsIntervalIpGroupEstablishedCallsOut OBJECT-TYPE
       SYNTAX Counter64
       MAX-ACCESS read-only
       STATUS current
       DESCRIPTION
           "Number of established outbound calls (INVITE dialogs).
AC INI-Param: N/A"
       ::= {acKpiSbcCallStatsIntervalIpGroupEntry 15}



     acKpiSbcCallStatsIntervalIpGroupEstablishedCallsRateInAvg OBJECT-TYPE
       SYNTAX Gauge32
       MAX-ACCESS read-only
       STATUS current
       DESCRIPTION
           "Average rate of established inbound calls (call establish per
second).
AC INI-Param: N/A"
       ::= {acKpiSbcCallStatsIntervalIpGroupEntry 16}



     acKpiSbcCallStatsIntervalIpGroupEstablishedCallsRateInMax OBJECT-TYPE
       SYNTAX Gauge32
       MAX-ACCESS read-only
       STATUS current
       DESCRIPTION
           "Maximum rate of established inbound calls (call establish per
second).
AC INI-Param: N/A"
       ::= {acKpiSbcCallStatsIntervalIpGroupEntry 17}



     acKpiSbcCallStatsIntervalIpGroupEstablishedCallsRateOutAvg OBJECT-TYPE
       SYNTAX Gauge32
       MAX-ACCESS read-only
       STATUS current
       DESCRIPTION
           "Average rate of established outbound calls (call establish per
second).
AC INI-Param: N/A"
       ::= {acKpiSbcCallStatsIntervalIpGroupEntry 18}



     acKpiSbcCallStatsIntervalIpGroupEstablishedCallsRateOutMax OBJECT-TYPE
       SYNTAX Gauge32
       MAX-ACCESS read-only
       STATUS current
       DESCRIPTION
           "Maximum rate of established outbound calls (call establish per
second).
AC INI-Param: N/A"
       ::= {acKpiSbcCallStatsIntervalIpGroupEntry 19}



     acKpiSbcCallStatsIntervalIpGroupAnswerSeizureRatioAvg OBJECT-TYPE
       SYNTAX Gauge32
       MAX-ACCESS read-only
       STATUS current
       DESCRIPTION
           "Average answer/seizure ratio (ASR, %).
AC INI-Param: N/A"
       ::= {acKpiSbcCallStatsIntervalIpGroupEntry 20}



     acKpiSbcCallStatsIntervalIpGroupNetworkEffectivenessRatioAvg OBJECT-TYPE
       SYNTAX Gauge32
       MAX-ACCESS read-only
       STATUS current
       DESCRIPTION
           "Average network effectiveness ratio (NER, %).
AC INI-Param: N/A"
       ::= {acKpiSbcCallStatsIntervalIpGroupEntry 21}



     acKpiSbcCallStatsIntervalIpGroupForwardedCallsIn OBJECT-TYPE
       SYNTAX Counter64
       MAX-ACCESS read-only
       STATUS current
       DESCRIPTION
           "Number of forwarded inbound calls (INVITE dialogs).
AC INI-Param: N/A"
       ::= {acKpiSbcCallStatsIntervalIpGroupEntry 22}



     acKpiSbcCallStatsIntervalIpGroupForwardedCallsOut OBJECT-TYPE
       SYNTAX Counter64
       MAX-ACCESS read-only
       STATUS current
       DESCRIPTION
           "Number of forwarded outbound calls (INVITE dialogs).
AC INI-Param: N/A"
       ::= {acKpiSbcCallStatsIntervalIpGroupEntry 23}



     acKpiSbcCallStatsIntervalIpGroupMediaBrokenConnectionCalls OBJECT-TYPE
       SYNTAX Counter64
       MAX-ACCESS read-only
       STATUS current
       DESCRIPTION
           "Number of calls that failed due to broken connection.
AC INI-Param: N/A"
       ::= {acKpiSbcCallStatsIntervalIpGroupEntry 24}



     acKpiSbcCallStatsIntervalIpGroupNotEstablishSuccessCallsIn OBJECT-TYPE
       SYNTAX Counter64
       MAX-ACCESS read-only
       STATUS current
       DESCRIPTION
           "Number of not established inbound calls configured as success.
AC INI-Param: N/A"
       ::= {acKpiSbcCallStatsIntervalIpGroupEntry 25}



     acKpiSbcCallStatsIntervalIpGroupNotEstablishSuccessCallsOut OBJECT-TYPE
       SYNTAX Counter64
       MAX-ACCESS read-only
       STATUS current
       DESCRIPTION
           "Number of not established outbound calls configured as success.
AC INI-Param: N/A"
       ::= {acKpiSbcCallStatsIntervalIpGroupEntry 26}



     acKpiSbcCallStatsIntervalIpGroupNotEstablishFailedCallsIn OBJECT-TYPE
       SYNTAX Counter64
       MAX-ACCESS read-only
       STATUS current
       DESCRIPTION
           "Number of not established inbound calls configured as failed.
AC INI-Param: N/A"
       ::= {acKpiSbcCallStatsIntervalIpGroupEntry 27}



     acKpiSbcCallStatsIntervalIpGroupNotEstablishFailedCallsOut OBJECT-TYPE
       SYNTAX Counter64
       MAX-ACCESS read-only
       STATUS current
       DESCRIPTION
           "Number of not established outbound calls configured as failed.
AC INI-Param: N/A"
       ::= {acKpiSbcCallStatsIntervalIpGroupEntry 28}



     acKpiSbcCallStatsIntervalIpGroupBusyCallsIn OBJECT-TYPE
       SYNTAX Counter64
       MAX-ACCESS read-only
       STATUS current
       DESCRIPTION
           "Number of inbound calls closed due to callee being busy.
AC INI-Param: N/A"
       ::= {acKpiSbcCallStatsIntervalIpGroupEntry 29}



     acKpiSbcCallStatsIntervalIpGroupBusyCallsOut OBJECT-TYPE
       SYNTAX Counter64
       MAX-ACCESS read-only
       STATUS current
       DESCRIPTION
           "Number of outbound calls closed due to callee being busy.
AC INI-Param: N/A"
       ::= {acKpiSbcCallStatsIntervalIpGroupEntry 30}



     acKpiSbcCallStatsIntervalIpGroupNoAnswerCallsIn OBJECT-TYPE
       SYNTAX Counter64
       MAX-ACCESS read-only
       STATUS current
       DESCRIPTION
           "Number of inbound calls closed due to no answer from callee.
AC INI-Param: N/A"
       ::= {acKpiSbcCallStatsIntervalIpGroupEntry 31}



     acKpiSbcCallStatsIntervalIpGroupNoAnswerCallsOut OBJECT-TYPE
       SYNTAX Counter64
       MAX-ACCESS read-only
       STATUS current
       DESCRIPTION
           "Number of outbound calls closed due to no answer from callee.
AC INI-Param: N/A"
       ::= {acKpiSbcCallStatsIntervalIpGroupEntry 32}



     acKpiSbcCallStatsIntervalIpGroupNoResourcesCallsIn OBJECT-TYPE
       SYNTAX Counter64
       MAX-ACCESS read-only
       STATUS current
       DESCRIPTION
           "Number of inbound calls closed due to lack of internal resources.
AC INI-Param: N/A"
       ::= {acKpiSbcCallStatsIntervalIpGroupEntry 33}



     acKpiSbcCallStatsIntervalIpGroupNoResourcesCallsOut OBJECT-TYPE
       SYNTAX Counter64
       MAX-ACCESS read-only
       STATUS current
       DESCRIPTION
           "Number of outbound calls closed due to lack of internal resources.
AC INI-Param: N/A"
       ::= {acKpiSbcCallStatsIntervalIpGroupEntry 34}



     acKpiSbcCallStatsIntervalIpGroupMediaMismatchCallsIn OBJECT-TYPE
       SYNTAX Counter64
       MAX-ACCESS read-only
       STATUS current
       DESCRIPTION
           "Number of inbound calls closed due to media mismatch.
AC INI-Param: N/A"
       ::= {acKpiSbcCallStatsIntervalIpGroupEntry 35}



     acKpiSbcCallStatsIntervalIpGroupMediaMismatchCallsOut OBJECT-TYPE
       SYNTAX Counter64
       MAX-ACCESS read-only
       STATUS current
       DESCRIPTION
           "Number of outbound calls closed due to media mismatch.
AC INI-Param: N/A"
       ::= {acKpiSbcCallStatsIntervalIpGroupEntry 36}



     acKpiSbcCallStatsIntervalIpGroupAdmissionFailedCallsIn OBJECT-TYPE
       SYNTAX Counter64
       MAX-ACCESS read-only
       STATUS current
       DESCRIPTION
           "Number of inbound calls closed due to admission control (CAC).
AC INI-Param: N/A"
       ::= {acKpiSbcCallStatsIntervalIpGroupEntry 37}



     acKpiSbcCallStatsIntervalIpGroupAdmissionFailedCallsOut OBJECT-TYPE
       SYNTAX Counter64
       MAX-ACCESS read-only
       STATUS current
       DESCRIPTION
           "Number of outbound calls closed due to admission control (CAC).
AC INI-Param: N/A"
       ::= {acKpiSbcCallStatsIntervalIpGroupEntry 38}



     acKpiSbcCallStatsIntervalIpGroupNoRouteCallsIn OBJECT-TYPE
       SYNTAX Counter64
       MAX-ACCESS read-only
       STATUS current
       DESCRIPTION
           "Number of inbound calls closed due to routing failure.
AC INI-Param: N/A"
       ::= {acKpiSbcCallStatsIntervalIpGroupEntry 39}



     acKpiSbcCallStatsIntervalIpGroupOtherReasonCallsIn OBJECT-TYPE
       SYNTAX Counter64
       MAX-ACCESS read-only
       STATUS current
       DESCRIPTION
           "Number of inbound calls closed due to other reasons.
AC INI-Param: N/A"
       ::= {acKpiSbcCallStatsIntervalIpGroupEntry 40}



     acKpiSbcCallStatsIntervalIpGroupOtherReasonCallsOut OBJECT-TYPE
       SYNTAX Counter64
       MAX-ACCESS read-only
       STATUS current
       DESCRIPTION
           "Number of outbound calls closed due to other reasons.
AC INI-Param: N/A"
       ::= {acKpiSbcCallStatsIntervalIpGroupEntry 41}



     acKpiSbcCallStatsIntervalIpGroupAbnormalTerminatedCallsIn OBJECT-TYPE
       SYNTAX Counter64
       MAX-ACCESS read-only
       STATUS current
       DESCRIPTION
           "Number of abnormally terminated inbound calls (after connect).
AC INI-Param: N/A"
       ::= {acKpiSbcCallStatsIntervalIpGroupEntry 42}



     acKpiSbcCallStatsIntervalIpGroupAbnormalTerminatedCallsOut OBJECT-TYPE
       SYNTAX Counter64
       MAX-ACCESS read-only
       STATUS current
       DESCRIPTION
           "Number of abnormally terminated outbound calls (after connect).
AC INI-Param: N/A"
       ::= {acKpiSbcCallStatsIntervalIpGroupEntry 43}



     acKpiSbcCallStatsIntervalIpGroupPostDialDelayAvg OBJECT-TYPE
       SYNTAX Gauge32
       MAX-ACCESS read-only
       STATUS current
       DESCRIPTION
           "Average number of seconds from INVITE to response.
AC INI-Param: N/A"
       ::= {acKpiSbcCallStatsIntervalIpGroupEntry 44}



     acKpiSbcCallStatsIntervalIpGroupPostDialDelayMax OBJECT-TYPE
       SYNTAX Gauge32
       MAX-ACCESS read-only
       STATUS current
       DESCRIPTION
           "Maximum number of seconds from INVITE to response.
AC INI-Param: N/A"
       ::= {acKpiSbcCallStatsIntervalIpGroupEntry 45}



     acKpiSbcCallStatsIntervalIpGroupPostDialDelayMin OBJECT-TYPE
       SYNTAX Gauge32
       MAX-ACCESS read-only
       STATUS current
       DESCRIPTION
           "Minimum number of seconds from INVITE to response.
AC INI-Param: N/A"
       ::= {acKpiSbcCallStatsIntervalIpGroupEntry 46}



     acKpiSbcCallStatsIntervalIpGroupMinutesOfUsage OBJECT-TYPE
       SYNTAX Counter64
       MAX-ACCESS read-only
       STATUS current
       DESCRIPTION
           "Sum in minutes of call duration.
AC INI-Param: N/A"
       ::= {acKpiSbcCallStatsIntervalIpGroupEntry 47}



     acKpiSbcCallStatsIntervalIpGroupShortCallsCounter OBJECT-TYPE
       SYNTAX Counter64
       MAX-ACCESS read-only
       STATUS current
       DESCRIPTION
           "Number of calls with duration shorter than pre-set threshold.
AC INI-Param: N/A"
       ::= {acKpiSbcCallStatsIntervalIpGroupEntry 48}



     acKpiSbcCallStatsIntervalIpGroupLongCallsCounter OBJECT-TYPE
       SYNTAX Counter64
       MAX-ACCESS read-only
       STATUS current
       DESCRIPTION
           "Number of calls with duration longer than pre-set threshold.
AC INI-Param: N/A"
       ::= {acKpiSbcCallStatsIntervalIpGroupEntry 49}



     acKpiSbcCallStatsIntervalIpGroupNotEstablishCallsIn OBJECT-TYPE
       SYNTAX Counter64
       MAX-ACCESS read-only
       STATUS current
       DESCRIPTION
           "Number of not established inbound calls (due to all reasons).
AC INI-Param: N/A"
       ::= {acKpiSbcCallStatsIntervalIpGroupEntry 50}



     acKpiSbcCallStatsIntervalIpGroupNotEstablishCallsOut OBJECT-TYPE
       SYNTAX Counter64
       MAX-ACCESS read-only
       STATUS current
       DESCRIPTION
           "Number of not established outbound calls (due to all reasons).
AC INI-Param: N/A"
       ::= {acKpiSbcCallStatsIntervalIpGroupEntry 51}



     -- ****************************************
     -- acKpiSbcCallStatsIntervalSrd table declaration
     -- ****************************************
     acKpiSbcCallStatsIntervalSrdTable OBJECT-TYPE
       SYNTAX SEQUENCE OF AcKpiSbcCallStatsIntervalSrdEntry
       MAX-ACCESS not-accessible
       STATUS current
       DESCRIPTION
           ""
       ::= {acKpiSbcCallStatsIntervalTables 2}



     -- ****************************************
     -- acKpiSbcCallStatsIntervalSrd table entry
     -- ****************************************
     acKpiSbcCallStatsIntervalSrdEntry OBJECT-TYPE
       SYNTAX AcKpiSbcCallStatsIntervalSrdEntry
       MAX-ACCESS not-accessible
       STATUS current
       DESCRIPTION
           ""
       INDEX {acKpiSbcCallStatsIntervalSrdIndex,acKpiSbcCallStatsIntervalSrdInterval}
       ::= {acKpiSbcCallStatsIntervalSrdTable 1}



     -- ****************************************
     -- acKpiSbcCallStatsIntervalSrd TABLE
     -- ****************************************
     AcKpiSbcCallStatsIntervalSrdEntry ::= SEQUENCE {
       acKpiSbcCallStatsIntervalSrdIndex               Unsigned32,
       acKpiSbcCallStatsIntervalSrdInterval            Unsigned32,
       acKpiSbcCallStatsIntervalSrdAverageCallDurationAvg 
                                                       Gauge32,
       acKpiSbcCallStatsIntervalSrdActiveCallsInAvg    Gauge32,
       acKpiSbcCallStatsIntervalSrdActiveCallsInMax    Gauge32,
       acKpiSbcCallStatsIntervalSrdActiveCallsOutAvg   Gauge32,
       acKpiSbcCallStatsIntervalSrdActiveCallsOutMax   Gauge32,
       acKpiSbcCallStatsIntervalSrdAttemptedCallsIn    Counter64,
       acKpiSbcCallStatsIntervalSrdAttemptedCallsOut   Counter64,
       acKpiSbcCallStatsIntervalSrdAttemptedCallsRateInAvg 
                                                       Gauge32,
       acKpiSbcCallStatsIntervalSrdAttemptedCallsRateInMax 
                                                       Gauge32,
       acKpiSbcCallStatsIntervalSrdAttemptedCallsRateOutAvg 
                                                       Gauge32,
       acKpiSbcCallStatsIntervalSrdAttemptedCallsRateOutMax 
                                                       Gauge32,
       acKpiSbcCallStatsIntervalSrdEstablishedCallsIn  Counter64,
       acKpiSbcCallStatsIntervalSrdEstablishedCallsOut Counter64,
       acKpiSbcCallStatsIntervalSrdEstablishedCallsRateInAvg 
                                                       Gauge32,
       acKpiSbcCallStatsIntervalSrdEstablishedCallsRateInMax 
                                                       Gauge32,
       acKpiSbcCallStatsIntervalSrdEstablishedCallsRateOutAvg 
                                                       Gauge32,
       acKpiSbcCallStatsIntervalSrdEstablishedCallsRateOutMax 
                                                       Gauge32,
       acKpiSbcCallStatsIntervalSrdAnswerSeizureRatioAvg 
                                                       Gauge32,
       acKpiSbcCallStatsIntervalSrdNetworkEffectivenessRatioAvg 
                                                       Gauge32,
       acKpiSbcCallStatsIntervalSrdForwardedCallsIn    Counter64,
       acKpiSbcCallStatsIntervalSrdForwardedCallsOut   Counter64,
       acKpiSbcCallStatsIntervalSrdMediaBrokenConnectionCalls 
                                                       Counter64,
       acKpiSbcCallStatsIntervalSrdNotEstablishSuccessCallsIn 
                                                       Counter64,
       acKpiSbcCallStatsIntervalSrdNotEstablishSuccessCallsOut 
                                                       Counter64,
       acKpiSbcCallStatsIntervalSrdNotEstablishFailedCallsIn 
                                                       Counter64,
       acKpiSbcCallStatsIntervalSrdNotEstablishFailedCallsOut 
                                                       Counter64,
       acKpiSbcCallStatsIntervalSrdBusyCallsIn         Counter64,
       acKpiSbcCallStatsIntervalSrdBusyCallsOut        Counter64,
       acKpiSbcCallStatsIntervalSrdNoAnswerCallsIn     Counter64,
       acKpiSbcCallStatsIntervalSrdNoAnswerCallsOut    Counter64,
       acKpiSbcCallStatsIntervalSrdNoResourcesCallsIn  Counter64,
       acKpiSbcCallStatsIntervalSrdNoResourcesCallsOut Counter64,
       acKpiSbcCallStatsIntervalSrdMediaMismatchCallsIn 
                                                       Counter64,
       acKpiSbcCallStatsIntervalSrdMediaMismatchCallsOut 
                                                       Counter64,
       acKpiSbcCallStatsIntervalSrdAdmissionFailedCallsIn 
                                                       Counter64,
       acKpiSbcCallStatsIntervalSrdAdmissionFailedCallsOut 
                                                       Counter64,
       acKpiSbcCallStatsIntervalSrdNoRouteCallsIn      Counter64,
       acKpiSbcCallStatsIntervalSrdClassificationFailedCallsIn 
                                                       Counter64,
       acKpiSbcCallStatsIntervalSrdOtherReasonCallsIn  Counter64,
       acKpiSbcCallStatsIntervalSrdOtherReasonCallsOut Counter64,
       acKpiSbcCallStatsIntervalSrdAbnormalTerminatedCallsIn 
                                                       Counter64,
       acKpiSbcCallStatsIntervalSrdAbnormalTerminatedCallsOut 
                                                       Counter64,
       acKpiSbcCallStatsIntervalSrdPostDialDelayAvg    Gauge32,
       acKpiSbcCallStatsIntervalSrdPostDialDelayMax    Gauge32,
       acKpiSbcCallStatsIntervalSrdPostDialDelayMin    Gauge32,
       acKpiSbcCallStatsIntervalSrdMinutesOfUsage      Counter64,
       acKpiSbcCallStatsIntervalSrdShortCallsCounter   Counter64,
       acKpiSbcCallStatsIntervalSrdLongCallsCounter    Counter64,
       acKpiSbcCallStatsIntervalSrdNotEstablishCallsIn Counter64,
       acKpiSbcCallStatsIntervalSrdNotEstablishCallsOut 
                                                       Counter64
     }



     acKpiSbcCallStatsIntervalSrdIndex OBJECT-TYPE
       SYNTAX Unsigned32 (0..32767)
       MAX-ACCESS not-accessible
       STATUS current
       DESCRIPTION
           "
AC INI-Param: N/A"
       ::= {acKpiSbcCallStatsIntervalSrdEntry 1}



     acKpiSbcCallStatsIntervalSrdInterval OBJECT-TYPE
       SYNTAX Unsigned32 (1..200)
       MAX-ACCESS not-accessible
       STATUS current
       DESCRIPTION
           "
AC INI-Param: N/A"
       ::= {acKpiSbcCallStatsIntervalSrdEntry 2}



     acKpiSbcCallStatsIntervalSrdAverageCallDurationAvg OBJECT-TYPE
       SYNTAX Gauge32
       MAX-ACCESS read-only
       STATUS current
       DESCRIPTION
           "Average call duration (ACD, seconds).
AC INI-Param: N/A"
       ::= {acKpiSbcCallStatsIntervalSrdEntry 3}



     acKpiSbcCallStatsIntervalSrdActiveCallsInAvg OBJECT-TYPE
       SYNTAX Gauge32
       MAX-ACCESS read-only
       STATUS current
       DESCRIPTION
           "Average number of active inbound calls (INVITE dialogs in all
states).
AC INI-Param: N/A"
       ::= {acKpiSbcCallStatsIntervalSrdEntry 4}



     acKpiSbcCallStatsIntervalSrdActiveCallsInMax OBJECT-TYPE
       SYNTAX Gauge32
       MAX-ACCESS read-only
       STATUS current
       DESCRIPTION
           "Maximum number of active inbound calls (INVITE dialogs in all
states).
AC INI-Param: N/A"
       ::= {acKpiSbcCallStatsIntervalSrdEntry 5}



     acKpiSbcCallStatsIntervalSrdActiveCallsOutAvg OBJECT-TYPE
       SYNTAX Gauge32
       MAX-ACCESS read-only
       STATUS current
       DESCRIPTION
           "Average number of active outbound calls (INVITE dialogs in all
states).
AC INI-Param: N/A"
       ::= {acKpiSbcCallStatsIntervalSrdEntry 6}



     acKpiSbcCallStatsIntervalSrdActiveCallsOutMax OBJECT-TYPE
       SYNTAX Gauge32
       MAX-ACCESS read-only
       STATUS current
       DESCRIPTION
           "Maximum number of active outbound calls (INVITE dialogs in all
states).
AC INI-Param: N/A"
       ::= {acKpiSbcCallStatsIntervalSrdEntry 7}



     acKpiSbcCallStatsIntervalSrdAttemptedCallsIn OBJECT-TYPE
       SYNTAX Counter64
       MAX-ACCESS read-only
       STATUS current
       DESCRIPTION
           "Number of attempted inbound calls (INVITE dialogs).
AC INI-Param: N/A"
       ::= {acKpiSbcCallStatsIntervalSrdEntry 8}



     acKpiSbcCallStatsIntervalSrdAttemptedCallsOut OBJECT-TYPE
       SYNTAX Counter64
       MAX-ACCESS read-only
       STATUS current
       DESCRIPTION
           "Number of attempted outbound calls (INVITE dialogs).
AC INI-Param: N/A"
       ::= {acKpiSbcCallStatsIntervalSrdEntry 9}



     acKpiSbcCallStatsIntervalSrdAttemptedCallsRateInAvg OBJECT-TYPE
       SYNTAX Gauge32
       MAX-ACCESS read-only
       STATUS current
       DESCRIPTION
           "Average rate of attempted inbound calls (call attempts per second).
AC INI-Param: N/A"
       ::= {acKpiSbcCallStatsIntervalSrdEntry 10}



     acKpiSbcCallStatsIntervalSrdAttemptedCallsRateInMax OBJECT-TYPE
       SYNTAX Gauge32
       MAX-ACCESS read-only
       STATUS current
       DESCRIPTION
           "Maximum rate of attempted inbound calls (call attempts per second).
AC INI-Param: N/A"
       ::= {acKpiSbcCallStatsIntervalSrdEntry 11}



     acKpiSbcCallStatsIntervalSrdAttemptedCallsRateOutAvg OBJECT-TYPE
       SYNTAX Gauge32
       MAX-ACCESS read-only
       STATUS current
       DESCRIPTION
           "Average rate of attempted outbound calls (call attempts per
second).
AC INI-Param: N/A"
       ::= {acKpiSbcCallStatsIntervalSrdEntry 12}



     acKpiSbcCallStatsIntervalSrdAttemptedCallsRateOutMax OBJECT-TYPE
       SYNTAX Gauge32
       MAX-ACCESS read-only
       STATUS current
       DESCRIPTION
           "Maximum rate of attempted outbound calls (call attempts per
second).
AC INI-Param: N/A"
       ::= {acKpiSbcCallStatsIntervalSrdEntry 13}



     acKpiSbcCallStatsIntervalSrdEstablishedCallsIn OBJECT-TYPE
       SYNTAX Counter64
       MAX-ACCESS read-only
       STATUS current
       DESCRIPTION
           "Number of established inbound calls (INVITE dialogs).
AC INI-Param: N/A"
       ::= {acKpiSbcCallStatsIntervalSrdEntry 14}



     acKpiSbcCallStatsIntervalSrdEstablishedCallsOut OBJECT-TYPE
       SYNTAX Counter64
       MAX-ACCESS read-only
       STATUS current
       DESCRIPTION
           "Number of established outbound calls (INVITE dialogs).
AC INI-Param: N/A"
       ::= {acKpiSbcCallStatsIntervalSrdEntry 15}



     acKpiSbcCallStatsIntervalSrdEstablishedCallsRateInAvg OBJECT-TYPE
       SYNTAX Gauge32
       MAX-ACCESS read-only
       STATUS current
       DESCRIPTION
           "Average rate of established inbound calls (call establish per
second).
AC INI-Param: N/A"
       ::= {acKpiSbcCallStatsIntervalSrdEntry 16}



     acKpiSbcCallStatsIntervalSrdEstablishedCallsRateInMax OBJECT-TYPE
       SYNTAX Gauge32
       MAX-ACCESS read-only
       STATUS current
       DESCRIPTION
           "Maximum rate of established inbound calls (call establish per
second).
AC INI-Param: N/A"
       ::= {acKpiSbcCallStatsIntervalSrdEntry 17}



     acKpiSbcCallStatsIntervalSrdEstablishedCallsRateOutAvg OBJECT-TYPE
       SYNTAX Gauge32
       MAX-ACCESS read-only
       STATUS current
       DESCRIPTION
           "Average rate of established outbound calls (call establish per
second).
AC INI-Param: N/A"
       ::= {acKpiSbcCallStatsIntervalSrdEntry 18}



     acKpiSbcCallStatsIntervalSrdEstablishedCallsRateOutMax OBJECT-TYPE
       SYNTAX Gauge32
       MAX-ACCESS read-only
       STATUS current
       DESCRIPTION
           "Maximum rate of established outbound calls (call establish per
second).
AC INI-Param: N/A"
       ::= {acKpiSbcCallStatsIntervalSrdEntry 19}



     acKpiSbcCallStatsIntervalSrdAnswerSeizureRatioAvg OBJECT-TYPE
       SYNTAX Gauge32
       MAX-ACCESS read-only
       STATUS current
       DESCRIPTION
           "Average answer/seizure ratio (ASR, %).
AC INI-Param: N/A"
       ::= {acKpiSbcCallStatsIntervalSrdEntry 20}



     acKpiSbcCallStatsIntervalSrdNetworkEffectivenessRatioAvg OBJECT-TYPE
       SYNTAX Gauge32
       MAX-ACCESS read-only
       STATUS current
       DESCRIPTION
           "Average network effectiveness ratio (NER, %).
AC INI-Param: N/A"
       ::= {acKpiSbcCallStatsIntervalSrdEntry 21}



     acKpiSbcCallStatsIntervalSrdForwardedCallsIn OBJECT-TYPE
       SYNTAX Counter64
       MAX-ACCESS read-only
       STATUS current
       DESCRIPTION
           "Number of forwarded inbound calls (INVITE dialogs).
AC INI-Param: N/A"
       ::= {acKpiSbcCallStatsIntervalSrdEntry 22}



     acKpiSbcCallStatsIntervalSrdForwardedCallsOut OBJECT-TYPE
       SYNTAX Counter64
       MAX-ACCESS read-only
       STATUS current
       DESCRIPTION
           "Number of forwarded outbound calls (INVITE dialogs).
AC INI-Param: N/A"
       ::= {acKpiSbcCallStatsIntervalSrdEntry 23}



     acKpiSbcCallStatsIntervalSrdMediaBrokenConnectionCalls OBJECT-TYPE
       SYNTAX Counter64
       MAX-ACCESS read-only
       STATUS current
       DESCRIPTION
           "Number of calls that failed due to broken connection.
AC INI-Param: N/A"
       ::= {acKpiSbcCallStatsIntervalSrdEntry 24}



     acKpiSbcCallStatsIntervalSrdNotEstablishSuccessCallsIn OBJECT-TYPE
       SYNTAX Counter64
       MAX-ACCESS read-only
       STATUS current
       DESCRIPTION
           "Number of not established inbound calls configured as success.
AC INI-Param: N/A"
       ::= {acKpiSbcCallStatsIntervalSrdEntry 25}



     acKpiSbcCallStatsIntervalSrdNotEstablishSuccessCallsOut OBJECT-TYPE
       SYNTAX Counter64
       MAX-ACCESS read-only
       STATUS current
       DESCRIPTION
           "Number of not established outbound calls configured as success.
AC INI-Param: N/A"
       ::= {acKpiSbcCallStatsIntervalSrdEntry 26}



     acKpiSbcCallStatsIntervalSrdNotEstablishFailedCallsIn OBJECT-TYPE
       SYNTAX Counter64
       MAX-ACCESS read-only
       STATUS current
       DESCRIPTION
           "Number of not established inbound calls configured as failed.
AC INI-Param: N/A"
       ::= {acKpiSbcCallStatsIntervalSrdEntry 27}



     acKpiSbcCallStatsIntervalSrdNotEstablishFailedCallsOut OBJECT-TYPE
       SYNTAX Counter64
       MAX-ACCESS read-only
       STATUS current
       DESCRIPTION
           "Number of not established outbound calls configured as failed.
AC INI-Param: N/A"
       ::= {acKpiSbcCallStatsIntervalSrdEntry 28}



     acKpiSbcCallStatsIntervalSrdBusyCallsIn OBJECT-TYPE
       SYNTAX Counter64
       MAX-ACCESS read-only
       STATUS current
       DESCRIPTION
           "Number of inbound calls closed due to callee being busy.
AC INI-Param: N/A"
       ::= {acKpiSbcCallStatsIntervalSrdEntry 29}



     acKpiSbcCallStatsIntervalSrdBusyCallsOut OBJECT-TYPE
       SYNTAX Counter64
       MAX-ACCESS read-only
       STATUS current
       DESCRIPTION
           "Number of outbound calls closed due to callee being busy.
AC INI-Param: N/A"
       ::= {acKpiSbcCallStatsIntervalSrdEntry 30}



     acKpiSbcCallStatsIntervalSrdNoAnswerCallsIn OBJECT-TYPE
       SYNTAX Counter64
       MAX-ACCESS read-only
       STATUS current
       DESCRIPTION
           "Number of inbound calls closed due to no answer from callee.
AC INI-Param: N/A"
       ::= {acKpiSbcCallStatsIntervalSrdEntry 31}



     acKpiSbcCallStatsIntervalSrdNoAnswerCallsOut OBJECT-TYPE
       SYNTAX Counter64
       MAX-ACCESS read-only
       STATUS current
       DESCRIPTION
           "Number of outbound calls closed due to no answer from callee.
AC INI-Param: N/A"
       ::= {acKpiSbcCallStatsIntervalSrdEntry 32}



     acKpiSbcCallStatsIntervalSrdNoResourcesCallsIn OBJECT-TYPE
       SYNTAX Counter64
       MAX-ACCESS read-only
       STATUS current
       DESCRIPTION
           "Number of inbound calls closed due to lack of internal resources.
AC INI-Param: N/A"
       ::= {acKpiSbcCallStatsIntervalSrdEntry 33}



     acKpiSbcCallStatsIntervalSrdNoResourcesCallsOut OBJECT-TYPE
       SYNTAX Counter64
       MAX-ACCESS read-only
       STATUS current
       DESCRIPTION
           "Number of outbound calls closed due to lack of internal resources.
AC INI-Param: N/A"
       ::= {acKpiSbcCallStatsIntervalSrdEntry 34}



     acKpiSbcCallStatsIntervalSrdMediaMismatchCallsIn OBJECT-TYPE
       SYNTAX Counter64
       MAX-ACCESS read-only
       STATUS current
       DESCRIPTION
           "Number of inbound calls closed due to media mismatch.
AC INI-Param: N/A"
       ::= {acKpiSbcCallStatsIntervalSrdEntry 35}



     acKpiSbcCallStatsIntervalSrdMediaMismatchCallsOut OBJECT-TYPE
       SYNTAX Counter64
       MAX-ACCESS read-only
       STATUS current
       DESCRIPTION
           "Number of outbound calls closed due to media mismatch.
AC INI-Param: N/A"
       ::= {acKpiSbcCallStatsIntervalSrdEntry 36}



     acKpiSbcCallStatsIntervalSrdAdmissionFailedCallsIn OBJECT-TYPE
       SYNTAX Counter64
       MAX-ACCESS read-only
       STATUS current
       DESCRIPTION
           "Number of inbound calls closed due to admission control (CAC).
AC INI-Param: N/A"
       ::= {acKpiSbcCallStatsIntervalSrdEntry 37}



     acKpiSbcCallStatsIntervalSrdAdmissionFailedCallsOut OBJECT-TYPE
       SYNTAX Counter64
       MAX-ACCESS read-only
       STATUS current
       DESCRIPTION
           "Number of outbound calls closed due to admission control (CAC).
AC INI-Param: N/A"
       ::= {acKpiSbcCallStatsIntervalSrdEntry 38}



     acKpiSbcCallStatsIntervalSrdNoRouteCallsIn OBJECT-TYPE
       SYNTAX Counter64
       MAX-ACCESS read-only
       STATUS current
       DESCRIPTION
           "Number of inbound calls closed due to routing failure.
AC INI-Param: N/A"
       ::= {acKpiSbcCallStatsIntervalSrdEntry 39}



     acKpiSbcCallStatsIntervalSrdClassificationFailedCallsIn OBJECT-TYPE
       SYNTAX Counter64
       MAX-ACCESS read-only
       STATUS current
       DESCRIPTION
           "Number of inbound calls closed due to classification failure.
AC INI-Param: N/A"
       ::= {acKpiSbcCallStatsIntervalSrdEntry 40}



     acKpiSbcCallStatsIntervalSrdOtherReasonCallsIn OBJECT-TYPE
       SYNTAX Counter64
       MAX-ACCESS read-only
       STATUS current
       DESCRIPTION
           "Number of inbound calls closed due to other reasons.
AC INI-Param: N/A"
       ::= {acKpiSbcCallStatsIntervalSrdEntry 41}



     acKpiSbcCallStatsIntervalSrdOtherReasonCallsOut OBJECT-TYPE
       SYNTAX Counter64
       MAX-ACCESS read-only
       STATUS current
       DESCRIPTION
           "Number of outbound calls closed due to other reasons.
AC INI-Param: N/A"
       ::= {acKpiSbcCallStatsIntervalSrdEntry 42}



     acKpiSbcCallStatsIntervalSrdAbnormalTerminatedCallsIn OBJECT-TYPE
       SYNTAX Counter64
       MAX-ACCESS read-only
       STATUS current
       DESCRIPTION
           "Number of abnormally terminated inbound calls (after connect).
AC INI-Param: N/A"
       ::= {acKpiSbcCallStatsIntervalSrdEntry 43}



     acKpiSbcCallStatsIntervalSrdAbnormalTerminatedCallsOut OBJECT-TYPE
       SYNTAX Counter64
       MAX-ACCESS read-only
       STATUS current
       DESCRIPTION
           "Number of abnormally terminated outbound calls (after connect).
AC INI-Param: N/A"
       ::= {acKpiSbcCallStatsIntervalSrdEntry 44}



     acKpiSbcCallStatsIntervalSrdPostDialDelayAvg OBJECT-TYPE
       SYNTAX Gauge32
       MAX-ACCESS read-only
       STATUS current
       DESCRIPTION
           "Average number of seconds from INVITE to response.
AC INI-Param: N/A"
       ::= {acKpiSbcCallStatsIntervalSrdEntry 45}



     acKpiSbcCallStatsIntervalSrdPostDialDelayMax OBJECT-TYPE
       SYNTAX Gauge32
       MAX-ACCESS read-only
       STATUS current
       DESCRIPTION
           "Maximum number of seconds from INVITE to response.
AC INI-Param: N/A"
       ::= {acKpiSbcCallStatsIntervalSrdEntry 46}



     acKpiSbcCallStatsIntervalSrdPostDialDelayMin OBJECT-TYPE
       SYNTAX Gauge32
       MAX-ACCESS read-only
       STATUS current
       DESCRIPTION
           "Minimum number of seconds from INVITE to response.
AC INI-Param: N/A"
       ::= {acKpiSbcCallStatsIntervalSrdEntry 47}



     acKpiSbcCallStatsIntervalSrdMinutesOfUsage OBJECT-TYPE
       SYNTAX Counter64
       MAX-ACCESS read-only
       STATUS current
       DESCRIPTION
           "Sum in minutes of call duration.
AC INI-Param: N/A"
       ::= {acKpiSbcCallStatsIntervalSrdEntry 48}



     acKpiSbcCallStatsIntervalSrdShortCallsCounter OBJECT-TYPE
       SYNTAX Counter64
       MAX-ACCESS read-only
       STATUS current
       DESCRIPTION
           "Number of calls with duration shorter than pre-set threshold.
AC INI-Param: N/A"
       ::= {acKpiSbcCallStatsIntervalSrdEntry 49}



     acKpiSbcCallStatsIntervalSrdLongCallsCounter OBJECT-TYPE
       SYNTAX Counter64
       MAX-ACCESS read-only
       STATUS current
       DESCRIPTION
           "Number of calls with duration longer than pre-set threshold.
AC INI-Param: N/A"
       ::= {acKpiSbcCallStatsIntervalSrdEntry 50}



     acKpiSbcCallStatsIntervalSrdNotEstablishCallsIn OBJECT-TYPE
       SYNTAX Counter64
       MAX-ACCESS read-only
       STATUS current
       DESCRIPTION
           "Number of not established inbound calls (due to all reasons).
AC INI-Param: N/A"
       ::= {acKpiSbcCallStatsIntervalSrdEntry 51}



     acKpiSbcCallStatsIntervalSrdNotEstablishCallsOut OBJECT-TYPE
       SYNTAX Counter64
       MAX-ACCESS read-only
       STATUS current
       DESCRIPTION
           "Number of not established outbound calls (due to all reasons).
AC INI-Param: N/A"
       ::= {acKpiSbcCallStatsIntervalSrdEntry 52}



     acKpiUserDefined OBJECT IDENTIFIER ::= {acKpiSbc 2}


     acKpiUserDefinedCurrent OBJECT IDENTIFIER ::= {acKpiUserDefined 1}


     acKpiUserDefinedCurrentGlobal OBJECT IDENTIFIER ::= {acKpiUserDefinedCurrent 1}


     acKpiUserDefinedCurrentGlobalUserDefinedFailuresIn1Total OBJECT-TYPE
       SYNTAX Counter64
       MAX-ACCESS read-only
       STATUS current
       DESCRIPTION
           "Total number of inbound user defined failures 1.
AC INI-Param: N/A"
       ::= {acKpiUserDefinedCurrentGlobal 1}



     acKpiUserDefinedCurrentGlobalUserDefinedFailuresOut1Total OBJECT-TYPE
       SYNTAX Counter64
       MAX-ACCESS read-only
       STATUS current
       DESCRIPTION
           "Total number of outbound user defined failures 1.
AC INI-Param: N/A"
       ::= {acKpiUserDefinedCurrentGlobal 2}



     acKpiUserDefinedCurrentGlobalUserDefinedFailuresIn2Total OBJECT-TYPE
       SYNTAX Counter64
       MAX-ACCESS read-only
       STATUS current
       DESCRIPTION
           "Total number of inbound user defined failures 2.
AC INI-Param: N/A"
       ::= {acKpiUserDefinedCurrentGlobal 3}



     acKpiUserDefinedCurrentGlobalUserDefinedFailuresOut2Total OBJECT-TYPE
       SYNTAX Counter64
       MAX-ACCESS read-only
       STATUS current
       DESCRIPTION
           "Total number of outbound user defined failures 2.
AC INI-Param: N/A"
       ::= {acKpiUserDefinedCurrentGlobal 4}



     acKpiUserDefinedCurrentGlobalUserDefinedFailuresIn3Total OBJECT-TYPE
       SYNTAX Counter64
       MAX-ACCESS read-only
       STATUS current
       DESCRIPTION
           "Total number of inbound user defined failures 3.
AC INI-Param: N/A"
       ::= {acKpiUserDefinedCurrentGlobal 5}



     acKpiUserDefinedCurrentGlobalUserDefinedFailuresOut3Total OBJECT-TYPE
       SYNTAX Counter64
       MAX-ACCESS read-only
       STATUS current
       DESCRIPTION
           "Total number of outbound user defined failures 3.
AC INI-Param: N/A"
       ::= {acKpiUserDefinedCurrentGlobal 6}



     acKpiUserDefinedCurrentGlobalUserDefinedFailuresIn4Total OBJECT-TYPE
       SYNTAX Counter64
       MAX-ACCESS read-only
       STATUS current
       DESCRIPTION
           "Total number of inbound user defined failures 4.
AC INI-Param: N/A"
       ::= {acKpiUserDefinedCurrentGlobal 7}



     acKpiUserDefinedCurrentGlobalUserDefinedFailuresOut4Total OBJECT-TYPE
       SYNTAX Counter64
       MAX-ACCESS read-only
       STATUS current
       DESCRIPTION
           "Total number of outbound user defined failures 4.
AC INI-Param: N/A"
       ::= {acKpiUserDefinedCurrentGlobal 8}



     acKpiUserDefinedCurrentGlobalUserDefinedFailuresIn5Total OBJECT-TYPE
       SYNTAX Counter64
       MAX-ACCESS read-only
       STATUS current
       DESCRIPTION
           "Total number of inbound user defined failures 5.
AC INI-Param: N/A"
       ::= {acKpiUserDefinedCurrentGlobal 9}



     acKpiUserDefinedCurrentGlobalUserDefinedFailuresOut5Total OBJECT-TYPE
       SYNTAX Counter64
       MAX-ACCESS read-only
       STATUS current
       DESCRIPTION
           "Total number of outbound user defined failures 5.
AC INI-Param: N/A"
       ::= {acKpiUserDefinedCurrentGlobal 10}



     acKpiUserDefinedCurrentGlobalUserDefinedFailuresIn6Total OBJECT-TYPE
       SYNTAX Counter64
       MAX-ACCESS read-only
       STATUS current
       DESCRIPTION
           "Total number of inbound user defined failures 6.
AC INI-Param: N/A"
       ::= {acKpiUserDefinedCurrentGlobal 11}



     acKpiUserDefinedCurrentGlobalUserDefinedFailuresOut6Total OBJECT-TYPE
       SYNTAX Counter64
       MAX-ACCESS read-only
       STATUS current
       DESCRIPTION
           "Total number of outbound user defined failures 6.
AC INI-Param: N/A"
       ::= {acKpiUserDefinedCurrentGlobal 12}



     acKpiUserDefinedCurrentGlobalUserDefinedFailuresIn7Total OBJECT-TYPE
       SYNTAX Counter64
       MAX-ACCESS read-only
       STATUS current
       DESCRIPTION
           "Total number of inbound user defined failures 7.
AC INI-Param: N/A"
       ::= {acKpiUserDefinedCurrentGlobal 13}



     acKpiUserDefinedCurrentGlobalUserDefinedFailuresOut7Total OBJECT-TYPE
       SYNTAX Counter64
       MAX-ACCESS read-only
       STATUS current
       DESCRIPTION
           "Total number of outbound user defined failures 7.
AC INI-Param: N/A"
       ::= {acKpiUserDefinedCurrentGlobal 14}



     acKpiUserDefinedCurrentGlobalUserDefinedFailuresIn8Total OBJECT-TYPE
       SYNTAX Counter64
       MAX-ACCESS read-only
       STATUS current
       DESCRIPTION
           "Total number of inbound user defined failures 8.
AC INI-Param: N/A"
       ::= {acKpiUserDefinedCurrentGlobal 15}



     acKpiUserDefinedCurrentGlobalUserDefinedFailuresOut8Total OBJECT-TYPE
       SYNTAX Counter64
       MAX-ACCESS read-only
       STATUS current
       DESCRIPTION
           "Total number of outbound user defined failures 8.
AC INI-Param: N/A"
       ::= {acKpiUserDefinedCurrentGlobal 16}



     acKpiUserDefinedCurrentGlobalUserDefinedFailuresIn9Total OBJECT-TYPE
       SYNTAX Counter64
       MAX-ACCESS read-only
       STATUS current
       DESCRIPTION
           "Total number of inbound user defined failures 9.
AC INI-Param: N/A"
       ::= {acKpiUserDefinedCurrentGlobal 17}



     acKpiUserDefinedCurrentGlobalUserDefinedFailuresOut9Total OBJECT-TYPE
       SYNTAX Counter64
       MAX-ACCESS read-only
       STATUS current
       DESCRIPTION
           "Total number of outbound user defined failures 9.
AC INI-Param: N/A"
       ::= {acKpiUserDefinedCurrentGlobal 18}



     acKpiUserDefinedCurrentGlobalUserDefinedFailuresIn10Total OBJECT-TYPE
       SYNTAX Counter64
       MAX-ACCESS read-only
       STATUS current
       DESCRIPTION
           "Total number of inbound user defined failures 10.
AC INI-Param: N/A"
       ::= {acKpiUserDefinedCurrentGlobal 19}



     acKpiUserDefinedCurrentGlobalUserDefinedFailuresOut10Total OBJECT-TYPE
       SYNTAX Counter64
       MAX-ACCESS read-only
       STATUS current
       DESCRIPTION
           "Total number of outbound user defined failures 10.
AC INI-Param: N/A"
       ::= {acKpiUserDefinedCurrentGlobal 20}



     acKpiUserDefinedCurrentGlobalUserDefinedFailuresIn11Total OBJECT-TYPE
       SYNTAX Counter64
       MAX-ACCESS read-only
       STATUS current
       DESCRIPTION
           "Total number of inbound user defined failures 11.
AC INI-Param: N/A"
       ::= {acKpiUserDefinedCurrentGlobal 21}



     acKpiUserDefinedCurrentGlobalUserDefinedFailuresOut11Total OBJECT-TYPE
       SYNTAX Counter64
       MAX-ACCESS read-only
       STATUS current
       DESCRIPTION
           "Total number of outbound user defined failures 11.
AC INI-Param: N/A"
       ::= {acKpiUserDefinedCurrentGlobal 22}



     acKpiUserDefinedCurrentGlobalUserDefinedFailuresIn12Total OBJECT-TYPE
       SYNTAX Counter64
       MAX-ACCESS read-only
       STATUS current
       DESCRIPTION
           "Total number of inbound user defined failures 12.
AC INI-Param: N/A"
       ::= {acKpiUserDefinedCurrentGlobal 23}



     acKpiUserDefinedCurrentGlobalUserDefinedFailuresOut12Total OBJECT-TYPE
       SYNTAX Counter64
       MAX-ACCESS read-only
       STATUS current
       DESCRIPTION
           "Total number of outbound user defined failures 12.
AC INI-Param: N/A"
       ::= {acKpiUserDefinedCurrentGlobal 24}



     acKpiUserDefinedCurrentGlobalUserDefinedFailuresIn13Total OBJECT-TYPE
       SYNTAX Counter64
       MAX-ACCESS read-only
       STATUS current
       DESCRIPTION
           "Total number of inbound user defined failures 13.
AC INI-Param: N/A"
       ::= {acKpiUserDefinedCurrentGlobal 25}



     acKpiUserDefinedCurrentGlobalUserDefinedFailuresOut13Total OBJECT-TYPE
       SYNTAX Counter64
       MAX-ACCESS read-only
       STATUS current
       DESCRIPTION
           "Total number of outbound user defined failures 13.
AC INI-Param: N/A"
       ::= {acKpiUserDefinedCurrentGlobal 26}



     acKpiUserDefinedCurrentGlobalUserDefinedFailuresIn14Total OBJECT-TYPE
       SYNTAX Counter64
       MAX-ACCESS read-only
       STATUS current
       DESCRIPTION
           "Total number of inbound user defined failures 14.
AC INI-Param: N/A"
       ::= {acKpiUserDefinedCurrentGlobal 27}



     acKpiUserDefinedCurrentGlobalUserDefinedFailuresOut14Total OBJECT-TYPE
       SYNTAX Counter64
       MAX-ACCESS read-only
       STATUS current
       DESCRIPTION
           "Total number of outbound user defined failures 14.
AC INI-Param: N/A"
       ::= {acKpiUserDefinedCurrentGlobal 28}



     acKpiUserDefinedCurrentGlobalUserDefinedFailuresIn15Total OBJECT-TYPE
       SYNTAX Counter64
       MAX-ACCESS read-only
       STATUS current
       DESCRIPTION
           "Total number of inbound user defined failures 15.
AC INI-Param: N/A"
       ::= {acKpiUserDefinedCurrentGlobal 29}



     acKpiUserDefinedCurrentGlobalUserDefinedFailuresOut15Total OBJECT-TYPE
       SYNTAX Counter64
       MAX-ACCESS read-only
       STATUS current
       DESCRIPTION
           "Total number of outbound user defined failures 15.
AC INI-Param: N/A"
       ::= {acKpiUserDefinedCurrentGlobal 30}



     acKpiUserDefinedCurrentGlobalUserDefinedFailuresIn16Total OBJECT-TYPE
       SYNTAX Counter64
       MAX-ACCESS read-only
       STATUS current
       DESCRIPTION
           "Total number of inbound user defined failures 16.
AC INI-Param: N/A"
       ::= {acKpiUserDefinedCurrentGlobal 31}



     acKpiUserDefinedCurrentGlobalUserDefinedFailuresOut16Total OBJECT-TYPE
       SYNTAX Counter64
       MAX-ACCESS read-only
       STATUS current
       DESCRIPTION
           "Total number of outbound user defined failures 16.
AC INI-Param: N/A"
       ::= {acKpiUserDefinedCurrentGlobal 32}



     acKpiUserDefinedCurrentGlobalUserDefinedFailuresIn17Total OBJECT-TYPE
       SYNTAX Counter64
       MAX-ACCESS read-only
       STATUS current
       DESCRIPTION
           "Total number of inbound user defined failures 17.
AC INI-Param: N/A"
       ::= {acKpiUserDefinedCurrentGlobal 33}



     acKpiUserDefinedCurrentGlobalUserDefinedFailuresOut17Total OBJECT-TYPE
       SYNTAX Counter64
       MAX-ACCESS read-only
       STATUS current
       DESCRIPTION
           "Total number of outbound user defined failures 17.
AC INI-Param: N/A"
       ::= {acKpiUserDefinedCurrentGlobal 34}



     acKpiUserDefinedCurrentGlobalUserDefinedFailuresIn18Total OBJECT-TYPE
       SYNTAX Counter64
       MAX-ACCESS read-only
       STATUS current
       DESCRIPTION
           "Total number of inbound user defined failures 18.
AC INI-Param: N/A"
       ::= {acKpiUserDefinedCurrentGlobal 35}



     acKpiUserDefinedCurrentGlobalUserDefinedFailuresOut18Total OBJECT-TYPE
       SYNTAX Counter64
       MAX-ACCESS read-only
       STATUS current
       DESCRIPTION
           "Total number of outbound user defined failures 18.
AC INI-Param: N/A"
       ::= {acKpiUserDefinedCurrentGlobal 36}



     acKpiUserDefinedCurrentGlobalUserDefinedFailuresIn19Total OBJECT-TYPE
       SYNTAX Counter64
       MAX-ACCESS read-only
       STATUS current
       DESCRIPTION
           "Total number of inbound user defined failures 19.
AC INI-Param: N/A"
       ::= {acKpiUserDefinedCurrentGlobal 37}



     acKpiUserDefinedCurrentGlobalUserDefinedFailuresOut19Total OBJECT-TYPE
       SYNTAX Counter64
       MAX-ACCESS read-only
       STATUS current
       DESCRIPTION
           "Total number of outbound user defined failures 19.
AC INI-Param: N/A"
       ::= {acKpiUserDefinedCurrentGlobal 38}



     acKpiUserDefinedCurrentGlobalUserDefinedFailuresIn20Total OBJECT-TYPE
       SYNTAX Counter64
       MAX-ACCESS read-only
       STATUS current
       DESCRIPTION
           "Total number of inbound user defined failures 20.
AC INI-Param: N/A"
       ::= {acKpiUserDefinedCurrentGlobal 39}



     acKpiUserDefinedCurrentGlobalUserDefinedFailuresOut20Total OBJECT-TYPE
       SYNTAX Counter64
       MAX-ACCESS read-only
       STATUS current
       DESCRIPTION
           "Total number of outbound user defined failures 20.
AC INI-Param: N/A"
       ::= {acKpiUserDefinedCurrentGlobal 40}



     acKpiUserDefinedCurrentGlobalUserDefinedFailuresIn21Total OBJECT-TYPE
       SYNTAX Counter64
       MAX-ACCESS read-only
       STATUS current
       DESCRIPTION
           "Total number of inbound user defined failures 21.
AC INI-Param: N/A"
       ::= {acKpiUserDefinedCurrentGlobal 41}



     acKpiUserDefinedCurrentGlobalUserDefinedFailuresOut21Total OBJECT-TYPE
       SYNTAX Counter64
       MAX-ACCESS read-only
       STATUS current
       DESCRIPTION
           "Total number of outbound user defined failures 21.
AC INI-Param: N/A"
       ::= {acKpiUserDefinedCurrentGlobal 42}



     acKpiUserDefinedCurrentGlobalUserDefinedFailuresIn22Total OBJECT-TYPE
       SYNTAX Counter64
       MAX-ACCESS read-only
       STATUS current
       DESCRIPTION
           "Total number of inbound user defined failures 22.
AC INI-Param: N/A"
       ::= {acKpiUserDefinedCurrentGlobal 43}



     acKpiUserDefinedCurrentGlobalUserDefinedFailuresOut22Total OBJECT-TYPE
       SYNTAX Counter64
       MAX-ACCESS read-only
       STATUS current
       DESCRIPTION
           "Total number of outbound user defined failures 22.
AC INI-Param: N/A"
       ::= {acKpiUserDefinedCurrentGlobal 44}



     acKpiUserDefinedCurrentGlobalUserDefinedFailuresIn23Total OBJECT-TYPE
       SYNTAX Counter64
       MAX-ACCESS read-only
       STATUS current
       DESCRIPTION
           "Total number of inbound user defined failures 23.
AC INI-Param: N/A"
       ::= {acKpiUserDefinedCurrentGlobal 45}



     acKpiUserDefinedCurrentGlobalUserDefinedFailuresOut23Total OBJECT-TYPE
       SYNTAX Counter64
       MAX-ACCESS read-only
       STATUS current
       DESCRIPTION
           "Total number of outbound user defined failures 23.
AC INI-Param: N/A"
       ::= {acKpiUserDefinedCurrentGlobal 46}



     acKpiUserDefinedCurrentGlobalUserDefinedFailuresIn24Total OBJECT-TYPE
       SYNTAX Counter64
       MAX-ACCESS read-only
       STATUS current
       DESCRIPTION
           "Total number of inbound user defined failures 24.
AC INI-Param: N/A"
       ::= {acKpiUserDefinedCurrentGlobal 47}



     acKpiUserDefinedCurrentGlobalUserDefinedFailuresOut24Total OBJECT-TYPE
       SYNTAX Counter64
       MAX-ACCESS read-only
       STATUS current
       DESCRIPTION
           "Total number of outbound user defined failures 24.
AC INI-Param: N/A"
       ::= {acKpiUserDefinedCurrentGlobal 48}



     acKpiUserDefinedCurrentGlobalUserDefinedFailuresIn25Total OBJECT-TYPE
       SYNTAX Counter64
       MAX-ACCESS read-only
       STATUS current
       DESCRIPTION
           "Total number of inbound user defined failures 25.
AC INI-Param: N/A"
       ::= {acKpiUserDefinedCurrentGlobal 49}



     acKpiUserDefinedCurrentGlobalUserDefinedFailuresOut25Total OBJECT-TYPE
       SYNTAX Counter64
       MAX-ACCESS read-only
       STATUS current
       DESCRIPTION
           "Total number of outbound user defined failures 25.
AC INI-Param: N/A"
       ::= {acKpiUserDefinedCurrentGlobal 50}



     acKpiUserDefinedCurrentGlobalUserDefinedFailuresIn26Total OBJECT-TYPE
       SYNTAX Counter64
       MAX-ACCESS read-only
       STATUS current
       DESCRIPTION
           "Total number of inbound user defined failures 26.
AC INI-Param: N/A"
       ::= {acKpiUserDefinedCurrentGlobal 51}



     acKpiUserDefinedCurrentGlobalUserDefinedFailuresOut26Total OBJECT-TYPE
       SYNTAX Counter64
       MAX-ACCESS read-only
       STATUS current
       DESCRIPTION
           "Total number of outbound user defined failures 26.
AC INI-Param: N/A"
       ::= {acKpiUserDefinedCurrentGlobal 52}



     acKpiUserDefinedCurrentTables OBJECT IDENTIFIER ::= {acKpiUserDefinedCurrent 2}


     -- ****************************************
     -- acKpiUserDefinedCurrentIpGroup table declaration
     -- ****************************************
     acKpiUserDefinedCurrentIpGroupTable OBJECT-TYPE
       SYNTAX SEQUENCE OF AcKpiUserDefinedCurrentIpGroupEntry
       MAX-ACCESS not-accessible
       STATUS current
       DESCRIPTION
           ""
       ::= {acKpiUserDefinedCurrentTables 1}



     -- ****************************************
     -- acKpiUserDefinedCurrentIpGroup table entry
     -- ****************************************
     acKpiUserDefinedCurrentIpGroupEntry OBJECT-TYPE
       SYNTAX AcKpiUserDefinedCurrentIpGroupEntry
       MAX-ACCESS not-accessible
       STATUS current
       DESCRIPTION
           ""
       INDEX {acKpiUserDefinedCurrentIpGroupIndex}
       ::= {acKpiUserDefinedCurrentIpGroupTable 1}



     -- ****************************************
     -- acKpiUserDefinedCurrentIpGroup TABLE
     -- ****************************************
     AcKpiUserDefinedCurrentIpGroupEntry ::= SEQUENCE {
       acKpiUserDefinedCurrentIpGroupIndex             Unsigned32,
       acKpiUserDefinedCurrentIpGroupUserDefinedFailuresIn1Total 
                                                       Counter64,
       acKpiUserDefinedCurrentIpGroupUserDefinedFailuresOut1Total 
                                                       Counter64,
       acKpiUserDefinedCurrentIpGroupUserDefinedFailuresIn2Total 
                                                       Counter64,
       acKpiUserDefinedCurrentIpGroupUserDefinedFailuresOut2Total 
                                                       Counter64,
       acKpiUserDefinedCurrentIpGroupUserDefinedFailuresIn3Total 
                                                       Counter64,
       acKpiUserDefinedCurrentIpGroupUserDefinedFailuresOut3Total 
                                                       Counter64,
       acKpiUserDefinedCurrentIpGroupUserDefinedFailuresIn4Total 
                                                       Counter64,
       acKpiUserDefinedCurrentIpGroupUserDefinedFailuresOut4Total 
                                                       Counter64,
       acKpiUserDefinedCurrentIpGroupUserDefinedFailuresIn5Total 
                                                       Counter64,
       acKpiUserDefinedCurrentIpGroupUserDefinedFailuresOut5Total 
                                                       Counter64,
       acKpiUserDefinedCurrentIpGroupUserDefinedFailuresIn6Total 
                                                       Counter64,
       acKpiUserDefinedCurrentIpGroupUserDefinedFailuresOut6Total 
                                                       Counter64,
       acKpiUserDefinedCurrentIpGroupUserDefinedFailuresIn7Total 
                                                       Counter64,
       acKpiUserDefinedCurrentIpGroupUserDefinedFailuresOut7Total 
                                                       Counter64,
       acKpiUserDefinedCurrentIpGroupUserDefinedFailuresIn8Total 
                                                       Counter64,
       acKpiUserDefinedCurrentIpGroupUserDefinedFailuresOut8Total 
                                                       Counter64,
       acKpiUserDefinedCurrentIpGroupUserDefinedFailuresIn9Total 
                                                       Counter64,
       acKpiUserDefinedCurrentIpGroupUserDefinedFailuresOut9Total 
                                                       Counter64,
       acKpiUserDefinedCurrentIpGroupUserDefinedFailuresIn10Total 
                                                       Counter64,
       acKpiUserDefinedCurrentIpGroupUserDefinedFailuresOut10Total 
                                                       Counter64,
       acKpiUserDefinedCurrentIpGroupUserDefinedFailuresIn11Total 
                                                       Counter64,
       acKpiUserDefinedCurrentIpGroupUserDefinedFailuresOut11Total 
                                                       Counter64,
       acKpiUserDefinedCurrentIpGroupUserDefinedFailuresIn12Total 
                                                       Counter64,
       acKpiUserDefinedCurrentIpGroupUserDefinedFailuresOut12Total 
                                                       Counter64,
       acKpiUserDefinedCurrentIpGroupUserDefinedFailuresIn13Total 
                                                       Counter64,
       acKpiUserDefinedCurrentIpGroupUserDefinedFailuresOut13Total 
                                                       Counter64,
       acKpiUserDefinedCurrentIpGroupUserDefinedFailuresIn14Total 
                                                       Counter64,
       acKpiUserDefinedCurrentIpGroupUserDefinedFailuresOut14Total 
                                                       Counter64,
       acKpiUserDefinedCurrentIpGroupUserDefinedFailuresIn15Total 
                                                       Counter64,
       acKpiUserDefinedCurrentIpGroupUserDefinedFailuresOut15Total 
                                                       Counter64,
       acKpiUserDefinedCurrentIpGroupUserDefinedFailuresIn16Total 
                                                       Counter64,
       acKpiUserDefinedCurrentIpGroupUserDefinedFailuresOut16Total 
                                                       Counter64,
       acKpiUserDefinedCurrentIpGroupUserDefinedFailuresIn17Total 
                                                       Counter64,
       acKpiUserDefinedCurrentIpGroupUserDefinedFailuresOut17Total 
                                                       Counter64,
       acKpiUserDefinedCurrentIpGroupUserDefinedFailuresIn18Total 
                                                       Counter64,
       acKpiUserDefinedCurrentIpGroupUserDefinedFailuresOut18Total 
                                                       Counter64,
       acKpiUserDefinedCurrentIpGroupUserDefinedFailuresIn19Total 
                                                       Counter64,
       acKpiUserDefinedCurrentIpGroupUserDefinedFailuresOut19Total 
                                                       Counter64,
       acKpiUserDefinedCurrentIpGroupUserDefinedFailuresIn20Total 
                                                       Counter64,
       acKpiUserDefinedCurrentIpGroupUserDefinedFailuresOut20Total 
                                                       Counter64,
       acKpiUserDefinedCurrentIpGroupUserDefinedFailuresIn21Total 
                                                       Counter64,
       acKpiUserDefinedCurrentIpGroupUserDefinedFailuresOut21Total 
                                                       Counter64,
       acKpiUserDefinedCurrentIpGroupUserDefinedFailuresIn22Total 
                                                       Counter64,
       acKpiUserDefinedCurrentIpGroupUserDefinedFailuresOut22Total 
                                                       Counter64,
       acKpiUserDefinedCurrentIpGroupUserDefinedFailuresIn23Total 
                                                       Counter64,
       acKpiUserDefinedCurrentIpGroupUserDefinedFailuresOut23Total 
                                                       Counter64,
       acKpiUserDefinedCurrentIpGroupUserDefinedFailuresIn24Total 
                                                       Counter64,
       acKpiUserDefinedCurrentIpGroupUserDefinedFailuresOut24Total 
                                                       Counter64,
       acKpiUserDefinedCurrentIpGroupUserDefinedFailuresIn25Total 
                                                       Counter64,
       acKpiUserDefinedCurrentIpGroupUserDefinedFailuresOut25Total 
                                                       Counter64,
       acKpiUserDefinedCurrentIpGroupUserDefinedFailuresIn26Total 
                                                       Counter64,
       acKpiUserDefinedCurrentIpGroupUserDefinedFailuresOut26Total 
                                                       Counter64
     }



     acKpiUserDefinedCurrentIpGroupIndex OBJECT-TYPE
       SYNTAX Unsigned32 (0..32767)
       MAX-ACCESS not-accessible
       STATUS current
       DESCRIPTION
           "
AC INI-Param: N/A"
       ::= {acKpiUserDefinedCurrentIpGroupEntry 1}



     acKpiUserDefinedCurrentIpGroupUserDefinedFailuresIn1Total OBJECT-TYPE
       SYNTAX Counter64
       MAX-ACCESS read-only
       STATUS current
       DESCRIPTION
           "Total number of inbound user defined failures 1.
AC INI-Param: N/A"
       ::= {acKpiUserDefinedCurrentIpGroupEntry 2}



     acKpiUserDefinedCurrentIpGroupUserDefinedFailuresOut1Total OBJECT-TYPE
       SYNTAX Counter64
       MAX-ACCESS read-only
       STATUS current
       DESCRIPTION
           "Total number of outbound user defined failures 1.
AC INI-Param: N/A"
       ::= {acKpiUserDefinedCurrentIpGroupEntry 3}



     acKpiUserDefinedCurrentIpGroupUserDefinedFailuresIn2Total OBJECT-TYPE
       SYNTAX Counter64
       MAX-ACCESS read-only
       STATUS current
       DESCRIPTION
           "Total number of inbound user defined failures 2.
AC INI-Param: N/A"
       ::= {acKpiUserDefinedCurrentIpGroupEntry 4}



     acKpiUserDefinedCurrentIpGroupUserDefinedFailuresOut2Total OBJECT-TYPE
       SYNTAX Counter64
       MAX-ACCESS read-only
       STATUS current
       DESCRIPTION
           "Total number of outbound user defined failures 2.
AC INI-Param: N/A"
       ::= {acKpiUserDefinedCurrentIpGroupEntry 5}



     acKpiUserDefinedCurrentIpGroupUserDefinedFailuresIn3Total OBJECT-TYPE
       SYNTAX Counter64
       MAX-ACCESS read-only
       STATUS current
       DESCRIPTION
           "Total number of inbound user defined failures 3.
AC INI-Param: N/A"
       ::= {acKpiUserDefinedCurrentIpGroupEntry 6}



     acKpiUserDefinedCurrentIpGroupUserDefinedFailuresOut3Total OBJECT-TYPE
       SYNTAX Counter64
       MAX-ACCESS read-only
       STATUS current
       DESCRIPTION
           "Total number of outbound user defined failures 3.
AC INI-Param: N/A"
       ::= {acKpiUserDefinedCurrentIpGroupEntry 7}



     acKpiUserDefinedCurrentIpGroupUserDefinedFailuresIn4Total OBJECT-TYPE
       SYNTAX Counter64
       MAX-ACCESS read-only
       STATUS current
       DESCRIPTION
           "Total number of inbound user defined failures 4.
AC INI-Param: N/A"
       ::= {acKpiUserDefinedCurrentIpGroupEntry 8}



     acKpiUserDefinedCurrentIpGroupUserDefinedFailuresOut4Total OBJECT-TYPE
       SYNTAX Counter64
       MAX-ACCESS read-only
       STATUS current
       DESCRIPTION
           "Total number of outbound user defined failures 4.
AC INI-Param: N/A"
       ::= {acKpiUserDefinedCurrentIpGroupEntry 9}



     acKpiUserDefinedCurrentIpGroupUserDefinedFailuresIn5Total OBJECT-TYPE
       SYNTAX Counter64
       MAX-ACCESS read-only
       STATUS current
       DESCRIPTION
           "Total number of inbound user defined failures 5.
AC INI-Param: N/A"
       ::= {acKpiUserDefinedCurrentIpGroupEntry 10}



     acKpiUserDefinedCurrentIpGroupUserDefinedFailuresOut5Total OBJECT-TYPE
       SYNTAX Counter64
       MAX-ACCESS read-only
       STATUS current
       DESCRIPTION
           "Total number of outbound user defined failures 5.
AC INI-Param: N/A"
       ::= {acKpiUserDefinedCurrentIpGroupEntry 11}



     acKpiUserDefinedCurrentIpGroupUserDefinedFailuresIn6Total OBJECT-TYPE
       SYNTAX Counter64
       MAX-ACCESS read-only
       STATUS current
       DESCRIPTION
           "Total number of inbound user defined failures 6.
AC INI-Param: N/A"
       ::= {acKpiUserDefinedCurrentIpGroupEntry 12}



     acKpiUserDefinedCurrentIpGroupUserDefinedFailuresOut6Total OBJECT-TYPE
       SYNTAX Counter64
       MAX-ACCESS read-only
       STATUS current
       DESCRIPTION
           "Total number of outbound user defined failures 6.
AC INI-Param: N/A"
       ::= {acKpiUserDefinedCurrentIpGroupEntry 13}



     acKpiUserDefinedCurrentIpGroupUserDefinedFailuresIn7Total OBJECT-TYPE
       SYNTAX Counter64
       MAX-ACCESS read-only
       STATUS current
       DESCRIPTION
           "Total number of inbound user defined failures 7.
AC INI-Param: N/A"
       ::= {acKpiUserDefinedCurrentIpGroupEntry 14}



     acKpiUserDefinedCurrentIpGroupUserDefinedFailuresOut7Total OBJECT-TYPE
       SYNTAX Counter64
       MAX-ACCESS read-only
       STATUS current
       DESCRIPTION
           "Total number of outbound user defined failures 7.
AC INI-Param: N/A"
       ::= {acKpiUserDefinedCurrentIpGroupEntry 15}



     acKpiUserDefinedCurrentIpGroupUserDefinedFailuresIn8Total OBJECT-TYPE
       SYNTAX Counter64
       MAX-ACCESS read-only
       STATUS current
       DESCRIPTION
           "Total number of inbound user defined failures 8.
AC INI-Param: N/A"
       ::= {acKpiUserDefinedCurrentIpGroupEntry 16}



     acKpiUserDefinedCurrentIpGroupUserDefinedFailuresOut8Total OBJECT-TYPE
       SYNTAX Counter64
       MAX-ACCESS read-only
       STATUS current
       DESCRIPTION
           "Total number of outbound user defined failures 8.
AC INI-Param: N/A"
       ::= {acKpiUserDefinedCurrentIpGroupEntry 17}



     acKpiUserDefinedCurrentIpGroupUserDefinedFailuresIn9Total OBJECT-TYPE
       SYNTAX Counter64
       MAX-ACCESS read-only
       STATUS current
       DESCRIPTION
           "Total number of inbound user defined failures 9.
AC INI-Param: N/A"
       ::= {acKpiUserDefinedCurrentIpGroupEntry 18}



     acKpiUserDefinedCurrentIpGroupUserDefinedFailuresOut9Total OBJECT-TYPE
       SYNTAX Counter64
       MAX-ACCESS read-only
       STATUS current
       DESCRIPTION
           "Total number of outbound user defined failures 9.
AC INI-Param: N/A"
       ::= {acKpiUserDefinedCurrentIpGroupEntry 19}



     acKpiUserDefinedCurrentIpGroupUserDefinedFailuresIn10Total OBJECT-TYPE
       SYNTAX Counter64
       MAX-ACCESS read-only
       STATUS current
       DESCRIPTION
           "Total number of inbound user defined failures 10.
AC INI-Param: N/A"
       ::= {acKpiUserDefinedCurrentIpGroupEntry 20}



     acKpiUserDefinedCurrentIpGroupUserDefinedFailuresOut10Total OBJECT-TYPE
       SYNTAX Counter64
       MAX-ACCESS read-only
       STATUS current
       DESCRIPTION
           "Total number of outbound user defined failures 10.
AC INI-Param: N/A"
       ::= {acKpiUserDefinedCurrentIpGroupEntry 21}



     acKpiUserDefinedCurrentIpGroupUserDefinedFailuresIn11Total OBJECT-TYPE
       SYNTAX Counter64
       MAX-ACCESS read-only
       STATUS current
       DESCRIPTION
           "Total number of inbound user defined failures 11.
AC INI-Param: N/A"
       ::= {acKpiUserDefinedCurrentIpGroupEntry 22}



     acKpiUserDefinedCurrentIpGroupUserDefinedFailuresOut11Total OBJECT-TYPE
       SYNTAX Counter64
       MAX-ACCESS read-only
       STATUS current
       DESCRIPTION
           "Total number of outbound user defined failures 11.
AC INI-Param: N/A"
       ::= {acKpiUserDefinedCurrentIpGroupEntry 23}



     acKpiUserDefinedCurrentIpGroupUserDefinedFailuresIn12Total OBJECT-TYPE
       SYNTAX Counter64
       MAX-ACCESS read-only
       STATUS current
       DESCRIPTION
           "Total number of inbound user defined failures 12.
AC INI-Param: N/A"
       ::= {acKpiUserDefinedCurrentIpGroupEntry 24}



     acKpiUserDefinedCurrentIpGroupUserDefinedFailuresOut12Total OBJECT-TYPE
       SYNTAX Counter64
       MAX-ACCESS read-only
       STATUS current
       DESCRIPTION
           "Total number of outbound user defined failures 12.
AC INI-Param: N/A"
       ::= {acKpiUserDefinedCurrentIpGroupEntry 25}



     acKpiUserDefinedCurrentIpGroupUserDefinedFailuresIn13Total OBJECT-TYPE
       SYNTAX Counter64
       MAX-ACCESS read-only
       STATUS current
       DESCRIPTION
           "Total number of inbound user defined failures 13.
AC INI-Param: N/A"
       ::= {acKpiUserDefinedCurrentIpGroupEntry 26}



     acKpiUserDefinedCurrentIpGroupUserDefinedFailuresOut13Total OBJECT-TYPE
       SYNTAX Counter64
       MAX-ACCESS read-only
       STATUS current
       DESCRIPTION
           "Total number of outbound user defined failures 13.
AC INI-Param: N/A"
       ::= {acKpiUserDefinedCurrentIpGroupEntry 27}



     acKpiUserDefinedCurrentIpGroupUserDefinedFailuresIn14Total OBJECT-TYPE
       SYNTAX Counter64
       MAX-ACCESS read-only
       STATUS current
       DESCRIPTION
           "Total number of inbound user defined failures 14.
AC INI-Param: N/A"
       ::= {acKpiUserDefinedCurrentIpGroupEntry 28}



     acKpiUserDefinedCurrentIpGroupUserDefinedFailuresOut14Total OBJECT-TYPE
       SYNTAX Counter64
       MAX-ACCESS read-only
       STATUS current
       DESCRIPTION
           "Total number of outbound user defined failures 14.
AC INI-Param: N/A"
       ::= {acKpiUserDefinedCurrentIpGroupEntry 29}



     acKpiUserDefinedCurrentIpGroupUserDefinedFailuresIn15Total OBJECT-TYPE
       SYNTAX Counter64
       MAX-ACCESS read-only
       STATUS current
       DESCRIPTION
           "Total number of inbound user defined failures 15.
AC INI-Param: N/A"
       ::= {acKpiUserDefinedCurrentIpGroupEntry 30}



     acKpiUserDefinedCurrentIpGroupUserDefinedFailuresOut15Total OBJECT-TYPE
       SYNTAX Counter64
       MAX-ACCESS read-only
       STATUS current
       DESCRIPTION
           "Total number of outbound user defined failures 15.
AC INI-Param: N/A"
       ::= {acKpiUserDefinedCurrentIpGroupEntry 31}



     acKpiUserDefinedCurrentIpGroupUserDefinedFailuresIn16Total OBJECT-TYPE
       SYNTAX Counter64
       MAX-ACCESS read-only
       STATUS current
       DESCRIPTION
           "Total number of inbound user defined failures 16.
AC INI-Param: N/A"
       ::= {acKpiUserDefinedCurrentIpGroupEntry 32}



     acKpiUserDefinedCurrentIpGroupUserDefinedFailuresOut16Total OBJECT-TYPE
       SYNTAX Counter64
       MAX-ACCESS read-only
       STATUS current
       DESCRIPTION
           "Total number of outbound user defined failures 16.
AC INI-Param: N/A"
       ::= {acKpiUserDefinedCurrentIpGroupEntry 33}



     acKpiUserDefinedCurrentIpGroupUserDefinedFailuresIn17Total OBJECT-TYPE
       SYNTAX Counter64
       MAX-ACCESS read-only
       STATUS current
       DESCRIPTION
           "Total number of inbound user defined failures 17.
AC INI-Param: N/A"
       ::= {acKpiUserDefinedCurrentIpGroupEntry 34}



     acKpiUserDefinedCurrentIpGroupUserDefinedFailuresOut17Total OBJECT-TYPE
       SYNTAX Counter64
       MAX-ACCESS read-only
       STATUS current
       DESCRIPTION
           "Total number of outbound user defined failures 17.
AC INI-Param: N/A"
       ::= {acKpiUserDefinedCurrentIpGroupEntry 35}



     acKpiUserDefinedCurrentIpGroupUserDefinedFailuresIn18Total OBJECT-TYPE
       SYNTAX Counter64
       MAX-ACCESS read-only
       STATUS current
       DESCRIPTION
           "Total number of inbound user defined failures 18.
AC INI-Param: N/A"
       ::= {acKpiUserDefinedCurrentIpGroupEntry 36}



     acKpiUserDefinedCurrentIpGroupUserDefinedFailuresOut18Total OBJECT-TYPE
       SYNTAX Counter64
       MAX-ACCESS read-only
       STATUS current
       DESCRIPTION
           "Total number of outbound user defined failures 18.
AC INI-Param: N/A"
       ::= {acKpiUserDefinedCurrentIpGroupEntry 37}



     acKpiUserDefinedCurrentIpGroupUserDefinedFailuresIn19Total OBJECT-TYPE
       SYNTAX Counter64
       MAX-ACCESS read-only
       STATUS current
       DESCRIPTION
           "Total number of inbound user defined failures 19.
AC INI-Param: N/A"
       ::= {acKpiUserDefinedCurrentIpGroupEntry 38}



     acKpiUserDefinedCurrentIpGroupUserDefinedFailuresOut19Total OBJECT-TYPE
       SYNTAX Counter64
       MAX-ACCESS read-only
       STATUS current
       DESCRIPTION
           "Total number of outbound user defined failures 19.
AC INI-Param: N/A"
       ::= {acKpiUserDefinedCurrentIpGroupEntry 39}



     acKpiUserDefinedCurrentIpGroupUserDefinedFailuresIn20Total OBJECT-TYPE
       SYNTAX Counter64
       MAX-ACCESS read-only
       STATUS current
       DESCRIPTION
           "Total number of inbound user defined failures 20.
AC INI-Param: N/A"
       ::= {acKpiUserDefinedCurrentIpGroupEntry 40}



     acKpiUserDefinedCurrentIpGroupUserDefinedFailuresOut20Total OBJECT-TYPE
       SYNTAX Counter64
       MAX-ACCESS read-only
       STATUS current
       DESCRIPTION
           "Total number of outbound user defined failures 20.
AC INI-Param: N/A"
       ::= {acKpiUserDefinedCurrentIpGroupEntry 41}



     acKpiUserDefinedCurrentIpGroupUserDefinedFailuresIn21Total OBJECT-TYPE
       SYNTAX Counter64
       MAX-ACCESS read-only
       STATUS current
       DESCRIPTION
           "Total number of inbound user defined failures 21.
AC INI-Param: N/A"
       ::= {acKpiUserDefinedCurrentIpGroupEntry 42}



     acKpiUserDefinedCurrentIpGroupUserDefinedFailuresOut21Total OBJECT-TYPE
       SYNTAX Counter64
       MAX-ACCESS read-only
       STATUS current
       DESCRIPTION
           "Total number of outbound user defined failures 21.
AC INI-Param: N/A"
       ::= {acKpiUserDefinedCurrentIpGroupEntry 43}



     acKpiUserDefinedCurrentIpGroupUserDefinedFailuresIn22Total OBJECT-TYPE
       SYNTAX Counter64
       MAX-ACCESS read-only
       STATUS current
       DESCRIPTION
           "Total number of inbound user defined failures 22.
AC INI-Param: N/A"
       ::= {acKpiUserDefinedCurrentIpGroupEntry 44}



     acKpiUserDefinedCurrentIpGroupUserDefinedFailuresOut22Total OBJECT-TYPE
       SYNTAX Counter64
       MAX-ACCESS read-only
       STATUS current
       DESCRIPTION
           "Total number of outbound user defined failures 22.
AC INI-Param: N/A"
       ::= {acKpiUserDefinedCurrentIpGroupEntry 45}



     acKpiUserDefinedCurrentIpGroupUserDefinedFailuresIn23Total OBJECT-TYPE
       SYNTAX Counter64
       MAX-ACCESS read-only
       STATUS current
       DESCRIPTION
           "Total number of inbound user defined failures 23.
AC INI-Param: N/A"
       ::= {acKpiUserDefinedCurrentIpGroupEntry 46}



     acKpiUserDefinedCurrentIpGroupUserDefinedFailuresOut23Total OBJECT-TYPE
       SYNTAX Counter64
       MAX-ACCESS read-only
       STATUS current
       DESCRIPTION
           "Total number of outbound user defined failures 23.
AC INI-Param: N/A"
       ::= {acKpiUserDefinedCurrentIpGroupEntry 47}



     acKpiUserDefinedCurrentIpGroupUserDefinedFailuresIn24Total OBJECT-TYPE
       SYNTAX Counter64
       MAX-ACCESS read-only
       STATUS current
       DESCRIPTION
           "Total number of inbound user defined failures 24.
AC INI-Param: N/A"
       ::= {acKpiUserDefinedCurrentIpGroupEntry 48}



     acKpiUserDefinedCurrentIpGroupUserDefinedFailuresOut24Total OBJECT-TYPE
       SYNTAX Counter64
       MAX-ACCESS read-only
       STATUS current
       DESCRIPTION
           "Total number of outbound user defined failures 24.
AC INI-Param: N/A"
       ::= {acKpiUserDefinedCurrentIpGroupEntry 49}



     acKpiUserDefinedCurrentIpGroupUserDefinedFailuresIn25Total OBJECT-TYPE
       SYNTAX Counter64
       MAX-ACCESS read-only
       STATUS current
       DESCRIPTION
           "Total number of inbound user defined failures 25.
AC INI-Param: N/A"
       ::= {acKpiUserDefinedCurrentIpGroupEntry 50}



     acKpiUserDefinedCurrentIpGroupUserDefinedFailuresOut25Total OBJECT-TYPE
       SYNTAX Counter64
       MAX-ACCESS read-only
       STATUS current
       DESCRIPTION
           "Total number of outbound user defined failures 25.
AC INI-Param: N/A"
       ::= {acKpiUserDefinedCurrentIpGroupEntry 51}



     acKpiUserDefinedCurrentIpGroupUserDefinedFailuresIn26Total OBJECT-TYPE
       SYNTAX Counter64
       MAX-ACCESS read-only
       STATUS current
       DESCRIPTION
           "Total number of inbound user defined failures 26.
AC INI-Param: N/A"
       ::= {acKpiUserDefinedCurrentIpGroupEntry 52}



     acKpiUserDefinedCurrentIpGroupUserDefinedFailuresOut26Total OBJECT-TYPE
       SYNTAX Counter64
       MAX-ACCESS read-only
       STATUS current
       DESCRIPTION
           "Total number of outbound user defined failures 26.
AC INI-Param: N/A"
       ::= {acKpiUserDefinedCurrentIpGroupEntry 53}



     -- ****************************************
     -- acKpiUserDefinedCurrentSrd table declaration
     -- ****************************************
     acKpiUserDefinedCurrentSrdTable OBJECT-TYPE
       SYNTAX SEQUENCE OF AcKpiUserDefinedCurrentSrdEntry
       MAX-ACCESS not-accessible
       STATUS current
       DESCRIPTION
           ""
       ::= {acKpiUserDefinedCurrentTables 2}



     -- ****************************************
     -- acKpiUserDefinedCurrentSrd table entry
     -- ****************************************
     acKpiUserDefinedCurrentSrdEntry OBJECT-TYPE
       SYNTAX AcKpiUserDefinedCurrentSrdEntry
       MAX-ACCESS not-accessible
       STATUS current
       DESCRIPTION
           ""
       INDEX {acKpiUserDefinedCurrentSrdIndex}
       ::= {acKpiUserDefinedCurrentSrdTable 1}



     -- ****************************************
     -- acKpiUserDefinedCurrentSrd TABLE
     -- ****************************************
     AcKpiUserDefinedCurrentSrdEntry ::= SEQUENCE {
       acKpiUserDefinedCurrentSrdIndex                 Unsigned32,
       acKpiUserDefinedCurrentSrdUserDefinedFailuresIn1Total 
                                                       Counter64,
       acKpiUserDefinedCurrentSrdUserDefinedFailuresOut1Total 
                                                       Counter64,
       acKpiUserDefinedCurrentSrdUserDefinedFailuresIn2Total 
                                                       Counter64,
       acKpiUserDefinedCurrentSrdUserDefinedFailuresOut2Total 
                                                       Counter64,
       acKpiUserDefinedCurrentSrdUserDefinedFailuresIn3Total 
                                                       Counter64,
       acKpiUserDefinedCurrentSrdUserDefinedFailuresOut3Total 
                                                       Counter64,
       acKpiUserDefinedCurrentSrdUserDefinedFailuresIn4Total 
                                                       Counter64,
       acKpiUserDefinedCurrentSrdUserDefinedFailuresOut4Total 
                                                       Counter64,
       acKpiUserDefinedCurrentSrdUserDefinedFailuresIn5Total 
                                                       Counter64,
       acKpiUserDefinedCurrentSrdUserDefinedFailuresOut5Total 
                                                       Counter64,
       acKpiUserDefinedCurrentSrdUserDefinedFailuresIn6Total 
                                                       Counter64,
       acKpiUserDefinedCurrentSrdUserDefinedFailuresOut6Total 
                                                       Counter64,
       acKpiUserDefinedCurrentSrdUserDefinedFailuresIn7Total 
                                                       Counter64,
       acKpiUserDefinedCurrentSrdUserDefinedFailuresOut7Total 
                                                       Counter64,
       acKpiUserDefinedCurrentSrdUserDefinedFailuresIn8Total 
                                                       Counter64,
       acKpiUserDefinedCurrentSrdUserDefinedFailuresOut8Total 
                                                       Counter64,
       acKpiUserDefinedCurrentSrdUserDefinedFailuresIn9Total 
                                                       Counter64,
       acKpiUserDefinedCurrentSrdUserDefinedFailuresOut9Total 
                                                       Counter64,
       acKpiUserDefinedCurrentSrdUserDefinedFailuresIn10Total 
                                                       Counter64,
       acKpiUserDefinedCurrentSrdUserDefinedFailuresOut10Total 
                                                       Counter64,
       acKpiUserDefinedCurrentSrdUserDefinedFailuresIn11Total 
                                                       Counter64,
       acKpiUserDefinedCurrentSrdUserDefinedFailuresOut11Total 
                                                       Counter64,
       acKpiUserDefinedCurrentSrdUserDefinedFailuresIn12Total 
                                                       Counter64,
       acKpiUserDefinedCurrentSrdUserDefinedFailuresOut12Total 
                                                       Counter64,
       acKpiUserDefinedCurrentSrdUserDefinedFailuresIn13Total 
                                                       Counter64,
       acKpiUserDefinedCurrentSrdUserDefinedFailuresOut13Total 
                                                       Counter64,
       acKpiUserDefinedCurrentSrdUserDefinedFailuresIn14Total 
                                                       Counter64,
       acKpiUserDefinedCurrentSrdUserDefinedFailuresOut14Total 
                                                       Counter64,
       acKpiUserDefinedCurrentSrdUserDefinedFailuresIn15Total 
                                                       Counter64,
       acKpiUserDefinedCurrentSrdUserDefinedFailuresOut15Total 
                                                       Counter64,
       acKpiUserDefinedCurrentSrdUserDefinedFailuresIn16Total 
                                                       Counter64,
       acKpiUserDefinedCurrentSrdUserDefinedFailuresOut16Total 
                                                       Counter64,
       acKpiUserDefinedCurrentSrdUserDefinedFailuresIn17Total 
                                                       Counter64,
       acKpiUserDefinedCurrentSrdUserDefinedFailuresOut17Total 
                                                       Counter64,
       acKpiUserDefinedCurrentSrdUserDefinedFailuresIn18Total 
                                                       Counter64,
       acKpiUserDefinedCurrentSrdUserDefinedFailuresOut18Total 
                                                       Counter64,
       acKpiUserDefinedCurrentSrdUserDefinedFailuresIn19Total 
                                                       Counter64,
       acKpiUserDefinedCurrentSrdUserDefinedFailuresOut19Total 
                                                       Counter64,
       acKpiUserDefinedCurrentSrdUserDefinedFailuresIn20Total 
                                                       Counter64,
       acKpiUserDefinedCurrentSrdUserDefinedFailuresOut20Total 
                                                       Counter64,
       acKpiUserDefinedCurrentSrdUserDefinedFailuresIn21Total 
                                                       Counter64,
       acKpiUserDefinedCurrentSrdUserDefinedFailuresOut21Total 
                                                       Counter64,
       acKpiUserDefinedCurrentSrdUserDefinedFailuresIn22Total 
                                                       Counter64,
       acKpiUserDefinedCurrentSrdUserDefinedFailuresOut22Total 
                                                       Counter64,
       acKpiUserDefinedCurrentSrdUserDefinedFailuresIn23Total 
                                                       Counter64,
       acKpiUserDefinedCurrentSrdUserDefinedFailuresOut23Total 
                                                       Counter64,
       acKpiUserDefinedCurrentSrdUserDefinedFailuresIn24Total 
                                                       Counter64,
       acKpiUserDefinedCurrentSrdUserDefinedFailuresOut24Total 
                                                       Counter64,
       acKpiUserDefinedCurrentSrdUserDefinedFailuresIn25Total 
                                                       Counter64,
       acKpiUserDefinedCurrentSrdUserDefinedFailuresOut25Total 
                                                       Counter64,
       acKpiUserDefinedCurrentSrdUserDefinedFailuresIn26Total 
                                                       Counter64,
       acKpiUserDefinedCurrentSrdUserDefinedFailuresOut26Total 
                                                       Counter64
     }



     acKpiUserDefinedCurrentSrdIndex OBJECT-TYPE
       SYNTAX Unsigned32 (0..32767)
       MAX-ACCESS not-accessible
       STATUS current
       DESCRIPTION
           "
AC INI-Param: N/A"
       ::= {acKpiUserDefinedCurrentSrdEntry 1}



     acKpiUserDefinedCurrentSrdUserDefinedFailuresIn1Total OBJECT-TYPE
       SYNTAX Counter64
       MAX-ACCESS read-only
       STATUS current
       DESCRIPTION
           "Total number of inbound user defined failures 1.
AC INI-Param: N/A"
       ::= {acKpiUserDefinedCurrentSrdEntry 2}



     acKpiUserDefinedCurrentSrdUserDefinedFailuresOut1Total OBJECT-TYPE
       SYNTAX Counter64
       MAX-ACCESS read-only
       STATUS current
       DESCRIPTION
           "Total number of outbound user defined failures 1.
AC INI-Param: N/A"
       ::= {acKpiUserDefinedCurrentSrdEntry 3}



     acKpiUserDefinedCurrentSrdUserDefinedFailuresIn2Total OBJECT-TYPE
       SYNTAX Counter64
       MAX-ACCESS read-only
       STATUS current
       DESCRIPTION
           "Total number of inbound user defined failures 2.
AC INI-Param: N/A"
       ::= {acKpiUserDefinedCurrentSrdEntry 4}



     acKpiUserDefinedCurrentSrdUserDefinedFailuresOut2Total OBJECT-TYPE
       SYNTAX Counter64
       MAX-ACCESS read-only
       STATUS current
       DESCRIPTION
           "Total number of outbound user defined failures 2.
AC INI-Param: N/A"
       ::= {acKpiUserDefinedCurrentSrdEntry 5}



     acKpiUserDefinedCurrentSrdUserDefinedFailuresIn3Total OBJECT-TYPE
       SYNTAX Counter64
       MAX-ACCESS read-only
       STATUS current
       DESCRIPTION
           "Total number of inbound user defined failures 3.
AC INI-Param: N/A"
       ::= {acKpiUserDefinedCurrentSrdEntry 6}



     acKpiUserDefinedCurrentSrdUserDefinedFailuresOut3Total OBJECT-TYPE
       SYNTAX Counter64
       MAX-ACCESS read-only
       STATUS current
       DESCRIPTION
           "Total number of outbound user defined failures 3.
AC INI-Param: N/A"
       ::= {acKpiUserDefinedCurrentSrdEntry 7}



     acKpiUserDefinedCurrentSrdUserDefinedFailuresIn4Total OBJECT-TYPE
       SYNTAX Counter64
       MAX-ACCESS read-only
       STATUS current
       DESCRIPTION
           "Total number of inbound user defined failures 4.
AC INI-Param: N/A"
       ::= {acKpiUserDefinedCurrentSrdEntry 8}



     acKpiUserDefinedCurrentSrdUserDefinedFailuresOut4Total OBJECT-TYPE
       SYNTAX Counter64
       MAX-ACCESS read-only
       STATUS current
       DESCRIPTION
           "Total number of outbound user defined failures 4.
AC INI-Param: N/A"
       ::= {acKpiUserDefinedCurrentSrdEntry 9}



     acKpiUserDefinedCurrentSrdUserDefinedFailuresIn5Total OBJECT-TYPE
       SYNTAX Counter64
       MAX-ACCESS read-only
       STATUS current
       DESCRIPTION
           "Total number of inbound user defined failures 5.
AC INI-Param: N/A"
       ::= {acKpiUserDefinedCurrentSrdEntry 10}



     acKpiUserDefinedCurrentSrdUserDefinedFailuresOut5Total OBJECT-TYPE
       SYNTAX Counter64
       MAX-ACCESS read-only
       STATUS current
       DESCRIPTION
           "Total number of outbound user defined failures 5.
AC INI-Param: N/A"
       ::= {acKpiUserDefinedCurrentSrdEntry 11}



     acKpiUserDefinedCurrentSrdUserDefinedFailuresIn6Total OBJECT-TYPE
       SYNTAX Counter64
       MAX-ACCESS read-only
       STATUS current
       DESCRIPTION
           "Total number of inbound user defined failures 6.
AC INI-Param: N/A"
       ::= {acKpiUserDefinedCurrentSrdEntry 12}



     acKpiUserDefinedCurrentSrdUserDefinedFailuresOut6Total OBJECT-TYPE
       SYNTAX Counter64
       MAX-ACCESS read-only
       STATUS current
       DESCRIPTION
           "Total number of outbound user defined failures 6.
AC INI-Param: N/A"
       ::= {acKpiUserDefinedCurrentSrdEntry 13}



     acKpiUserDefinedCurrentSrdUserDefinedFailuresIn7Total OBJECT-TYPE
       SYNTAX Counter64
       MAX-ACCESS read-only
       STATUS current
       DESCRIPTION
           "Total number of inbound user defined failures 7.
AC INI-Param: N/A"
       ::= {acKpiUserDefinedCurrentSrdEntry 14}



     acKpiUserDefinedCurrentSrdUserDefinedFailuresOut7Total OBJECT-TYPE
       SYNTAX Counter64
       MAX-ACCESS read-only
       STATUS current
       DESCRIPTION
           "Total number of outbound user defined failures 7.
AC INI-Param: N/A"
       ::= {acKpiUserDefinedCurrentSrdEntry 15}



     acKpiUserDefinedCurrentSrdUserDefinedFailuresIn8Total OBJECT-TYPE
       SYNTAX Counter64
       MAX-ACCESS read-only
       STATUS current
       DESCRIPTION
           "Total number of inbound user defined failures 8.
AC INI-Param: N/A"
       ::= {acKpiUserDefinedCurrentSrdEntry 16}



     acKpiUserDefinedCurrentSrdUserDefinedFailuresOut8Total OBJECT-TYPE
       SYNTAX Counter64
       MAX-ACCESS read-only
       STATUS current
       DESCRIPTION
           "Total number of outbound user defined failures 8.
AC INI-Param: N/A"
       ::= {acKpiUserDefinedCurrentSrdEntry 17}



     acKpiUserDefinedCurrentSrdUserDefinedFailuresIn9Total OBJECT-TYPE
       SYNTAX Counter64
       MAX-ACCESS read-only
       STATUS current
       DESCRIPTION
           "Total number of inbound user defined failures 9.
AC INI-Param: N/A"
       ::= {acKpiUserDefinedCurrentSrdEntry 18}



     acKpiUserDefinedCurrentSrdUserDefinedFailuresOut9Total OBJECT-TYPE
       SYNTAX Counter64
       MAX-ACCESS read-only
       STATUS current
       DESCRIPTION
           "Total number of outbound user defined failures 9.
AC INI-Param: N/A"
       ::= {acKpiUserDefinedCurrentSrdEntry 19}



     acKpiUserDefinedCurrentSrdUserDefinedFailuresIn10Total OBJECT-TYPE
       SYNTAX Counter64
       MAX-ACCESS read-only
       STATUS current
       DESCRIPTION
           "Total number of inbound user defined failures 10.
AC INI-Param: N/A"
       ::= {acKpiUserDefinedCurrentSrdEntry 20}



     acKpiUserDefinedCurrentSrdUserDefinedFailuresOut10Total OBJECT-TYPE
       SYNTAX Counter64
       MAX-ACCESS read-only
       STATUS current
       DESCRIPTION
           "Total number of outbound user defined failures 10.
AC INI-Param: N/A"
       ::= {acKpiUserDefinedCurrentSrdEntry 21}



     acKpiUserDefinedCurrentSrdUserDefinedFailuresIn11Total OBJECT-TYPE
       SYNTAX Counter64
       MAX-ACCESS read-only
       STATUS current
       DESCRIPTION
           "Total number of inbound user defined failures 11.
AC INI-Param: N/A"
       ::= {acKpiUserDefinedCurrentSrdEntry 22}



     acKpiUserDefinedCurrentSrdUserDefinedFailuresOut11Total OBJECT-TYPE
       SYNTAX Counter64
       MAX-ACCESS read-only
       STATUS current
       DESCRIPTION
           "Total number of outbound user defined failures 11.
AC INI-Param: N/A"
       ::= {acKpiUserDefinedCurrentSrdEntry 23}



     acKpiUserDefinedCurrentSrdUserDefinedFailuresIn12Total OBJECT-TYPE
       SYNTAX Counter64
       MAX-ACCESS read-only
       STATUS current
       DESCRIPTION
           "Total number of inbound user defined failures 12.
AC INI-Param: N/A"
       ::= {acKpiUserDefinedCurrentSrdEntry 24}



     acKpiUserDefinedCurrentSrdUserDefinedFailuresOut12Total OBJECT-TYPE
       SYNTAX Counter64
       MAX-ACCESS read-only
       STATUS current
       DESCRIPTION
           "Total number of outbound user defined failures 12.
AC INI-Param: N/A"
       ::= {acKpiUserDefinedCurrentSrdEntry 25}



     acKpiUserDefinedCurrentSrdUserDefinedFailuresIn13Total OBJECT-TYPE
       SYNTAX Counter64
       MAX-ACCESS read-only
       STATUS current
       DESCRIPTION
           "Total number of inbound user defined failures 13.
AC INI-Param: N/A"
       ::= {acKpiUserDefinedCurrentSrdEntry 26}



     acKpiUserDefinedCurrentSrdUserDefinedFailuresOut13Total OBJECT-TYPE
       SYNTAX Counter64
       MAX-ACCESS read-only
       STATUS current
       DESCRIPTION
           "Total number of outbound user defined failures 13.
AC INI-Param: N/A"
       ::= {acKpiUserDefinedCurrentSrdEntry 27}



     acKpiUserDefinedCurrentSrdUserDefinedFailuresIn14Total OBJECT-TYPE
       SYNTAX Counter64
       MAX-ACCESS read-only
       STATUS current
       DESCRIPTION
           "Total number of inbound user defined failures 14.
AC INI-Param: N/A"
       ::= {acKpiUserDefinedCurrentSrdEntry 28}



     acKpiUserDefinedCurrentSrdUserDefinedFailuresOut14Total OBJECT-TYPE
       SYNTAX Counter64
       MAX-ACCESS read-only
       STATUS current
       DESCRIPTION
           "Total number of outbound user defined failures 14.
AC INI-Param: N/A"
       ::= {acKpiUserDefinedCurrentSrdEntry 29}



     acKpiUserDefinedCurrentSrdUserDefinedFailuresIn15Total OBJECT-TYPE
       SYNTAX Counter64
       MAX-ACCESS read-only
       STATUS current
       DESCRIPTION
           "Total number of inbound user defined failures 15.
AC INI-Param: N/A"
       ::= {acKpiUserDefinedCurrentSrdEntry 30}



     acKpiUserDefinedCurrentSrdUserDefinedFailuresOut15Total OBJECT-TYPE
       SYNTAX Counter64
       MAX-ACCESS read-only
       STATUS current
       DESCRIPTION
           "Total number of outbound user defined failures 15.
AC INI-Param: N/A"
       ::= {acKpiUserDefinedCurrentSrdEntry 31}



     acKpiUserDefinedCurrentSrdUserDefinedFailuresIn16Total OBJECT-TYPE
       SYNTAX Counter64
       MAX-ACCESS read-only
       STATUS current
       DESCRIPTION
           "Total number of inbound user defined failures 16.
AC INI-Param: N/A"
       ::= {acKpiUserDefinedCurrentSrdEntry 32}



     acKpiUserDefinedCurrentSrdUserDefinedFailuresOut16Total OBJECT-TYPE
       SYNTAX Counter64
       MAX-ACCESS read-only
       STATUS current
       DESCRIPTION
           "Total number of outbound user defined failures 16.
AC INI-Param: N/A"
       ::= {acKpiUserDefinedCurrentSrdEntry 33}



     acKpiUserDefinedCurrentSrdUserDefinedFailuresIn17Total OBJECT-TYPE
       SYNTAX Counter64
       MAX-ACCESS read-only
       STATUS current
       DESCRIPTION
           "Total number of inbound user defined failures 17.
AC INI-Param: N/A"
       ::= {acKpiUserDefinedCurrentSrdEntry 34}



     acKpiUserDefinedCurrentSrdUserDefinedFailuresOut17Total OBJECT-TYPE
       SYNTAX Counter64
       MAX-ACCESS read-only
       STATUS current
       DESCRIPTION
           "Total number of outbound user defined failures 17.
AC INI-Param: N/A"
       ::= {acKpiUserDefinedCurrentSrdEntry 35}



     acKpiUserDefinedCurrentSrdUserDefinedFailuresIn18Total OBJECT-TYPE
       SYNTAX Counter64
       MAX-ACCESS read-only
       STATUS current
       DESCRIPTION
           "Total number of inbound user defined failures 18.
AC INI-Param: N/A"
       ::= {acKpiUserDefinedCurrentSrdEntry 36}



     acKpiUserDefinedCurrentSrdUserDefinedFailuresOut18Total OBJECT-TYPE
       SYNTAX Counter64
       MAX-ACCESS read-only
       STATUS current
       DESCRIPTION
           "Total number of outbound user defined failures 18.
AC INI-Param: N/A"
       ::= {acKpiUserDefinedCurrentSrdEntry 37}



     acKpiUserDefinedCurrentSrdUserDefinedFailuresIn19Total OBJECT-TYPE
       SYNTAX Counter64
       MAX-ACCESS read-only
       STATUS current
       DESCRIPTION
           "Total number of inbound user defined failures 19.
AC INI-Param: N/A"
       ::= {acKpiUserDefinedCurrentSrdEntry 38}



     acKpiUserDefinedCurrentSrdUserDefinedFailuresOut19Total OBJECT-TYPE
       SYNTAX Counter64
       MAX-ACCESS read-only
       STATUS current
       DESCRIPTION
           "Total number of outbound user defined failures 19.
AC INI-Param: N/A"
       ::= {acKpiUserDefinedCurrentSrdEntry 39}



     acKpiUserDefinedCurrentSrdUserDefinedFailuresIn20Total OBJECT-TYPE
       SYNTAX Counter64
       MAX-ACCESS read-only
       STATUS current
       DESCRIPTION
           "Total number of inbound user defined failures 20.
AC INI-Param: N/A"
       ::= {acKpiUserDefinedCurrentSrdEntry 40}



     acKpiUserDefinedCurrentSrdUserDefinedFailuresOut20Total OBJECT-TYPE
       SYNTAX Counter64
       MAX-ACCESS read-only
       STATUS current
       DESCRIPTION
           "Total number of outbound user defined failures 20.
AC INI-Param: N/A"
       ::= {acKpiUserDefinedCurrentSrdEntry 41}



     acKpiUserDefinedCurrentSrdUserDefinedFailuresIn21Total OBJECT-TYPE
       SYNTAX Counter64
       MAX-ACCESS read-only
       STATUS current
       DESCRIPTION
           "Total number of inbound user defined failures 21.
AC INI-Param: N/A"
       ::= {acKpiUserDefinedCurrentSrdEntry 42}



     acKpiUserDefinedCurrentSrdUserDefinedFailuresOut21Total OBJECT-TYPE
       SYNTAX Counter64
       MAX-ACCESS read-only
       STATUS current
       DESCRIPTION
           "Total number of outbound user defined failures 21.
AC INI-Param: N/A"
       ::= {acKpiUserDefinedCurrentSrdEntry 43}



     acKpiUserDefinedCurrentSrdUserDefinedFailuresIn22Total OBJECT-TYPE
       SYNTAX Counter64
       MAX-ACCESS read-only
       STATUS current
       DESCRIPTION
           "Total number of inbound user defined failures 22.
AC INI-Param: N/A"
       ::= {acKpiUserDefinedCurrentSrdEntry 44}



     acKpiUserDefinedCurrentSrdUserDefinedFailuresOut22Total OBJECT-TYPE
       SYNTAX Counter64
       MAX-ACCESS read-only
       STATUS current
       DESCRIPTION
           "Total number of outbound user defined failures 22.
AC INI-Param: N/A"
       ::= {acKpiUserDefinedCurrentSrdEntry 45}



     acKpiUserDefinedCurrentSrdUserDefinedFailuresIn23Total OBJECT-TYPE
       SYNTAX Counter64
       MAX-ACCESS read-only
       STATUS current
       DESCRIPTION
           "Total number of inbound user defined failures 23.
AC INI-Param: N/A"
       ::= {acKpiUserDefinedCurrentSrdEntry 46}



     acKpiUserDefinedCurrentSrdUserDefinedFailuresOut23Total OBJECT-TYPE
       SYNTAX Counter64
       MAX-ACCESS read-only
       STATUS current
       DESCRIPTION
           "Total number of outbound user defined failures 23.
AC INI-Param: N/A"
       ::= {acKpiUserDefinedCurrentSrdEntry 47}



     acKpiUserDefinedCurrentSrdUserDefinedFailuresIn24Total OBJECT-TYPE
       SYNTAX Counter64
       MAX-ACCESS read-only
       STATUS current
       DESCRIPTION
           "Total number of inbound user defined failures 24.
AC INI-Param: N/A"
       ::= {acKpiUserDefinedCurrentSrdEntry 48}



     acKpiUserDefinedCurrentSrdUserDefinedFailuresOut24Total OBJECT-TYPE
       SYNTAX Counter64
       MAX-ACCESS read-only
       STATUS current
       DESCRIPTION
           "Total number of outbound user defined failures 24.
AC INI-Param: N/A"
       ::= {acKpiUserDefinedCurrentSrdEntry 49}



     acKpiUserDefinedCurrentSrdUserDefinedFailuresIn25Total OBJECT-TYPE
       SYNTAX Counter64
       MAX-ACCESS read-only
       STATUS current
       DESCRIPTION
           "Total number of inbound user defined failures 25.
AC INI-Param: N/A"
       ::= {acKpiUserDefinedCurrentSrdEntry 50}



     acKpiUserDefinedCurrentSrdUserDefinedFailuresOut25Total OBJECT-TYPE
       SYNTAX Counter64
       MAX-ACCESS read-only
       STATUS current
       DESCRIPTION
           "Total number of outbound user defined failures 25.
AC INI-Param: N/A"
       ::= {acKpiUserDefinedCurrentSrdEntry 51}



     acKpiUserDefinedCurrentSrdUserDefinedFailuresIn26Total OBJECT-TYPE
       SYNTAX Counter64
       MAX-ACCESS read-only
       STATUS current
       DESCRIPTION
           "Total number of inbound user defined failures 26.
AC INI-Param: N/A"
       ::= {acKpiUserDefinedCurrentSrdEntry 52}



     acKpiUserDefinedCurrentSrdUserDefinedFailuresOut26Total OBJECT-TYPE
       SYNTAX Counter64
       MAX-ACCESS read-only
       STATUS current
       DESCRIPTION
           "Total number of outbound user defined failures 26.
AC INI-Param: N/A"
       ::= {acKpiUserDefinedCurrentSrdEntry 53}



     acKpiUserDefinedInterval OBJECT IDENTIFIER ::= {acKpiUserDefined 2}


     acKpiUserDefinedIntervalGlobal OBJECT IDENTIFIER ::= {acKpiUserDefinedInterval 1}


     -- ****************************************
     -- acKpiUserDefinedIntervalGlobal table declaration
     -- ****************************************
     acKpiUserDefinedIntervalGlobalTable OBJECT-TYPE
       SYNTAX SEQUENCE OF AcKpiUserDefinedIntervalGlobalEntry
       MAX-ACCESS not-accessible
       STATUS current
       DESCRIPTION
           ""
       ::= {acKpiUserDefinedIntervalGlobal 1}



     -- ****************************************
     -- acKpiUserDefinedIntervalGlobal table entry
     -- ****************************************
     acKpiUserDefinedIntervalGlobalEntry OBJECT-TYPE
       SYNTAX AcKpiUserDefinedIntervalGlobalEntry
       MAX-ACCESS not-accessible
       STATUS current
       DESCRIPTION
           ""
       INDEX {acKpiUserDefinedIntervalGlobalInterval}
       ::= {acKpiUserDefinedIntervalGlobalTable 1}



     -- ****************************************
     -- acKpiUserDefinedIntervalGlobal TABLE
     -- ****************************************
     AcKpiUserDefinedIntervalGlobalEntry ::= SEQUENCE {
       acKpiUserDefinedIntervalGlobalInterval          Unsigned32,
       acKpiUserDefinedIntervalGlobalUserDefinedFailuresIn1 
                                                       Counter64,
       acKpiUserDefinedIntervalGlobalUserDefinedFailuresOut1 
                                                       Counter64,
       acKpiUserDefinedIntervalGlobalUserDefinedFailuresIn2 
                                                       Counter64,
       acKpiUserDefinedIntervalGlobalUserDefinedFailuresOut2 
                                                       Counter64,
       acKpiUserDefinedIntervalGlobalUserDefinedFailuresIn3 
                                                       Counter64,
       acKpiUserDefinedIntervalGlobalUserDefinedFailuresOut3 
                                                       Counter64,
       acKpiUserDefinedIntervalGlobalUserDefinedFailuresIn4 
                                                       Counter64,
       acKpiUserDefinedIntervalGlobalUserDefinedFailuresOut4 
                                                       Counter64,
       acKpiUserDefinedIntervalGlobalUserDefinedFailuresIn5 
                                                       Counter64,
       acKpiUserDefinedIntervalGlobalUserDefinedFailuresOut5 
                                                       Counter64,
       acKpiUserDefinedIntervalGlobalUserDefinedFailuresIn6 
                                                       Counter64,
       acKpiUserDefinedIntervalGlobalUserDefinedFailuresOut6 
                                                       Counter64,
       acKpiUserDefinedIntervalGlobalUserDefinedFailuresIn7 
                                                       Counter64,
       acKpiUserDefinedIntervalGlobalUserDefinedFailuresOut7 
                                                       Counter64,
       acKpiUserDefinedIntervalGlobalUserDefinedFailuresIn8 
                                                       Counter64,
       acKpiUserDefinedIntervalGlobalUserDefinedFailuresOut8 
                                                       Counter64,
       acKpiUserDefinedIntervalGlobalUserDefinedFailuresIn9 
                                                       Counter64,
       acKpiUserDefinedIntervalGlobalUserDefinedFailuresOut9 
                                                       Counter64,
       acKpiUserDefinedIntervalGlobalUserDefinedFailuresIn10 
                                                       Counter64,
       acKpiUserDefinedIntervalGlobalUserDefinedFailuresOut10 
                                                       Counter64,
       acKpiUserDefinedIntervalGlobalUserDefinedFailuresIn11 
                                                       Counter64,
       acKpiUserDefinedIntervalGlobalUserDefinedFailuresOut11 
                                                       Counter64,
       acKpiUserDefinedIntervalGlobalUserDefinedFailuresIn12 
                                                       Counter64,
       acKpiUserDefinedIntervalGlobalUserDefinedFailuresOut12 
                                                       Counter64,
       acKpiUserDefinedIntervalGlobalUserDefinedFailuresIn13 
                                                       Counter64,
       acKpiUserDefinedIntervalGlobalUserDefinedFailuresOut13 
                                                       Counter64,
       acKpiUserDefinedIntervalGlobalUserDefinedFailuresIn14 
                                                       Counter64,
       acKpiUserDefinedIntervalGlobalUserDefinedFailuresOut14 
                                                       Counter64,
       acKpiUserDefinedIntervalGlobalUserDefinedFailuresIn15 
                                                       Counter64,
       acKpiUserDefinedIntervalGlobalUserDefinedFailuresOut15 
                                                       Counter64,
       acKpiUserDefinedIntervalGlobalUserDefinedFailuresIn16 
                                                       Counter64,
       acKpiUserDefinedIntervalGlobalUserDefinedFailuresOut16 
                                                       Counter64,
       acKpiUserDefinedIntervalGlobalUserDefinedFailuresIn17 
                                                       Counter64,
       acKpiUserDefinedIntervalGlobalUserDefinedFailuresOut17 
                                                       Counter64,
       acKpiUserDefinedIntervalGlobalUserDefinedFailuresIn18 
                                                       Counter64,
       acKpiUserDefinedIntervalGlobalUserDefinedFailuresOut18 
                                                       Counter64,
       acKpiUserDefinedIntervalGlobalUserDefinedFailuresIn19 
                                                       Counter64,
       acKpiUserDefinedIntervalGlobalUserDefinedFailuresOut19 
                                                       Counter64,
       acKpiUserDefinedIntervalGlobalUserDefinedFailuresIn20 
                                                       Counter64,
       acKpiUserDefinedIntervalGlobalUserDefinedFailuresOut20 
                                                       Counter64,
       acKpiUserDefinedIntervalGlobalUserDefinedFailuresIn21 
                                                       Counter64,
       acKpiUserDefinedIntervalGlobalUserDefinedFailuresOut21 
                                                       Counter64,
       acKpiUserDefinedIntervalGlobalUserDefinedFailuresIn22 
                                                       Counter64,
       acKpiUserDefinedIntervalGlobalUserDefinedFailuresOut22 
                                                       Counter64,
       acKpiUserDefinedIntervalGlobalUserDefinedFailuresIn23 
                                                       Counter64,
       acKpiUserDefinedIntervalGlobalUserDefinedFailuresOut23 
                                                       Counter64,
       acKpiUserDefinedIntervalGlobalUserDefinedFailuresIn24 
                                                       Counter64,
       acKpiUserDefinedIntervalGlobalUserDefinedFailuresOut24 
                                                       Counter64,
       acKpiUserDefinedIntervalGlobalUserDefinedFailuresIn25 
                                                       Counter64,
       acKpiUserDefinedIntervalGlobalUserDefinedFailuresOut25 
                                                       Counter64,
       acKpiUserDefinedIntervalGlobalUserDefinedFailuresIn26 
                                                       Counter64,
       acKpiUserDefinedIntervalGlobalUserDefinedFailuresOut26 
                                                       Counter64
     }



     acKpiUserDefinedIntervalGlobalInterval OBJECT-TYPE
       SYNTAX Unsigned32 (1..200)
       MAX-ACCESS not-accessible
       STATUS current
       DESCRIPTION
           "
AC INI-Param: N/A"
       ::= {acKpiUserDefinedIntervalGlobalEntry 1}



     acKpiUserDefinedIntervalGlobalUserDefinedFailuresIn1 OBJECT-TYPE
       SYNTAX Counter64
       MAX-ACCESS read-only
       STATUS current
       DESCRIPTION
           "Number of inbound user defined failures 1.
AC INI-Param: N/A"
       ::= {acKpiUserDefinedIntervalGlobalEntry 2}



     acKpiUserDefinedIntervalGlobalUserDefinedFailuresOut1 OBJECT-TYPE
       SYNTAX Counter64
       MAX-ACCESS read-only
       STATUS current
       DESCRIPTION
           "Number of outbound user defined failures 1.
AC INI-Param: N/A"
       ::= {acKpiUserDefinedIntervalGlobalEntry 3}



     acKpiUserDefinedIntervalGlobalUserDefinedFailuresIn2 OBJECT-TYPE
       SYNTAX Counter64
       MAX-ACCESS read-only
       STATUS current
       DESCRIPTION
           "Number of inbound user defined failures 2.
AC INI-Param: N/A"
       ::= {acKpiUserDefinedIntervalGlobalEntry 4}



     acKpiUserDefinedIntervalGlobalUserDefinedFailuresOut2 OBJECT-TYPE
       SYNTAX Counter64
       MAX-ACCESS read-only
       STATUS current
       DESCRIPTION
           "Number of outbound user defined failures 2.
AC INI-Param: N/A"
       ::= {acKpiUserDefinedIntervalGlobalEntry 5}



     acKpiUserDefinedIntervalGlobalUserDefinedFailuresIn3 OBJECT-TYPE
       SYNTAX Counter64
       MAX-ACCESS read-only
       STATUS current
       DESCRIPTION
           "Number of inbound user defined failures 3.
AC INI-Param: N/A"
       ::= {acKpiUserDefinedIntervalGlobalEntry 6}



     acKpiUserDefinedIntervalGlobalUserDefinedFailuresOut3 OBJECT-TYPE
       SYNTAX Counter64
       MAX-ACCESS read-only
       STATUS current
       DESCRIPTION
           "Number of outbound user defined failures 3.
AC INI-Param: N/A"
       ::= {acKpiUserDefinedIntervalGlobalEntry 7}



     acKpiUserDefinedIntervalGlobalUserDefinedFailuresIn4 OBJECT-TYPE
       SYNTAX Counter64
       MAX-ACCESS read-only
       STATUS current
       DESCRIPTION
           "Number of inbound user defined failures 4.
AC INI-Param: N/A"
       ::= {acKpiUserDefinedIntervalGlobalEntry 8}



     acKpiUserDefinedIntervalGlobalUserDefinedFailuresOut4 OBJECT-TYPE
       SYNTAX Counter64
       MAX-ACCESS read-only
       STATUS current
       DESCRIPTION
           "Number of outbound user defined failures 4.
AC INI-Param: N/A"
       ::= {acKpiUserDefinedIntervalGlobalEntry 9}



     acKpiUserDefinedIntervalGlobalUserDefinedFailuresIn5 OBJECT-TYPE
       SYNTAX Counter64
       MAX-ACCESS read-only
       STATUS current
       DESCRIPTION
           "Number of inbound user defined failures 5.
AC INI-Param: N/A"
       ::= {acKpiUserDefinedIntervalGlobalEntry 10}



     acKpiUserDefinedIntervalGlobalUserDefinedFailuresOut5 OBJECT-TYPE
       SYNTAX Counter64
       MAX-ACCESS read-only
       STATUS current
       DESCRIPTION
           "Number of outbound user defined failures 5.
AC INI-Param: N/A"
       ::= {acKpiUserDefinedIntervalGlobalEntry 11}



     acKpiUserDefinedIntervalGlobalUserDefinedFailuresIn6 OBJECT-TYPE
       SYNTAX Counter64
       MAX-ACCESS read-only
       STATUS current
       DESCRIPTION
           "Number of inbound user defined failures 6.
AC INI-Param: N/A"
       ::= {acKpiUserDefinedIntervalGlobalEntry 12}



     acKpiUserDefinedIntervalGlobalUserDefinedFailuresOut6 OBJECT-TYPE
       SYNTAX Counter64
       MAX-ACCESS read-only
       STATUS current
       DESCRIPTION
           "Number of outbound user defined failures 6.
AC INI-Param: N/A"
       ::= {acKpiUserDefinedIntervalGlobalEntry 13}



     acKpiUserDefinedIntervalGlobalUserDefinedFailuresIn7 OBJECT-TYPE
       SYNTAX Counter64
       MAX-ACCESS read-only
       STATUS current
       DESCRIPTION
           "Number of inbound user defined failures 7.
AC INI-Param: N/A"
       ::= {acKpiUserDefinedIntervalGlobalEntry 14}



     acKpiUserDefinedIntervalGlobalUserDefinedFailuresOut7 OBJECT-TYPE
       SYNTAX Counter64
       MAX-ACCESS read-only
       STATUS current
       DESCRIPTION
           "Number of outbound user defined failures 7.
AC INI-Param: N/A"
       ::= {acKpiUserDefinedIntervalGlobalEntry 15}



     acKpiUserDefinedIntervalGlobalUserDefinedFailuresIn8 OBJECT-TYPE
       SYNTAX Counter64
       MAX-ACCESS read-only
       STATUS current
       DESCRIPTION
           "Number of inbound user defined failures 8.
AC INI-Param: N/A"
       ::= {acKpiUserDefinedIntervalGlobalEntry 16}



     acKpiUserDefinedIntervalGlobalUserDefinedFailuresOut8 OBJECT-TYPE
       SYNTAX Counter64
       MAX-ACCESS read-only
       STATUS current
       DESCRIPTION
           "Number of outbound user defined failures 8.
AC INI-Param: N/A"
       ::= {acKpiUserDefinedIntervalGlobalEntry 17}



     acKpiUserDefinedIntervalGlobalUserDefinedFailuresIn9 OBJECT-TYPE
       SYNTAX Counter64
       MAX-ACCESS read-only
       STATUS current
       DESCRIPTION
           "Number of inbound user defined failures 9.
AC INI-Param: N/A"
       ::= {acKpiUserDefinedIntervalGlobalEntry 18}



     acKpiUserDefinedIntervalGlobalUserDefinedFailuresOut9 OBJECT-TYPE
       SYNTAX Counter64
       MAX-ACCESS read-only
       STATUS current
       DESCRIPTION
           "Number of outbound user defined failures 9.
AC INI-Param: N/A"
       ::= {acKpiUserDefinedIntervalGlobalEntry 19}



     acKpiUserDefinedIntervalGlobalUserDefinedFailuresIn10 OBJECT-TYPE
       SYNTAX Counter64
       MAX-ACCESS read-only
       STATUS current
       DESCRIPTION
           "Number of inbound user defined failures 10.
AC INI-Param: N/A"
       ::= {acKpiUserDefinedIntervalGlobalEntry 20}



     acKpiUserDefinedIntervalGlobalUserDefinedFailuresOut10 OBJECT-TYPE
       SYNTAX Counter64
       MAX-ACCESS read-only
       STATUS current
       DESCRIPTION
           "Number of outbound user defined failures 10.
AC INI-Param: N/A"
       ::= {acKpiUserDefinedIntervalGlobalEntry 21}



     acKpiUserDefinedIntervalGlobalUserDefinedFailuresIn11 OBJECT-TYPE
       SYNTAX Counter64
       MAX-ACCESS read-only
       STATUS current
       DESCRIPTION
           "Number of inbound user defined failures 11.
AC INI-Param: N/A"
       ::= {acKpiUserDefinedIntervalGlobalEntry 22}



     acKpiUserDefinedIntervalGlobalUserDefinedFailuresOut11 OBJECT-TYPE
       SYNTAX Counter64
       MAX-ACCESS read-only
       STATUS current
       DESCRIPTION
           "Number of outbound user defined failures 11.
AC INI-Param: N/A"
       ::= {acKpiUserDefinedIntervalGlobalEntry 23}



     acKpiUserDefinedIntervalGlobalUserDefinedFailuresIn12 OBJECT-TYPE
       SYNTAX Counter64
       MAX-ACCESS read-only
       STATUS current
       DESCRIPTION
           "Number of inbound user defined failures 12.
AC INI-Param: N/A"
       ::= {acKpiUserDefinedIntervalGlobalEntry 24}



     acKpiUserDefinedIntervalGlobalUserDefinedFailuresOut12 OBJECT-TYPE
       SYNTAX Counter64
       MAX-ACCESS read-only
       STATUS current
       DESCRIPTION
           "Number of outbound user defined failures 12.
AC INI-Param: N/A"
       ::= {acKpiUserDefinedIntervalGlobalEntry 25}



     acKpiUserDefinedIntervalGlobalUserDefinedFailuresIn13 OBJECT-TYPE
       SYNTAX Counter64
       MAX-ACCESS read-only
       STATUS current
       DESCRIPTION
           "Number of inbound user defined failures 13.
AC INI-Param: N/A"
       ::= {acKpiUserDefinedIntervalGlobalEntry 26}



     acKpiUserDefinedIntervalGlobalUserDefinedFailuresOut13 OBJECT-TYPE
       SYNTAX Counter64
       MAX-ACCESS read-only
       STATUS current
       DESCRIPTION
           "Number of outbound user defined failures 13.
AC INI-Param: N/A"
       ::= {acKpiUserDefinedIntervalGlobalEntry 27}



     acKpiUserDefinedIntervalGlobalUserDefinedFailuresIn14 OBJECT-TYPE
       SYNTAX Counter64
       MAX-ACCESS read-only
       STATUS current
       DESCRIPTION
           "Number of inbound user defined failures 14.
AC INI-Param: N/A"
       ::= {acKpiUserDefinedIntervalGlobalEntry 28}



     acKpiUserDefinedIntervalGlobalUserDefinedFailuresOut14 OBJECT-TYPE
       SYNTAX Counter64
       MAX-ACCESS read-only
       STATUS current
       DESCRIPTION
           "Number of outbound user defined failures 14.
AC INI-Param: N/A"
       ::= {acKpiUserDefinedIntervalGlobalEntry 29}



     acKpiUserDefinedIntervalGlobalUserDefinedFailuresIn15 OBJECT-TYPE
       SYNTAX Counter64
       MAX-ACCESS read-only
       STATUS current
       DESCRIPTION
           "Number of inbound user defined failures 15.
AC INI-Param: N/A"
       ::= {acKpiUserDefinedIntervalGlobalEntry 30}



     acKpiUserDefinedIntervalGlobalUserDefinedFailuresOut15 OBJECT-TYPE
       SYNTAX Counter64
       MAX-ACCESS read-only
       STATUS current
       DESCRIPTION
           "Number of outbound user defined failures 15.
AC INI-Param: N/A"
       ::= {acKpiUserDefinedIntervalGlobalEntry 31}



     acKpiUserDefinedIntervalGlobalUserDefinedFailuresIn16 OBJECT-TYPE
       SYNTAX Counter64
       MAX-ACCESS read-only
       STATUS current
       DESCRIPTION
           "Number of inbound user defined failures 16.
AC INI-Param: N/A"
       ::= {acKpiUserDefinedIntervalGlobalEntry 32}



     acKpiUserDefinedIntervalGlobalUserDefinedFailuresOut16 OBJECT-TYPE
       SYNTAX Counter64
       MAX-ACCESS read-only
       STATUS current
       DESCRIPTION
           "Number of outbound user defined failures 16.
AC INI-Param: N/A"
       ::= {acKpiUserDefinedIntervalGlobalEntry 33}



     acKpiUserDefinedIntervalGlobalUserDefinedFailuresIn17 OBJECT-TYPE
       SYNTAX Counter64
       MAX-ACCESS read-only
       STATUS current
       DESCRIPTION
           "Number of inbound user defined failures 17.
AC INI-Param: N/A"
       ::= {acKpiUserDefinedIntervalGlobalEntry 34}



     acKpiUserDefinedIntervalGlobalUserDefinedFailuresOut17 OBJECT-TYPE
       SYNTAX Counter64
       MAX-ACCESS read-only
       STATUS current
       DESCRIPTION
           "Number of outbound user defined failures 17.
AC INI-Param: N/A"
       ::= {acKpiUserDefinedIntervalGlobalEntry 35}



     acKpiUserDefinedIntervalGlobalUserDefinedFailuresIn18 OBJECT-TYPE
       SYNTAX Counter64
       MAX-ACCESS read-only
       STATUS current
       DESCRIPTION
           "Number of inbound user defined failures 18.
AC INI-Param: N/A"
       ::= {acKpiUserDefinedIntervalGlobalEntry 36}



     acKpiUserDefinedIntervalGlobalUserDefinedFailuresOut18 OBJECT-TYPE
       SYNTAX Counter64
       MAX-ACCESS read-only
       STATUS current
       DESCRIPTION
           "Number of outbound user defined failures 18.
AC INI-Param: N/A"
       ::= {acKpiUserDefinedIntervalGlobalEntry 37}



     acKpiUserDefinedIntervalGlobalUserDefinedFailuresIn19 OBJECT-TYPE
       SYNTAX Counter64
       MAX-ACCESS read-only
       STATUS current
       DESCRIPTION
           "Number of inbound user defined failures 19.
AC INI-Param: N/A"
       ::= {acKpiUserDefinedIntervalGlobalEntry 38}



     acKpiUserDefinedIntervalGlobalUserDefinedFailuresOut19 OBJECT-TYPE
       SYNTAX Counter64
       MAX-ACCESS read-only
       STATUS current
       DESCRIPTION
           "Number of outbound user defined failures 19.
AC INI-Param: N/A"
       ::= {acKpiUserDefinedIntervalGlobalEntry 39}



     acKpiUserDefinedIntervalGlobalUserDefinedFailuresIn20 OBJECT-TYPE
       SYNTAX Counter64
       MAX-ACCESS read-only
       STATUS current
       DESCRIPTION
           "Number of inbound user defined failures 20.
AC INI-Param: N/A"
       ::= {acKpiUserDefinedIntervalGlobalEntry 40}



     acKpiUserDefinedIntervalGlobalUserDefinedFailuresOut20 OBJECT-TYPE
       SYNTAX Counter64
       MAX-ACCESS read-only
       STATUS current
       DESCRIPTION
           "Number of outbound user defined failures 20.
AC INI-Param: N/A"
       ::= {acKpiUserDefinedIntervalGlobalEntry 41}



     acKpiUserDefinedIntervalGlobalUserDefinedFailuresIn21 OBJECT-TYPE
       SYNTAX Counter64
       MAX-ACCESS read-only
       STATUS current
       DESCRIPTION
           "Number of inbound user defined failures 21.
AC INI-Param: N/A"
       ::= {acKpiUserDefinedIntervalGlobalEntry 42}



     acKpiUserDefinedIntervalGlobalUserDefinedFailuresOut21 OBJECT-TYPE
       SYNTAX Counter64
       MAX-ACCESS read-only
       STATUS current
       DESCRIPTION
           "Number of outbound user defined failures 21.
AC INI-Param: N/A"
       ::= {acKpiUserDefinedIntervalGlobalEntry 43}



     acKpiUserDefinedIntervalGlobalUserDefinedFailuresIn22 OBJECT-TYPE
       SYNTAX Counter64
       MAX-ACCESS read-only
       STATUS current
       DESCRIPTION
           "Number of inbound user defined failures 22.
AC INI-Param: N/A"
       ::= {acKpiUserDefinedIntervalGlobalEntry 44}



     acKpiUserDefinedIntervalGlobalUserDefinedFailuresOut22 OBJECT-TYPE
       SYNTAX Counter64
       MAX-ACCESS read-only
       STATUS current
       DESCRIPTION
           "Number of outbound user defined failures 22.
AC INI-Param: N/A"
       ::= {acKpiUserDefinedIntervalGlobalEntry 45}



     acKpiUserDefinedIntervalGlobalUserDefinedFailuresIn23 OBJECT-TYPE
       SYNTAX Counter64
       MAX-ACCESS read-only
       STATUS current
       DESCRIPTION
           "Number of inbound user defined failures 23.
AC INI-Param: N/A"
       ::= {acKpiUserDefinedIntervalGlobalEntry 46}



     acKpiUserDefinedIntervalGlobalUserDefinedFailuresOut23 OBJECT-TYPE
       SYNTAX Counter64
       MAX-ACCESS read-only
       STATUS current
       DESCRIPTION
           "Number of outbound user defined failures 23.
AC INI-Param: N/A"
       ::= {acKpiUserDefinedIntervalGlobalEntry 47}



     acKpiUserDefinedIntervalGlobalUserDefinedFailuresIn24 OBJECT-TYPE
       SYNTAX Counter64
       MAX-ACCESS read-only
       STATUS current
       DESCRIPTION
           "Number of inbound user defined failures 24.
AC INI-Param: N/A"
       ::= {acKpiUserDefinedIntervalGlobalEntry 48}



     acKpiUserDefinedIntervalGlobalUserDefinedFailuresOut24 OBJECT-TYPE
       SYNTAX Counter64
       MAX-ACCESS read-only
       STATUS current
       DESCRIPTION
           "Number of outbound user defined failures 24.
AC INI-Param: N/A"
       ::= {acKpiUserDefinedIntervalGlobalEntry 49}



     acKpiUserDefinedIntervalGlobalUserDefinedFailuresIn25 OBJECT-TYPE
       SYNTAX Counter64
       MAX-ACCESS read-only
       STATUS current
       DESCRIPTION
           "Number of inbound user defined failures 25.
AC INI-Param: N/A"
       ::= {acKpiUserDefinedIntervalGlobalEntry 50}



     acKpiUserDefinedIntervalGlobalUserDefinedFailuresOut25 OBJECT-TYPE
       SYNTAX Counter64
       MAX-ACCESS read-only
       STATUS current
       DESCRIPTION
           "Number of outbound user defined failures 25.
AC INI-Param: N/A"
       ::= {acKpiUserDefinedIntervalGlobalEntry 51}



     acKpiUserDefinedIntervalGlobalUserDefinedFailuresIn26 OBJECT-TYPE
       SYNTAX Counter64
       MAX-ACCESS read-only
       STATUS current
       DESCRIPTION
           "Number of inbound user defined failures 26.
AC INI-Param: N/A"
       ::= {acKpiUserDefinedIntervalGlobalEntry 52}



     acKpiUserDefinedIntervalGlobalUserDefinedFailuresOut26 OBJECT-TYPE
       SYNTAX Counter64
       MAX-ACCESS read-only
       STATUS current
       DESCRIPTION
           "Number of outbound user defined failures 26.
AC INI-Param: N/A"
       ::= {acKpiUserDefinedIntervalGlobalEntry 53}



     acKpiUserDefinedIntervalTables OBJECT IDENTIFIER ::= {acKpiUserDefinedInterval 2}


     -- ****************************************
     -- acKpiUserDefinedIntervalIpGroup table declaration
     -- ****************************************
     acKpiUserDefinedIntervalIpGroupTable OBJECT-TYPE
       SYNTAX SEQUENCE OF AcKpiUserDefinedIntervalIpGroupEntry
       MAX-ACCESS not-accessible
       STATUS current
       DESCRIPTION
           ""
       ::= {acKpiUserDefinedIntervalTables 1}



     -- ****************************************
     -- acKpiUserDefinedIntervalIpGroup table entry
     -- ****************************************
     acKpiUserDefinedIntervalIpGroupEntry OBJECT-TYPE
       SYNTAX AcKpiUserDefinedIntervalIpGroupEntry
       MAX-ACCESS not-accessible
       STATUS current
       DESCRIPTION
           ""
       INDEX {acKpiUserDefinedIntervalIpGroupIndex,acKpiUserDefinedIntervalIpGroupInterval}
       ::= {acKpiUserDefinedIntervalIpGroupTable 1}



     -- ****************************************
     -- acKpiUserDefinedIntervalIpGroup TABLE
     -- ****************************************
     AcKpiUserDefinedIntervalIpGroupEntry ::= SEQUENCE {
       acKpiUserDefinedIntervalIpGroupIndex            Unsigned32,
       acKpiUserDefinedIntervalIpGroupInterval         Unsigned32,
       acKpiUserDefinedIntervalIpGroupUserDefinedFailuresIn1 
                                                       Counter64,
       acKpiUserDefinedIntervalIpGroupUserDefinedFailuresOut1 
                                                       Counter64,
       acKpiUserDefinedIntervalIpGroupUserDefinedFailuresIn2 
                                                       Counter64,
       acKpiUserDefinedIntervalIpGroupUserDefinedFailuresOut2 
                                                       Counter64,
       acKpiUserDefinedIntervalIpGroupUserDefinedFailuresIn3 
                                                       Counter64,
       acKpiUserDefinedIntervalIpGroupUserDefinedFailuresOut3 
                                                       Counter64,
       acKpiUserDefinedIntervalIpGroupUserDefinedFailuresIn4 
                                                       Counter64,
       acKpiUserDefinedIntervalIpGroupUserDefinedFailuresOut4 
                                                       Counter64,
       acKpiUserDefinedIntervalIpGroupUserDefinedFailuresIn5 
                                                       Counter64,
       acKpiUserDefinedIntervalIpGroupUserDefinedFailuresOut5 
                                                       Counter64,
       acKpiUserDefinedIntervalIpGroupUserDefinedFailuresIn6 
                                                       Counter64,
       acKpiUserDefinedIntervalIpGroupUserDefinedFailuresOut6 
                                                       Counter64,
       acKpiUserDefinedIntervalIpGroupUserDefinedFailuresIn7 
                                                       Counter64,
       acKpiUserDefinedIntervalIpGroupUserDefinedFailuresOut7 
                                                       Counter64,
       acKpiUserDefinedIntervalIpGroupUserDefinedFailuresIn8 
                                                       Counter64,
       acKpiUserDefinedIntervalIpGroupUserDefinedFailuresOut8 
                                                       Counter64,
       acKpiUserDefinedIntervalIpGroupUserDefinedFailuresIn9 
                                                       Counter64,
       acKpiUserDefinedIntervalIpGroupUserDefinedFailuresOut9 
                                                       Counter64,
       acKpiUserDefinedIntervalIpGroupUserDefinedFailuresIn10 
                                                       Counter64,
       acKpiUserDefinedIntervalIpGroupUserDefinedFailuresOut10 
                                                       Counter64,
       acKpiUserDefinedIntervalIpGroupUserDefinedFailuresIn11 
                                                       Counter64,
       acKpiUserDefinedIntervalIpGroupUserDefinedFailuresOut11 
                                                       Counter64,
       acKpiUserDefinedIntervalIpGroupUserDefinedFailuresIn12 
                                                       Counter64,
       acKpiUserDefinedIntervalIpGroupUserDefinedFailuresOut12 
                                                       Counter64,
       acKpiUserDefinedIntervalIpGroupUserDefinedFailuresIn13 
                                                       Counter64,
       acKpiUserDefinedIntervalIpGroupUserDefinedFailuresOut13 
                                                       Counter64,
       acKpiUserDefinedIntervalIpGroupUserDefinedFailuresIn14 
                                                       Counter64,
       acKpiUserDefinedIntervalIpGroupUserDefinedFailuresOut14 
                                                       Counter64,
       acKpiUserDefinedIntervalIpGroupUserDefinedFailuresIn15 
                                                       Counter64,
       acKpiUserDefinedIntervalIpGroupUserDefinedFailuresOut15 
                                                       Counter64,
       acKpiUserDefinedIntervalIpGroupUserDefinedFailuresIn16 
                                                       Counter64,
       acKpiUserDefinedIntervalIpGroupUserDefinedFailuresOut16 
                                                       Counter64,
       acKpiUserDefinedIntervalIpGroupUserDefinedFailuresIn17 
                                                       Counter64,
       acKpiUserDefinedIntervalIpGroupUserDefinedFailuresOut17 
                                                       Counter64,
       acKpiUserDefinedIntervalIpGroupUserDefinedFailuresIn18 
                                                       Counter64,
       acKpiUserDefinedIntervalIpGroupUserDefinedFailuresOut18 
                                                       Counter64,
       acKpiUserDefinedIntervalIpGroupUserDefinedFailuresIn19 
                                                       Counter64,
       acKpiUserDefinedIntervalIpGroupUserDefinedFailuresOut19 
                                                       Counter64,
       acKpiUserDefinedIntervalIpGroupUserDefinedFailuresIn20 
                                                       Counter64,
       acKpiUserDefinedIntervalIpGroupUserDefinedFailuresOut20 
                                                       Counter64,
       acKpiUserDefinedIntervalIpGroupUserDefinedFailuresIn21 
                                                       Counter64,
       acKpiUserDefinedIntervalIpGroupUserDefinedFailuresOut21 
                                                       Counter64,
       acKpiUserDefinedIntervalIpGroupUserDefinedFailuresIn22 
                                                       Counter64,
       acKpiUserDefinedIntervalIpGroupUserDefinedFailuresOut22 
                                                       Counter64,
       acKpiUserDefinedIntervalIpGroupUserDefinedFailuresIn23 
                                                       Counter64,
       acKpiUserDefinedIntervalIpGroupUserDefinedFailuresOut23 
                                                       Counter64,
       acKpiUserDefinedIntervalIpGroupUserDefinedFailuresIn24 
                                                       Counter64,
       acKpiUserDefinedIntervalIpGroupUserDefinedFailuresOut24 
                                                       Counter64,
       acKpiUserDefinedIntervalIpGroupUserDefinedFailuresIn25 
                                                       Counter64,
       acKpiUserDefinedIntervalIpGroupUserDefinedFailuresOut25 
                                                       Counter64,
       acKpiUserDefinedIntervalIpGroupUserDefinedFailuresIn26 
                                                       Counter64,
       acKpiUserDefinedIntervalIpGroupUserDefinedFailuresOut26 
                                                       Counter64
     }



     acKpiUserDefinedIntervalIpGroupIndex OBJECT-TYPE
       SYNTAX Unsigned32 (0..32767)
       MAX-ACCESS not-accessible
       STATUS current
       DESCRIPTION
           "
AC INI-Param: N/A"
       ::= {acKpiUserDefinedIntervalIpGroupEntry 1}



     acKpiUserDefinedIntervalIpGroupInterval OBJECT-TYPE
       SYNTAX Unsigned32 (1..200)
       MAX-ACCESS not-accessible
       STATUS current
       DESCRIPTION
           "
AC INI-Param: N/A"
       ::= {acKpiUserDefinedIntervalIpGroupEntry 2}



     acKpiUserDefinedIntervalIpGroupUserDefinedFailuresIn1 OBJECT-TYPE
       SYNTAX Counter64
       MAX-ACCESS read-only
       STATUS current
       DESCRIPTION
           "Number of inbound user defined failures 1.
AC INI-Param: N/A"
       ::= {acKpiUserDefinedIntervalIpGroupEntry 3}



     acKpiUserDefinedIntervalIpGroupUserDefinedFailuresOut1 OBJECT-TYPE
       SYNTAX Counter64
       MAX-ACCESS read-only
       STATUS current
       DESCRIPTION
           "Number of outbound user defined failures 1.
AC INI-Param: N/A"
       ::= {acKpiUserDefinedIntervalIpGroupEntry 4}



     acKpiUserDefinedIntervalIpGroupUserDefinedFailuresIn2 OBJECT-TYPE
       SYNTAX Counter64
       MAX-ACCESS read-only
       STATUS current
       DESCRIPTION
           "Number of inbound user defined failures 2.
AC INI-Param: N/A"
       ::= {acKpiUserDefinedIntervalIpGroupEntry 5}



     acKpiUserDefinedIntervalIpGroupUserDefinedFailuresOut2 OBJECT-TYPE
       SYNTAX Counter64
       MAX-ACCESS read-only
       STATUS current
       DESCRIPTION
           "Number of outbound user defined failures 2.
AC INI-Param: N/A"
       ::= {acKpiUserDefinedIntervalIpGroupEntry 6}



     acKpiUserDefinedIntervalIpGroupUserDefinedFailuresIn3 OBJECT-TYPE
       SYNTAX Counter64
       MAX-ACCESS read-only
       STATUS current
       DESCRIPTION
           "Number of inbound user defined failures 3.
AC INI-Param: N/A"
       ::= {acKpiUserDefinedIntervalIpGroupEntry 7}



     acKpiUserDefinedIntervalIpGroupUserDefinedFailuresOut3 OBJECT-TYPE
       SYNTAX Counter64
       MAX-ACCESS read-only
       STATUS current
       DESCRIPTION
           "Number of outbound user defined failures 3.
AC INI-Param: N/A"
       ::= {acKpiUserDefinedIntervalIpGroupEntry 8}



     acKpiUserDefinedIntervalIpGroupUserDefinedFailuresIn4 OBJECT-TYPE
       SYNTAX Counter64
       MAX-ACCESS read-only
       STATUS current
       DESCRIPTION
           "Number of inbound user defined failures 4.
AC INI-Param: N/A"
       ::= {acKpiUserDefinedIntervalIpGroupEntry 9}



     acKpiUserDefinedIntervalIpGroupUserDefinedFailuresOut4 OBJECT-TYPE
       SYNTAX Counter64
       MAX-ACCESS read-only
       STATUS current
       DESCRIPTION
           "Number of outbound user defined failures 4.
AC INI-Param: N/A"
       ::= {acKpiUserDefinedIntervalIpGroupEntry 10}



     acKpiUserDefinedIntervalIpGroupUserDefinedFailuresIn5 OBJECT-TYPE
       SYNTAX Counter64
       MAX-ACCESS read-only
       STATUS current
       DESCRIPTION
           "Number of inbound user defined failures 5.
AC INI-Param: N/A"
       ::= {acKpiUserDefinedIntervalIpGroupEntry 11}



     acKpiUserDefinedIntervalIpGroupUserDefinedFailuresOut5 OBJECT-TYPE
       SYNTAX Counter64
       MAX-ACCESS read-only
       STATUS current
       DESCRIPTION
           "Number of outbound user defined failures 5.
AC INI-Param: N/A"
       ::= {acKpiUserDefinedIntervalIpGroupEntry 12}



     acKpiUserDefinedIntervalIpGroupUserDefinedFailuresIn6 OBJECT-TYPE
       SYNTAX Counter64
       MAX-ACCESS read-only
       STATUS current
       DESCRIPTION
           "Number of inbound user defined failures 6.
AC INI-Param: N/A"
       ::= {acKpiUserDefinedIntervalIpGroupEntry 13}



     acKpiUserDefinedIntervalIpGroupUserDefinedFailuresOut6 OBJECT-TYPE
       SYNTAX Counter64
       MAX-ACCESS read-only
       STATUS current
       DESCRIPTION
           "Number of outbound user defined failures 6.
AC INI-Param: N/A"
       ::= {acKpiUserDefinedIntervalIpGroupEntry 14}



     acKpiUserDefinedIntervalIpGroupUserDefinedFailuresIn7 OBJECT-TYPE
       SYNTAX Counter64
       MAX-ACCESS read-only
       STATUS current
       DESCRIPTION
           "Number of inbound user defined failures 7.
AC INI-Param: N/A"
       ::= {acKpiUserDefinedIntervalIpGroupEntry 15}



     acKpiUserDefinedIntervalIpGroupUserDefinedFailuresOut7 OBJECT-TYPE
       SYNTAX Counter64
       MAX-ACCESS read-only
       STATUS current
       DESCRIPTION
           "Number of outbound user defined failures 7.
AC INI-Param: N/A"
       ::= {acKpiUserDefinedIntervalIpGroupEntry 16}



     acKpiUserDefinedIntervalIpGroupUserDefinedFailuresIn8 OBJECT-TYPE
       SYNTAX Counter64
       MAX-ACCESS read-only
       STATUS current
       DESCRIPTION
           "Number of inbound user defined failures 8.
AC INI-Param: N/A"
       ::= {acKpiUserDefinedIntervalIpGroupEntry 17}



     acKpiUserDefinedIntervalIpGroupUserDefinedFailuresOut8 OBJECT-TYPE
       SYNTAX Counter64
       MAX-ACCESS read-only
       STATUS current
       DESCRIPTION
           "Number of outbound user defined failures 8.
AC INI-Param: N/A"
       ::= {acKpiUserDefinedIntervalIpGroupEntry 18}



     acKpiUserDefinedIntervalIpGroupUserDefinedFailuresIn9 OBJECT-TYPE
       SYNTAX Counter64
       MAX-ACCESS read-only
       STATUS current
       DESCRIPTION
           "Number of inbound user defined failures 9.
AC INI-Param: N/A"
       ::= {acKpiUserDefinedIntervalIpGroupEntry 19}



     acKpiUserDefinedIntervalIpGroupUserDefinedFailuresOut9 OBJECT-TYPE
       SYNTAX Counter64
       MAX-ACCESS read-only
       STATUS current
       DESCRIPTION
           "Number of outbound user defined failures 9.
AC INI-Param: N/A"
       ::= {acKpiUserDefinedIntervalIpGroupEntry 20}



     acKpiUserDefinedIntervalIpGroupUserDefinedFailuresIn10 OBJECT-TYPE
       SYNTAX Counter64
       MAX-ACCESS read-only
       STATUS current
       DESCRIPTION
           "Number of inbound user defined failures 10.
AC INI-Param: N/A"
       ::= {acKpiUserDefinedIntervalIpGroupEntry 21}



     acKpiUserDefinedIntervalIpGroupUserDefinedFailuresOut10 OBJECT-TYPE
       SYNTAX Counter64
       MAX-ACCESS read-only
       STATUS current
       DESCRIPTION
           "Number of outbound user defined failures 10.
AC INI-Param: N/A"
       ::= {acKpiUserDefinedIntervalIpGroupEntry 22}



     acKpiUserDefinedIntervalIpGroupUserDefinedFailuresIn11 OBJECT-TYPE
       SYNTAX Counter64
       MAX-ACCESS read-only
       STATUS current
       DESCRIPTION
           "Number of inbound user defined failures 11.
AC INI-Param: N/A"
       ::= {acKpiUserDefinedIntervalIpGroupEntry 23}



     acKpiUserDefinedIntervalIpGroupUserDefinedFailuresOut11 OBJECT-TYPE
       SYNTAX Counter64
       MAX-ACCESS read-only
       STATUS current
       DESCRIPTION
           "Number of outbound user defined failures 11.
AC INI-Param: N/A"
       ::= {acKpiUserDefinedIntervalIpGroupEntry 24}



     acKpiUserDefinedIntervalIpGroupUserDefinedFailuresIn12 OBJECT-TYPE
       SYNTAX Counter64
       MAX-ACCESS read-only
       STATUS current
       DESCRIPTION
           "Number of inbound user defined failures 12.
AC INI-Param: N/A"
       ::= {acKpiUserDefinedIntervalIpGroupEntry 25}



     acKpiUserDefinedIntervalIpGroupUserDefinedFailuresOut12 OBJECT-TYPE
       SYNTAX Counter64
       MAX-ACCESS read-only
       STATUS current
       DESCRIPTION
           "Number of outbound user defined failures 12.
AC INI-Param: N/A"
       ::= {acKpiUserDefinedIntervalIpGroupEntry 26}



     acKpiUserDefinedIntervalIpGroupUserDefinedFailuresIn13 OBJECT-TYPE
       SYNTAX Counter64
       MAX-ACCESS read-only
       STATUS current
       DESCRIPTION
           "Number of inbound user defined failures 13.
AC INI-Param: N/A"
       ::= {acKpiUserDefinedIntervalIpGroupEntry 27}



     acKpiUserDefinedIntervalIpGroupUserDefinedFailuresOut13 OBJECT-TYPE
       SYNTAX Counter64
       MAX-ACCESS read-only
       STATUS current
       DESCRIPTION
           "Number of outbound user defined failures 13.
AC INI-Param: N/A"
       ::= {acKpiUserDefinedIntervalIpGroupEntry 28}



     acKpiUserDefinedIntervalIpGroupUserDefinedFailuresIn14 OBJECT-TYPE
       SYNTAX Counter64
       MAX-ACCESS read-only
       STATUS current
       DESCRIPTION
           "Number of inbound user defined failures 14.
AC INI-Param: N/A"
       ::= {acKpiUserDefinedIntervalIpGroupEntry 29}



     acKpiUserDefinedIntervalIpGroupUserDefinedFailuresOut14 OBJECT-TYPE
       SYNTAX Counter64
       MAX-ACCESS read-only
       STATUS current
       DESCRIPTION
           "Number of outbound user defined failures 14.
AC INI-Param: N/A"
       ::= {acKpiUserDefinedIntervalIpGroupEntry 30}



     acKpiUserDefinedIntervalIpGroupUserDefinedFailuresIn15 OBJECT-TYPE
       SYNTAX Counter64
       MAX-ACCESS read-only
       STATUS current
       DESCRIPTION
           "Number of inbound user defined failures 15.
AC INI-Param: N/A"
       ::= {acKpiUserDefinedIntervalIpGroupEntry 31}



     acKpiUserDefinedIntervalIpGroupUserDefinedFailuresOut15 OBJECT-TYPE
       SYNTAX Counter64
       MAX-ACCESS read-only
       STATUS current
       DESCRIPTION
           "Number of outbound user defined failures 15.
AC INI-Param: N/A"
       ::= {acKpiUserDefinedIntervalIpGroupEntry 32}



     acKpiUserDefinedIntervalIpGroupUserDefinedFailuresIn16 OBJECT-TYPE
       SYNTAX Counter64
       MAX-ACCESS read-only
       STATUS current
       DESCRIPTION
           "Number of inbound user defined failures 16.
AC INI-Param: N/A"
       ::= {acKpiUserDefinedIntervalIpGroupEntry 33}



     acKpiUserDefinedIntervalIpGroupUserDefinedFailuresOut16 OBJECT-TYPE
       SYNTAX Counter64
       MAX-ACCESS read-only
       STATUS current
       DESCRIPTION
           "Number of outbound user defined failures 16.
AC INI-Param: N/A"
       ::= {acKpiUserDefinedIntervalIpGroupEntry 34}



     acKpiUserDefinedIntervalIpGroupUserDefinedFailuresIn17 OBJECT-TYPE
       SYNTAX Counter64
       MAX-ACCESS read-only
       STATUS current
       DESCRIPTION
           "Number of inbound user defined failures 17.
AC INI-Param: N/A"
       ::= {acKpiUserDefinedIntervalIpGroupEntry 35}



     acKpiUserDefinedIntervalIpGroupUserDefinedFailuresOut17 OBJECT-TYPE
       SYNTAX Counter64
       MAX-ACCESS read-only
       STATUS current
       DESCRIPTION
           "Number of outbound user defined failures 17.
AC INI-Param: N/A"
       ::= {acKpiUserDefinedIntervalIpGroupEntry 36}



     acKpiUserDefinedIntervalIpGroupUserDefinedFailuresIn18 OBJECT-TYPE
       SYNTAX Counter64
       MAX-ACCESS read-only
       STATUS current
       DESCRIPTION
           "Number of inbound user defined failures 18.
AC INI-Param: N/A"
       ::= {acKpiUserDefinedIntervalIpGroupEntry 37}



     acKpiUserDefinedIntervalIpGroupUserDefinedFailuresOut18 OBJECT-TYPE
       SYNTAX Counter64
       MAX-ACCESS read-only
       STATUS current
       DESCRIPTION
           "Number of outbound user defined failures 18.
AC INI-Param: N/A"
       ::= {acKpiUserDefinedIntervalIpGroupEntry 38}



     acKpiUserDefinedIntervalIpGroupUserDefinedFailuresIn19 OBJECT-TYPE
       SYNTAX Counter64
       MAX-ACCESS read-only
       STATUS current
       DESCRIPTION
           "Number of inbound user defined failures 19.
AC INI-Param: N/A"
       ::= {acKpiUserDefinedIntervalIpGroupEntry 39}



     acKpiUserDefinedIntervalIpGroupUserDefinedFailuresOut19 OBJECT-TYPE
       SYNTAX Counter64
       MAX-ACCESS read-only
       STATUS current
       DESCRIPTION
           "Number of outbound user defined failures 19.
AC INI-Param: N/A"
       ::= {acKpiUserDefinedIntervalIpGroupEntry 40}



     acKpiUserDefinedIntervalIpGroupUserDefinedFailuresIn20 OBJECT-TYPE
       SYNTAX Counter64
       MAX-ACCESS read-only
       STATUS current
       DESCRIPTION
           "Number of inbound user defined failures 20.
AC INI-Param: N/A"
       ::= {acKpiUserDefinedIntervalIpGroupEntry 41}



     acKpiUserDefinedIntervalIpGroupUserDefinedFailuresOut20 OBJECT-TYPE
       SYNTAX Counter64
       MAX-ACCESS read-only
       STATUS current
       DESCRIPTION
           "Number of outbound user defined failures 20.
AC INI-Param: N/A"
       ::= {acKpiUserDefinedIntervalIpGroupEntry 42}



     acKpiUserDefinedIntervalIpGroupUserDefinedFailuresIn21 OBJECT-TYPE
       SYNTAX Counter64
       MAX-ACCESS read-only
       STATUS current
       DESCRIPTION
           "Number of inbound user defined failures 21.
AC INI-Param: N/A"
       ::= {acKpiUserDefinedIntervalIpGroupEntry 43}



     acKpiUserDefinedIntervalIpGroupUserDefinedFailuresOut21 OBJECT-TYPE
       SYNTAX Counter64
       MAX-ACCESS read-only
       STATUS current
       DESCRIPTION
           "Number of outbound user defined failures 21.
AC INI-Param: N/A"
       ::= {acKpiUserDefinedIntervalIpGroupEntry 44}



     acKpiUserDefinedIntervalIpGroupUserDefinedFailuresIn22 OBJECT-TYPE
       SYNTAX Counter64
       MAX-ACCESS read-only
       STATUS current
       DESCRIPTION
           "Number of inbound user defined failures 22.
AC INI-Param: N/A"
       ::= {acKpiUserDefinedIntervalIpGroupEntry 45}



     acKpiUserDefinedIntervalIpGroupUserDefinedFailuresOut22 OBJECT-TYPE
       SYNTAX Counter64
       MAX-ACCESS read-only
       STATUS current
       DESCRIPTION
           "Number of outbound user defined failures 22.
AC INI-Param: N/A"
       ::= {acKpiUserDefinedIntervalIpGroupEntry 46}



     acKpiUserDefinedIntervalIpGroupUserDefinedFailuresIn23 OBJECT-TYPE
       SYNTAX Counter64
       MAX-ACCESS read-only
       STATUS current
       DESCRIPTION
           "Number of inbound user defined failures 23.
AC INI-Param: N/A"
       ::= {acKpiUserDefinedIntervalIpGroupEntry 47}



     acKpiUserDefinedIntervalIpGroupUserDefinedFailuresOut23 OBJECT-TYPE
       SYNTAX Counter64
       MAX-ACCESS read-only
       STATUS current
       DESCRIPTION
           "Number of outbound user defined failures 23.
AC INI-Param: N/A"
       ::= {acKpiUserDefinedIntervalIpGroupEntry 48}



     acKpiUserDefinedIntervalIpGroupUserDefinedFailuresIn24 OBJECT-TYPE
       SYNTAX Counter64
       MAX-ACCESS read-only
       STATUS current
       DESCRIPTION
           "Number of inbound user defined failures 24.
AC INI-Param: N/A"
       ::= {acKpiUserDefinedIntervalIpGroupEntry 49}



     acKpiUserDefinedIntervalIpGroupUserDefinedFailuresOut24 OBJECT-TYPE
       SYNTAX Counter64
       MAX-ACCESS read-only
       STATUS current
       DESCRIPTION
           "Number of outbound user defined failures 24.
AC INI-Param: N/A"
       ::= {acKpiUserDefinedIntervalIpGroupEntry 50}



     acKpiUserDefinedIntervalIpGroupUserDefinedFailuresIn25 OBJECT-TYPE
       SYNTAX Counter64
       MAX-ACCESS read-only
       STATUS current
       DESCRIPTION
           "Number of inbound user defined failures 25.
AC INI-Param: N/A"
       ::= {acKpiUserDefinedIntervalIpGroupEntry 51}



     acKpiUserDefinedIntervalIpGroupUserDefinedFailuresOut25 OBJECT-TYPE
       SYNTAX Counter64
       MAX-ACCESS read-only
       STATUS current
       DESCRIPTION
           "Number of outbound user defined failures 25.
AC INI-Param: N/A"
       ::= {acKpiUserDefinedIntervalIpGroupEntry 52}



     acKpiUserDefinedIntervalIpGroupUserDefinedFailuresIn26 OBJECT-TYPE
       SYNTAX Counter64
       MAX-ACCESS read-only
       STATUS current
       DESCRIPTION
           "Number of inbound user defined failures 26.
AC INI-Param: N/A"
       ::= {acKpiUserDefinedIntervalIpGroupEntry 53}



     acKpiUserDefinedIntervalIpGroupUserDefinedFailuresOut26 OBJECT-TYPE
       SYNTAX Counter64
       MAX-ACCESS read-only
       STATUS current
       DESCRIPTION
           "Number of outbound user defined failures 26.
AC INI-Param: N/A"
       ::= {acKpiUserDefinedIntervalIpGroupEntry 54}



     -- ****************************************
     -- acKpiUserDefinedIntervalSrd table declaration
     -- ****************************************
     acKpiUserDefinedIntervalSrdTable OBJECT-TYPE
       SYNTAX SEQUENCE OF AcKpiUserDefinedIntervalSrdEntry
       MAX-ACCESS not-accessible
       STATUS current
       DESCRIPTION
           ""
       ::= {acKpiUserDefinedIntervalTables 2}



     -- ****************************************
     -- acKpiUserDefinedIntervalSrd table entry
     -- ****************************************
     acKpiUserDefinedIntervalSrdEntry OBJECT-TYPE
       SYNTAX AcKpiUserDefinedIntervalSrdEntry
       MAX-ACCESS not-accessible
       STATUS current
       DESCRIPTION
           ""
       INDEX {acKpiUserDefinedIntervalSrdIndex,acKpiUserDefinedIntervalSrdInterval}
       ::= {acKpiUserDefinedIntervalSrdTable 1}



     -- ****************************************
     -- acKpiUserDefinedIntervalSrd TABLE
     -- ****************************************
     AcKpiUserDefinedIntervalSrdEntry ::= SEQUENCE {
       acKpiUserDefinedIntervalSrdIndex                Unsigned32,
       acKpiUserDefinedIntervalSrdInterval             Unsigned32,
       acKpiUserDefinedIntervalSrdUserDefinedFailuresIn1 
                                                       Counter64,
       acKpiUserDefinedIntervalSrdUserDefinedFailuresOut1 
                                                       Counter64,
       acKpiUserDefinedIntervalSrdUserDefinedFailuresIn2 
                                                       Counter64,
       acKpiUserDefinedIntervalSrdUserDefinedFailuresOut2 
                                                       Counter64,
       acKpiUserDefinedIntervalSrdUserDefinedFailuresIn3 
                                                       Counter64,
       acKpiUserDefinedIntervalSrdUserDefinedFailuresOut3 
                                                       Counter64,
       acKpiUserDefinedIntervalSrdUserDefinedFailuresIn4 
                                                       Counter64,
       acKpiUserDefinedIntervalSrdUserDefinedFailuresOut4 
                                                       Counter64,
       acKpiUserDefinedIntervalSrdUserDefinedFailuresIn5 
                                                       Counter64,
       acKpiUserDefinedIntervalSrdUserDefinedFailuresOut5 
                                                       Counter64,
       acKpiUserDefinedIntervalSrdUserDefinedFailuresIn6 
                                                       Counter64,
       acKpiUserDefinedIntervalSrdUserDefinedFailuresOut6 
                                                       Counter64,
       acKpiUserDefinedIntervalSrdUserDefinedFailuresIn7 
                                                       Counter64,
       acKpiUserDefinedIntervalSrdUserDefinedFailuresOut7 
                                                       Counter64,
       acKpiUserDefinedIntervalSrdUserDefinedFailuresIn8 
                                                       Counter64,
       acKpiUserDefinedIntervalSrdUserDefinedFailuresOut8 
                                                       Counter64,
       acKpiUserDefinedIntervalSrdUserDefinedFailuresIn9 
                                                       Counter64,
       acKpiUserDefinedIntervalSrdUserDefinedFailuresOut9 
                                                       Counter64,
       acKpiUserDefinedIntervalSrdUserDefinedFailuresIn10 
                                                       Counter64,
       acKpiUserDefinedIntervalSrdUserDefinedFailuresOut10 
                                                       Counter64,
       acKpiUserDefinedIntervalSrdUserDefinedFailuresIn11 
                                                       Counter64,
       acKpiUserDefinedIntervalSrdUserDefinedFailuresOut11 
                                                       Counter64,
       acKpiUserDefinedIntervalSrdUserDefinedFailuresIn12 
                                                       Counter64,
       acKpiUserDefinedIntervalSrdUserDefinedFailuresOut12 
                                                       Counter64,
       acKpiUserDefinedIntervalSrdUserDefinedFailuresIn13 
                                                       Counter64,
       acKpiUserDefinedIntervalSrdUserDefinedFailuresOut13 
                                                       Counter64,
       acKpiUserDefinedIntervalSrdUserDefinedFailuresIn14 
                                                       Counter64,
       acKpiUserDefinedIntervalSrdUserDefinedFailuresOut14 
                                                       Counter64,
       acKpiUserDefinedIntervalSrdUserDefinedFailuresIn15 
                                                       Counter64,
       acKpiUserDefinedIntervalSrdUserDefinedFailuresOut15 
                                                       Counter64,
       acKpiUserDefinedIntervalSrdUserDefinedFailuresIn16 
                                                       Counter64,
       acKpiUserDefinedIntervalSrdUserDefinedFailuresOut16 
                                                       Counter64,
       acKpiUserDefinedIntervalSrdUserDefinedFailuresIn17 
                                                       Counter64,
       acKpiUserDefinedIntervalSrdUserDefinedFailuresOut17 
                                                       Counter64,
       acKpiUserDefinedIntervalSrdUserDefinedFailuresIn18 
                                                       Counter64,
       acKpiUserDefinedIntervalSrdUserDefinedFailuresOut18 
                                                       Counter64,
       acKpiUserDefinedIntervalSrdUserDefinedFailuresIn19 
                                                       Counter64,
       acKpiUserDefinedIntervalSrdUserDefinedFailuresOut19 
                                                       Counter64,
       acKpiUserDefinedIntervalSrdUserDefinedFailuresIn20 
                                                       Counter64,
       acKpiUserDefinedIntervalSrdUserDefinedFailuresOut20 
                                                       Counter64,
       acKpiUserDefinedIntervalSrdUserDefinedFailuresIn21 
                                                       Counter64,
       acKpiUserDefinedIntervalSrdUserDefinedFailuresOut21 
                                                       Counter64,
       acKpiUserDefinedIntervalSrdUserDefinedFailuresIn22 
                                                       Counter64,
       acKpiUserDefinedIntervalSrdUserDefinedFailuresOut22 
                                                       Counter64,
       acKpiUserDefinedIntervalSrdUserDefinedFailuresIn23 
                                                       Counter64,
       acKpiUserDefinedIntervalSrdUserDefinedFailuresOut23 
                                                       Counter64,
       acKpiUserDefinedIntervalSrdUserDefinedFailuresIn24 
                                                       Counter64,
       acKpiUserDefinedIntervalSrdUserDefinedFailuresOut24 
                                                       Counter64,
       acKpiUserDefinedIntervalSrdUserDefinedFailuresIn25 
                                                       Counter64,
       acKpiUserDefinedIntervalSrdUserDefinedFailuresOut25 
                                                       Counter64,
       acKpiUserDefinedIntervalSrdUserDefinedFailuresIn26 
                                                       Counter64,
       acKpiUserDefinedIntervalSrdUserDefinedFailuresOut26 
                                                       Counter64
     }



     acKpiUserDefinedIntervalSrdIndex OBJECT-TYPE
       SYNTAX Unsigned32 (0..32767)
       MAX-ACCESS not-accessible
       STATUS current
       DESCRIPTION
           "
AC INI-Param: N/A"
       ::= {acKpiUserDefinedIntervalSrdEntry 1}



     acKpiUserDefinedIntervalSrdInterval OBJECT-TYPE
       SYNTAX Unsigned32 (1..200)
       MAX-ACCESS not-accessible
       STATUS current
       DESCRIPTION
           "
AC INI-Param: N/A"
       ::= {acKpiUserDefinedIntervalSrdEntry 2}



     acKpiUserDefinedIntervalSrdUserDefinedFailuresIn1 OBJECT-TYPE
       SYNTAX Counter64
       MAX-ACCESS read-only
       STATUS current
       DESCRIPTION
           "Number of inbound user defined failures 1.
AC INI-Param: N/A"
       ::= {acKpiUserDefinedIntervalSrdEntry 3}



     acKpiUserDefinedIntervalSrdUserDefinedFailuresOut1 OBJECT-TYPE
       SYNTAX Counter64
       MAX-ACCESS read-only
       STATUS current
       DESCRIPTION
           "Number of outbound user defined failures 1.
AC INI-Param: N/A"
       ::= {acKpiUserDefinedIntervalSrdEntry 4}



     acKpiUserDefinedIntervalSrdUserDefinedFailuresIn2 OBJECT-TYPE
       SYNTAX Counter64
       MAX-ACCESS read-only
       STATUS current
       DESCRIPTION
           "Number of inbound user defined failures 2.
AC INI-Param: N/A"
       ::= {acKpiUserDefinedIntervalSrdEntry 5}



     acKpiUserDefinedIntervalSrdUserDefinedFailuresOut2 OBJECT-TYPE
       SYNTAX Counter64
       MAX-ACCESS read-only
       STATUS current
       DESCRIPTION
           "Number of outbound user defined failures 2.
AC INI-Param: N/A"
       ::= {acKpiUserDefinedIntervalSrdEntry 6}



     acKpiUserDefinedIntervalSrdUserDefinedFailuresIn3 OBJECT-TYPE
       SYNTAX Counter64
       MAX-ACCESS read-only
       STATUS current
       DESCRIPTION
           "Number of inbound user defined failures 3.
AC INI-Param: N/A"
       ::= {acKpiUserDefinedIntervalSrdEntry 7}



     acKpiUserDefinedIntervalSrdUserDefinedFailuresOut3 OBJECT-TYPE
       SYNTAX Counter64
       MAX-ACCESS read-only
       STATUS current
       DESCRIPTION
           "Number of outbound user defined failures 3.
AC INI-Param: N/A"
       ::= {acKpiUserDefinedIntervalSrdEntry 8}



     acKpiUserDefinedIntervalSrdUserDefinedFailuresIn4 OBJECT-TYPE
       SYNTAX Counter64
       MAX-ACCESS read-only
       STATUS current
       DESCRIPTION
           "Number of inbound user defined failures 4.
AC INI-Param: N/A"
       ::= {acKpiUserDefinedIntervalSrdEntry 9}



     acKpiUserDefinedIntervalSrdUserDefinedFailuresOut4 OBJECT-TYPE
       SYNTAX Counter64
       MAX-ACCESS read-only
       STATUS current
       DESCRIPTION
           "Number of outbound user defined failures 4.
AC INI-Param: N/A"
       ::= {acKpiUserDefinedIntervalSrdEntry 10}



     acKpiUserDefinedIntervalSrdUserDefinedFailuresIn5 OBJECT-TYPE
       SYNTAX Counter64
       MAX-ACCESS read-only
       STATUS current
       DESCRIPTION
           "Number of inbound user defined failures 5.
AC INI-Param: N/A"
       ::= {acKpiUserDefinedIntervalSrdEntry 11}



     acKpiUserDefinedIntervalSrdUserDefinedFailuresOut5 OBJECT-TYPE
       SYNTAX Counter64
       MAX-ACCESS read-only
       STATUS current
       DESCRIPTION
           "Number of outbound user defined failures 5.
AC INI-Param: N/A"
       ::= {acKpiUserDefinedIntervalSrdEntry 12}



     acKpiUserDefinedIntervalSrdUserDefinedFailuresIn6 OBJECT-TYPE
       SYNTAX Counter64
       MAX-ACCESS read-only
       STATUS current
       DESCRIPTION
           "Number of inbound user defined failures 6.
AC INI-Param: N/A"
       ::= {acKpiUserDefinedIntervalSrdEntry 13}



     acKpiUserDefinedIntervalSrdUserDefinedFailuresOut6 OBJECT-TYPE
       SYNTAX Counter64
       MAX-ACCESS read-only
       STATUS current
       DESCRIPTION
           "Number of outbound user defined failures 6.
AC INI-Param: N/A"
       ::= {acKpiUserDefinedIntervalSrdEntry 14}



     acKpiUserDefinedIntervalSrdUserDefinedFailuresIn7 OBJECT-TYPE
       SYNTAX Counter64
       MAX-ACCESS read-only
       STATUS current
       DESCRIPTION
           "Number of inbound user defined failures 7.
AC INI-Param: N/A"
       ::= {acKpiUserDefinedIntervalSrdEntry 15}



     acKpiUserDefinedIntervalSrdUserDefinedFailuresOut7 OBJECT-TYPE
       SYNTAX Counter64
       MAX-ACCESS read-only
       STATUS current
       DESCRIPTION
           "Number of outbound user defined failures 7.
AC INI-Param: N/A"
       ::= {acKpiUserDefinedIntervalSrdEntry 16}



     acKpiUserDefinedIntervalSrdUserDefinedFailuresIn8 OBJECT-TYPE
       SYNTAX Counter64
       MAX-ACCESS read-only
       STATUS current
       DESCRIPTION
           "Number of inbound user defined failures 8.
AC INI-Param: N/A"
       ::= {acKpiUserDefinedIntervalSrdEntry 17}



     acKpiUserDefinedIntervalSrdUserDefinedFailuresOut8 OBJECT-TYPE
       SYNTAX Counter64
       MAX-ACCESS read-only
       STATUS current
       DESCRIPTION
           "Number of outbound user defined failures 8.
AC INI-Param: N/A"
       ::= {acKpiUserDefinedIntervalSrdEntry 18}



     acKpiUserDefinedIntervalSrdUserDefinedFailuresIn9 OBJECT-TYPE
       SYNTAX Counter64
       MAX-ACCESS read-only
       STATUS current
       DESCRIPTION
           "Number of inbound user defined failures 9.
AC INI-Param: N/A"
       ::= {acKpiUserDefinedIntervalSrdEntry 19}



     acKpiUserDefinedIntervalSrdUserDefinedFailuresOut9 OBJECT-TYPE
       SYNTAX Counter64
       MAX-ACCESS read-only
       STATUS current
       DESCRIPTION
           "Number of outbound user defined failures 9.
AC INI-Param: N/A"
       ::= {acKpiUserDefinedIntervalSrdEntry 20}



     acKpiUserDefinedIntervalSrdUserDefinedFailuresIn10 OBJECT-TYPE
       SYNTAX Counter64
       MAX-ACCESS read-only
       STATUS current
       DESCRIPTION
           "Number of inbound user defined failures 10.
AC INI-Param: N/A"
       ::= {acKpiUserDefinedIntervalSrdEntry 21}



     acKpiUserDefinedIntervalSrdUserDefinedFailuresOut10 OBJECT-TYPE
       SYNTAX Counter64
       MAX-ACCESS read-only
       STATUS current
       DESCRIPTION
           "Number of outbound user defined failures 10.
AC INI-Param: N/A"
       ::= {acKpiUserDefinedIntervalSrdEntry 22}



     acKpiUserDefinedIntervalSrdUserDefinedFailuresIn11 OBJECT-TYPE
       SYNTAX Counter64
       MAX-ACCESS read-only
       STATUS current
       DESCRIPTION
           "Number of inbound user defined failures 11.
AC INI-Param: N/A"
       ::= {acKpiUserDefinedIntervalSrdEntry 23}



     acKpiUserDefinedIntervalSrdUserDefinedFailuresOut11 OBJECT-TYPE
       SYNTAX Counter64
       MAX-ACCESS read-only
       STATUS current
       DESCRIPTION
           "Number of outbound user defined failures 11.
AC INI-Param: N/A"
       ::= {acKpiUserDefinedIntervalSrdEntry 24}



     acKpiUserDefinedIntervalSrdUserDefinedFailuresIn12 OBJECT-TYPE
       SYNTAX Counter64
       MAX-ACCESS read-only
       STATUS current
       DESCRIPTION
           "Number of inbound user defined failures 12.
AC INI-Param: N/A"
       ::= {acKpiUserDefinedIntervalSrdEntry 25}



     acKpiUserDefinedIntervalSrdUserDefinedFailuresOut12 OBJECT-TYPE
       SYNTAX Counter64
       MAX-ACCESS read-only
       STATUS current
       DESCRIPTION
           "Number of outbound user defined failures 12.
AC INI-Param: N/A"
       ::= {acKpiUserDefinedIntervalSrdEntry 26}



     acKpiUserDefinedIntervalSrdUserDefinedFailuresIn13 OBJECT-TYPE
       SYNTAX Counter64
       MAX-ACCESS read-only
       STATUS current
       DESCRIPTION
           "Number of inbound user defined failures 13.
AC INI-Param: N/A"
       ::= {acKpiUserDefinedIntervalSrdEntry 27}



     acKpiUserDefinedIntervalSrdUserDefinedFailuresOut13 OBJECT-TYPE
       SYNTAX Counter64
       MAX-ACCESS read-only
       STATUS current
       DESCRIPTION
           "Number of outbound user defined failures 13.
AC INI-Param: N/A"
       ::= {acKpiUserDefinedIntervalSrdEntry 28}



     acKpiUserDefinedIntervalSrdUserDefinedFailuresIn14 OBJECT-TYPE
       SYNTAX Counter64
       MAX-ACCESS read-only
       STATUS current
       DESCRIPTION
           "Number of inbound user defined failures 14.
AC INI-Param: N/A"
       ::= {acKpiUserDefinedIntervalSrdEntry 29}



     acKpiUserDefinedIntervalSrdUserDefinedFailuresOut14 OBJECT-TYPE
       SYNTAX Counter64
       MAX-ACCESS read-only
       STATUS current
       DESCRIPTION
           "Number of outbound user defined failures 14.
AC INI-Param: N/A"
       ::= {acKpiUserDefinedIntervalSrdEntry 30}



     acKpiUserDefinedIntervalSrdUserDefinedFailuresIn15 OBJECT-TYPE
       SYNTAX Counter64
       MAX-ACCESS read-only
       STATUS current
       DESCRIPTION
           "Number of inbound user defined failures 15.
AC INI-Param: N/A"
       ::= {acKpiUserDefinedIntervalSrdEntry 31}



     acKpiUserDefinedIntervalSrdUserDefinedFailuresOut15 OBJECT-TYPE
       SYNTAX Counter64
       MAX-ACCESS read-only
       STATUS current
       DESCRIPTION
           "Number of outbound user defined failures 15.
AC INI-Param: N/A"
       ::= {acKpiUserDefinedIntervalSrdEntry 32}



     acKpiUserDefinedIntervalSrdUserDefinedFailuresIn16 OBJECT-TYPE
       SYNTAX Counter64
       MAX-ACCESS read-only
       STATUS current
       DESCRIPTION
           "Number of inbound user defined failures 16.
AC INI-Param: N/A"
       ::= {acKpiUserDefinedIntervalSrdEntry 33}



     acKpiUserDefinedIntervalSrdUserDefinedFailuresOut16 OBJECT-TYPE
       SYNTAX Counter64
       MAX-ACCESS read-only
       STATUS current
       DESCRIPTION
           "Number of outbound user defined failures 16.
AC INI-Param: N/A"
       ::= {acKpiUserDefinedIntervalSrdEntry 34}



     acKpiUserDefinedIntervalSrdUserDefinedFailuresIn17 OBJECT-TYPE
       SYNTAX Counter64
       MAX-ACCESS read-only
       STATUS current
       DESCRIPTION
           "Number of inbound user defined failures 17.
AC INI-Param: N/A"
       ::= {acKpiUserDefinedIntervalSrdEntry 35}



     acKpiUserDefinedIntervalSrdUserDefinedFailuresOut17 OBJECT-TYPE
       SYNTAX Counter64
       MAX-ACCESS read-only
       STATUS current
       DESCRIPTION
           "Number of outbound user defined failures 17.
AC INI-Param: N/A"
       ::= {acKpiUserDefinedIntervalSrdEntry 36}



     acKpiUserDefinedIntervalSrdUserDefinedFailuresIn18 OBJECT-TYPE
       SYNTAX Counter64
       MAX-ACCESS read-only
       STATUS current
       DESCRIPTION
           "Number of inbound user defined failures 18.
AC INI-Param: N/A"
       ::= {acKpiUserDefinedIntervalSrdEntry 37}



     acKpiUserDefinedIntervalSrdUserDefinedFailuresOut18 OBJECT-TYPE
       SYNTAX Counter64
       MAX-ACCESS read-only
       STATUS current
       DESCRIPTION
           "Number of outbound user defined failures 18.
AC INI-Param: N/A"
       ::= {acKpiUserDefinedIntervalSrdEntry 38}



     acKpiUserDefinedIntervalSrdUserDefinedFailuresIn19 OBJECT-TYPE
       SYNTAX Counter64
       MAX-ACCESS read-only
       STATUS current
       DESCRIPTION
           "Number of inbound user defined failures 19.
AC INI-Param: N/A"
       ::= {acKpiUserDefinedIntervalSrdEntry 39}



     acKpiUserDefinedIntervalSrdUserDefinedFailuresOut19 OBJECT-TYPE
       SYNTAX Counter64
       MAX-ACCESS read-only
       STATUS current
       DESCRIPTION
           "Number of outbound user defined failures 19.
AC INI-Param: N/A"
       ::= {acKpiUserDefinedIntervalSrdEntry 40}



     acKpiUserDefinedIntervalSrdUserDefinedFailuresIn20 OBJECT-TYPE
       SYNTAX Counter64
       MAX-ACCESS read-only
       STATUS current
       DESCRIPTION
           "Number of inbound user defined failures 20.
AC INI-Param: N/A"
       ::= {acKpiUserDefinedIntervalSrdEntry 41}



     acKpiUserDefinedIntervalSrdUserDefinedFailuresOut20 OBJECT-TYPE
       SYNTAX Counter64
       MAX-ACCESS read-only
       STATUS current
       DESCRIPTION
           "Number of outbound user defined failures 20.
AC INI-Param: N/A"
       ::= {acKpiUserDefinedIntervalSrdEntry 42}



     acKpiUserDefinedIntervalSrdUserDefinedFailuresIn21 OBJECT-TYPE
       SYNTAX Counter64
       MAX-ACCESS read-only
       STATUS current
       DESCRIPTION
           "Number of inbound user defined failures 21.
AC INI-Param: N/A"
       ::= {acKpiUserDefinedIntervalSrdEntry 43}



     acKpiUserDefinedIntervalSrdUserDefinedFailuresOut21 OBJECT-TYPE
       SYNTAX Counter64
       MAX-ACCESS read-only
       STATUS current
       DESCRIPTION
           "Number of outbound user defined failures 21.
AC INI-Param: N/A"
       ::= {acKpiUserDefinedIntervalSrdEntry 44}



     acKpiUserDefinedIntervalSrdUserDefinedFailuresIn22 OBJECT-TYPE
       SYNTAX Counter64
       MAX-ACCESS read-only
       STATUS current
       DESCRIPTION
           "Number of inbound user defined failures 22.
AC INI-Param: N/A"
       ::= {acKpiUserDefinedIntervalSrdEntry 45}



     acKpiUserDefinedIntervalSrdUserDefinedFailuresOut22 OBJECT-TYPE
       SYNTAX Counter64
       MAX-ACCESS read-only
       STATUS current
       DESCRIPTION
           "Number of outbound user defined failures 22.
AC INI-Param: N/A"
       ::= {acKpiUserDefinedIntervalSrdEntry 46}



     acKpiUserDefinedIntervalSrdUserDefinedFailuresIn23 OBJECT-TYPE
       SYNTAX Counter64
       MAX-ACCESS read-only
       STATUS current
       DESCRIPTION
           "Number of inbound user defined failures 23.
AC INI-Param: N/A"
       ::= {acKpiUserDefinedIntervalSrdEntry 47}



     acKpiUserDefinedIntervalSrdUserDefinedFailuresOut23 OBJECT-TYPE
       SYNTAX Counter64
       MAX-ACCESS read-only
       STATUS current
       DESCRIPTION
           "Number of outbound user defined failures 23.
AC INI-Param: N/A"
       ::= {acKpiUserDefinedIntervalSrdEntry 48}



     acKpiUserDefinedIntervalSrdUserDefinedFailuresIn24 OBJECT-TYPE
       SYNTAX Counter64
       MAX-ACCESS read-only
       STATUS current
       DESCRIPTION
           "Number of inbound user defined failures 24.
AC INI-Param: N/A"
       ::= {acKpiUserDefinedIntervalSrdEntry 49}



     acKpiUserDefinedIntervalSrdUserDefinedFailuresOut24 OBJECT-TYPE
       SYNTAX Counter64
       MAX-ACCESS read-only
       STATUS current
       DESCRIPTION
           "Number of outbound user defined failures 24.
AC INI-Param: N/A"
       ::= {acKpiUserDefinedIntervalSrdEntry 50}



     acKpiUserDefinedIntervalSrdUserDefinedFailuresIn25 OBJECT-TYPE
       SYNTAX Counter64
       MAX-ACCESS read-only
       STATUS current
       DESCRIPTION
           "Number of inbound user defined failures 25.
AC INI-Param: N/A"
       ::= {acKpiUserDefinedIntervalSrdEntry 51}



     acKpiUserDefinedIntervalSrdUserDefinedFailuresOut25 OBJECT-TYPE
       SYNTAX Counter64
       MAX-ACCESS read-only
       STATUS current
       DESCRIPTION
           "Number of outbound user defined failures 25.
AC INI-Param: N/A"
       ::= {acKpiUserDefinedIntervalSrdEntry 52}



     acKpiUserDefinedIntervalSrdUserDefinedFailuresIn26 OBJECT-TYPE
       SYNTAX Counter64
       MAX-ACCESS read-only
       STATUS current
       DESCRIPTION
           "Number of inbound user defined failures 26.
AC INI-Param: N/A"
       ::= {acKpiUserDefinedIntervalSrdEntry 53}



     acKpiUserDefinedIntervalSrdUserDefinedFailuresOut26 OBJECT-TYPE
       SYNTAX Counter64
       MAX-ACCESS read-only
       STATUS current
       DESCRIPTION
           "Number of outbound user defined failures 26.
AC INI-Param: N/A"
       ::= {acKpiUserDefinedIntervalSrdEntry 54}



     acKpiOtherStats OBJECT IDENTIFIER ::= {acKpiSbc 3}


     acKpiOtherStatsCurrent OBJECT IDENTIFIER ::= {acKpiOtherStats 1}


     acKpiOtherStatsCurrentGlobal OBJECT IDENTIFIER ::= {acKpiOtherStatsCurrent 1}


     acKpiOtherStatsCurrentGlobalRegisteredUsers OBJECT-TYPE
       SYNTAX Gauge32
       MAX-ACCESS read-only
       STATUS current
       DESCRIPTION
           "Number of registered users.
AC INI-Param: N/A"
       ::= {acKpiOtherStatsCurrentGlobal 1}



     acKpiOtherStatsCurrentGlobalRegisterInTotal OBJECT-TYPE
       SYNTAX Counter64
       MAX-ACCESS read-only
       STATUS current
       DESCRIPTION
           "Total number of inbound registrations.
AC INI-Param: N/A"
       ::= {acKpiOtherStatsCurrentGlobal 2}



     acKpiOtherStatsCurrentGlobalRegisterRateIn OBJECT-TYPE
       SYNTAX Gauge32
       MAX-ACCESS read-only
       STATUS current
       DESCRIPTION
           "Rate of inbound registrations (registrations per second).
AC INI-Param: N/A"
       ::= {acKpiOtherStatsCurrentGlobal 3}



     acKpiOtherStatsCurrentGlobalRegisterOutTotal OBJECT-TYPE
       SYNTAX Counter64
       MAX-ACCESS read-only
       STATUS current
       DESCRIPTION
           "Total number of outbound registrations.
AC INI-Param: N/A"
       ::= {acKpiOtherStatsCurrentGlobal 4}



     acKpiOtherStatsCurrentGlobalRegisterRateOut OBJECT-TYPE
       SYNTAX Gauge32
       MAX-ACCESS read-only
       STATUS current
       DESCRIPTION
           "Rate of outbound registrations (registrations per second).
AC INI-Param: N/A"
       ::= {acKpiOtherStatsCurrentGlobal 5}



     acKpiOtherStatsCurrentGlobalActiveSubscribes OBJECT-TYPE
       SYNTAX Gauge32
       MAX-ACCESS read-only
       STATUS current
       DESCRIPTION
           "Number of active SUBSCRIBE dialogs.
AC INI-Param: N/A"
       ::= {acKpiOtherStatsCurrentGlobal 6}



     acKpiOtherStatsCurrentGlobalSubscribeRateIn OBJECT-TYPE
       SYNTAX Gauge32
       MAX-ACCESS read-only
       STATUS current
       DESCRIPTION
           "Inbound SUBSCRIBE Rate (dialogs per second).
AC INI-Param: N/A"
       ::= {acKpiOtherStatsCurrentGlobal 7}



     acKpiOtherStatsCurrentGlobalSubscribeRateOut OBJECT-TYPE
       SYNTAX Gauge32
       MAX-ACCESS read-only
       STATUS current
       DESCRIPTION
           "Outbound SUBSCRIBE Rate (dialogs per second).
AC INI-Param: N/A"
       ::= {acKpiOtherStatsCurrentGlobal 8}



     acKpiOtherStatsCurrentGlobalOtherDialogs OBJECT-TYPE
       SYNTAX Gauge32
       MAX-ACCESS read-only
       STATUS current
       DESCRIPTION
           "Number of active other dialogs (not INVITE,SUBSCRIBE,REGISTER).
AC INI-Param: N/A"
       ::= {acKpiOtherStatsCurrentGlobal 9}



     acKpiOtherStatsCurrentGlobalOtherDialogsRateIn OBJECT-TYPE
       SYNTAX Gauge32
       MAX-ACCESS read-only
       STATUS current
       DESCRIPTION
           "Inbound other dialogs rate (dialogs per second).
AC INI-Param: N/A"
       ::= {acKpiOtherStatsCurrentGlobal 10}



     acKpiOtherStatsCurrentGlobalOtherDialogsRateOut OBJECT-TYPE
       SYNTAX Gauge32
       MAX-ACCESS read-only
       STATUS current
       DESCRIPTION
           "Outbound other dialogs rate (dialogs per second).
AC INI-Param: N/A"
       ::= {acKpiOtherStatsCurrentGlobal 11}



     acKpiOtherStatsCurrentGlobalTransactionRate OBJECT-TYPE
       SYNTAX Gauge32
       MAX-ACCESS read-only
       STATUS current
       DESCRIPTION
           "SIP transactions rate (transactions per second).
AC INI-Param: N/A"
       ::= {acKpiOtherStatsCurrentGlobal 12}



     acKpiOtherStatsCurrentGlobalSbcSuccessfulRegistrationsTotal OBJECT-TYPE
       SYNTAX Counter64
       MAX-ACCESS read-only
       STATUS current
       DESCRIPTION
           "Total number of successful SBC-initiated outbound REGISTER dialogs.
AC INI-Param: N/A"
       ::= {acKpiOtherStatsCurrentGlobal 13}



     acKpiOtherStatsCurrentGlobalSbcRegistrationSuccessRatio OBJECT-TYPE
       SYNTAX Gauge32
       MAX-ACCESS read-only
       STATUS current
       DESCRIPTION
           "Success ratio for SBC-initiated REGISTER dialogs (%).
AC INI-Param: N/A"
       ::= {acKpiOtherStatsCurrentGlobal 14}



     acKpiOtherStatsCurrentGlobalSbcAttemptedRegistrationsTotal OBJECT-TYPE
       SYNTAX Counter64
       MAX-ACCESS read-only
       STATUS current
       DESCRIPTION
           "Total number of SBC-initiated outbound REGISTER dialogs.
AC INI-Param: N/A"
       ::= {acKpiOtherStatsCurrentGlobal 15}



     acKpiOtherStatsCurrentGlobalUserRegistrationSuccessRatio OBJECT-TYPE
       SYNTAX Gauge32
       MAX-ACCESS read-only
       STATUS current
       DESCRIPTION
           "Success ratio for user-initiated REGISTER dialogs (%).
AC INI-Param: N/A"
       ::= {acKpiOtherStatsCurrentGlobal 16}



     acKpiOtherStatsCurrentGlobalUserSuccessfulRegistrationsTotal OBJECT-TYPE
       SYNTAX Counter64
       MAX-ACCESS read-only
       STATUS current
       DESCRIPTION
           "Total number of successful user-initiated inbound REGISTER dialogs.
AC INI-Param: N/A"
       ::= {acKpiOtherStatsCurrentGlobal 17}



     acKpiOtherStatsCurrentGlobalSubscribeInTotal OBJECT-TYPE
       SYNTAX Counter64
       MAX-ACCESS read-only
       STATUS current
       DESCRIPTION
           "Total number of inbound SUBSCRIBE requests.
AC INI-Param: N/A"
       ::= {acKpiOtherStatsCurrentGlobal 18}



     acKpiOtherStatsCurrentGlobalSubscribeOutTotal OBJECT-TYPE
       SYNTAX Counter64
       MAX-ACCESS read-only
       STATUS current
       DESCRIPTION
           "Total number of outbound SUBSCRIBE requests.
AC INI-Param: N/A"
       ::= {acKpiOtherStatsCurrentGlobal 19}



     acKpiOtherStatsCurrentGlobalOtherDialogsInTotal OBJECT-TYPE
       SYNTAX Counter64
       MAX-ACCESS read-only
       STATUS current
       DESCRIPTION
           "Total number of inbound other requests (not INVITE,SUBSCRIBE,REGISTER).
AC INI-Param: N/A"
       ::= {acKpiOtherStatsCurrentGlobal 20}



     acKpiOtherStatsCurrentGlobalOtherDialogsOutTotal OBJECT-TYPE
       SYNTAX Counter64
       MAX-ACCESS read-only
       STATUS current
       DESCRIPTION
           "Total number of outbound other requests (not INVITE,SUBSCRIBE,REGISTER).
AC INI-Param: N/A"
       ::= {acKpiOtherStatsCurrentGlobal 21}



     acKpiOtherStatsCurrentGlobalFailedRegisterInTotal OBJECT-TYPE
       SYNTAX Counter64
       MAX-ACCESS read-only
       STATUS current
       DESCRIPTION
           "Total number of failed inbound REGISTER dialogs.
AC INI-Param: N/A"
       ::= {acKpiOtherStatsCurrentGlobal 22}



     acKpiOtherStatsCurrentGlobalFailedRegisterOutTotal OBJECT-TYPE
       SYNTAX Counter64
       MAX-ACCESS read-only
       STATUS current
       DESCRIPTION
           "Total number of failed outbound REGISTER dialogs.
AC INI-Param: N/A"
       ::= {acKpiOtherStatsCurrentGlobal 23}



     acKpiOtherStatsCurrentGlobalFailedRegisterAdmissionInTotal OBJECT-TYPE
       SYNTAX Counter64
       MAX-ACCESS read-only
       STATUS current
       DESCRIPTION
           "Total number of inbound REGISTER dialogs failed due to admission
control (CAC).
AC INI-Param: N/A"
       ::= {acKpiOtherStatsCurrentGlobal 24}



     acKpiOtherStatsCurrentGlobalFailedRegisterAdmissionOutTotal OBJECT-TYPE
       SYNTAX Counter64
       MAX-ACCESS read-only
       STATUS current
       DESCRIPTION
           "Total number of outbound REGISTER dialogs failed due to admission
control (CAC).
AC INI-Param: N/A"
       ::= {acKpiOtherStatsCurrentGlobal 25}



     acKpiOtherStatsCurrentGlobalFailedRegisterNoRouteInTotal OBJECT-TYPE
       SYNTAX Counter64
       MAX-ACCESS read-only
       STATUS current
       DESCRIPTION
           "Total number of inbound REGISTER dialogs failed due to routing
failure.
AC INI-Param: N/A"
       ::= {acKpiOtherStatsCurrentGlobal 26}



     acKpiOtherStatsCurrentGlobalFailedRegisterClassificationInTotal OBJECT-TYPE
       SYNTAX Counter64
       MAX-ACCESS read-only
       STATUS current
       DESCRIPTION
           "Total number of inbound REGISTER dialogs failed due to classification
failure.
AC INI-Param: N/A"
       ::= {acKpiOtherStatsCurrentGlobal 27}



     acKpiOtherStatsCurrentGlobalFailedRegisterOtherInTotal OBJECT-TYPE
       SYNTAX Counter64
       MAX-ACCESS read-only
       STATUS current
       DESCRIPTION
           "Total number of inbound REGISTER dialogs failed due to other
reasons.
AC INI-Param: N/A"
       ::= {acKpiOtherStatsCurrentGlobal 28}



     acKpiOtherStatsCurrentGlobalFailedRegisterOtherOutTotal OBJECT-TYPE
       SYNTAX Counter64
       MAX-ACCESS read-only
       STATUS current
       DESCRIPTION
           "Total number of outbound REGISTER dialogs failed due to other
reasons.
AC INI-Param: N/A"
       ::= {acKpiOtherStatsCurrentGlobal 29}



     acKpiOtherStatsCurrentGlobalFailedSubscribeInTotal OBJECT-TYPE
       SYNTAX Counter64
       MAX-ACCESS read-only
       STATUS current
       DESCRIPTION
           "Total number of Failed Inbound SUBSCRIBE dialogs.
AC INI-Param: N/A"
       ::= {acKpiOtherStatsCurrentGlobal 30}



     acKpiOtherStatsCurrentGlobalFailedSubscribeOutTotal OBJECT-TYPE
       SYNTAX Counter64
       MAX-ACCESS read-only
       STATUS current
       DESCRIPTION
           "Total number of Failed Outbound SUBSCRIBE dialogs.
AC INI-Param: N/A"
       ::= {acKpiOtherStatsCurrentGlobal 31}



     acKpiOtherStatsCurrentGlobalFailedOtherDialogsInTotal OBJECT-TYPE
       SYNTAX Counter64
       MAX-ACCESS read-only
       STATUS current
       DESCRIPTION
           "Total number of Failed Inbound other dialogs.
AC INI-Param: N/A"
       ::= {acKpiOtherStatsCurrentGlobal 32}



     acKpiOtherStatsCurrentGlobalFailedOtherDialogsOutTotal OBJECT-TYPE
       SYNTAX Counter64
       MAX-ACCESS read-only
       STATUS current
       DESCRIPTION
           "Total number of Failed Outbound other dialogs.
AC INI-Param: N/A"
       ::= {acKpiOtherStatsCurrentGlobal 33}



     acKpiOtherStatsCurrentTables OBJECT IDENTIFIER ::= {acKpiOtherStatsCurrent 2}


     -- ****************************************
     -- acKpiOtherStatsCurrentIpGroup table declaration
     -- ****************************************
     acKpiOtherStatsCurrentIpGroupTable OBJECT-TYPE
       SYNTAX SEQUENCE OF AcKpiOtherStatsCurrentIpGroupEntry
       MAX-ACCESS not-accessible
       STATUS current
       DESCRIPTION
           ""
       ::= {acKpiOtherStatsCurrentTables 1}



     -- ****************************************
     -- acKpiOtherStatsCurrentIpGroup table entry
     -- ****************************************
     acKpiOtherStatsCurrentIpGroupEntry OBJECT-TYPE
       SYNTAX AcKpiOtherStatsCurrentIpGroupEntry
       MAX-ACCESS not-accessible
       STATUS current
       DESCRIPTION
           ""
       INDEX {acKpiOtherStatsCurrentIpGroupIndex}
       ::= {acKpiOtherStatsCurrentIpGroupTable 1}



     -- ****************************************
     -- acKpiOtherStatsCurrentIpGroup TABLE
     -- ****************************************
     AcKpiOtherStatsCurrentIpGroupEntry ::= SEQUENCE {
       acKpiOtherStatsCurrentIpGroupIndex              Unsigned32,
       acKpiOtherStatsCurrentIpGroupRegisteredUsers    Gauge32,
       acKpiOtherStatsCurrentIpGroupRegisterInTotal    Counter64,
       acKpiOtherStatsCurrentIpGroupRegisterRateIn     Gauge32,
       acKpiOtherStatsCurrentIpGroupRegisterOutTotal   Counter64,
       acKpiOtherStatsCurrentIpGroupRegisterRateOut    Gauge32,
       acKpiOtherStatsCurrentIpGroupActiveSubscribes   Gauge32,
       acKpiOtherStatsCurrentIpGroupSubscribeRateIn    Gauge32,
       acKpiOtherStatsCurrentIpGroupSubscribeRateOut   Gauge32,
       acKpiOtherStatsCurrentIpGroupOtherDialogs       Gauge32,
       acKpiOtherStatsCurrentIpGroupOtherDialogsRateIn Gauge32,
       acKpiOtherStatsCurrentIpGroupOtherDialogsRateOut 
                                                       Gauge32,
       acKpiOtherStatsCurrentIpGroupTransactionRate    Gauge32,
       acKpiOtherStatsCurrentIpGroupSbcSuccessfulRegistrationsTotal 
                                                       Counter64,
       acKpiOtherStatsCurrentIpGroupSbcRegistrationSuccessRatio 
                                                       Gauge32,
       acKpiOtherStatsCurrentIpGroupSbcAttemptedRegistrationsTotal 
                                                       Counter64,
       acKpiOtherStatsCurrentIpGroupUserRegistrationSuccessRatio 
                                                       Gauge32,
       acKpiOtherStatsCurrentIpGroupUserSuccessfulRegistrationsTotal 
                                                       Counter64,
       acKpiOtherStatsCurrentIpGroupFailedOtherDialogsOutTotal 
                                                       Counter64,
       acKpiOtherStatsCurrentIpGroupFailedOtherDialogsInTotal 
                                                       Counter64,
       acKpiOtherStatsCurrentIpGroupFailedSubscribeOutTotal 
                                                       Counter64,
       acKpiOtherStatsCurrentIpGroupFailedSubscribeInTotal 
                                                       Counter64,
       acKpiOtherStatsCurrentIpGroupFailedRegisterOtherOutTotal 
                                                       Counter64,
       acKpiOtherStatsCurrentIpGroupFailedRegisterOtherInTotal 
                                                       Counter64,
       acKpiOtherStatsCurrentIpGroupFailedRegisterNoRouteInTotal 
                                                       Counter64,
       acKpiOtherStatsCurrentIpGroupFailedRegisterAdmissionOutTotal 
                                                       Counter64,
       acKpiOtherStatsCurrentIpGroupFailedRegisterAdmissionInTotal 
                                                       Counter64,
       acKpiOtherStatsCurrentIpGroupFailedRegisterOutTotal 
                                                       Counter64,
       acKpiOtherStatsCurrentIpGroupFailedRegisterInTotal 
                                                       Counter64,
       acKpiOtherStatsCurrentIpGroupOtherDialogsOutTotal 
                                                       Counter64,
       acKpiOtherStatsCurrentIpGroupOtherDialogsInTotal 
                                                       Counter64,
       acKpiOtherStatsCurrentIpGroupSubscribeOutTotal  Counter64,
       acKpiOtherStatsCurrentIpGroupSubscribeInTotal   Counter64
     }



     acKpiOtherStatsCurrentIpGroupIndex OBJECT-TYPE
       SYNTAX Unsigned32 (0..32767)
       MAX-ACCESS not-accessible
       STATUS current
       DESCRIPTION
           "
AC INI-Param: N/A"
       ::= {acKpiOtherStatsCurrentIpGroupEntry 1}



     acKpiOtherStatsCurrentIpGroupRegisteredUsers OBJECT-TYPE
       SYNTAX Gauge32
       MAX-ACCESS read-only
       STATUS current
       DESCRIPTION
           "Number of registered users.
AC INI-Param: N/A"
       ::= {acKpiOtherStatsCurrentIpGroupEntry 2}



     acKpiOtherStatsCurrentIpGroupRegisterInTotal OBJECT-TYPE
       SYNTAX Counter64
       MAX-ACCESS read-only
       STATUS current
       DESCRIPTION
           "Total number of inbound registrations.
AC INI-Param: N/A"
       ::= {acKpiOtherStatsCurrentIpGroupEntry 3}



     acKpiOtherStatsCurrentIpGroupRegisterRateIn OBJECT-TYPE
       SYNTAX Gauge32
       MAX-ACCESS read-only
       STATUS current
       DESCRIPTION
           "Rate of inbound registrations (registrations per second).
AC INI-Param: N/A"
       ::= {acKpiOtherStatsCurrentIpGroupEntry 4}



     acKpiOtherStatsCurrentIpGroupRegisterOutTotal OBJECT-TYPE
       SYNTAX Counter64
       MAX-ACCESS read-only
       STATUS current
       DESCRIPTION
           "Total number of outbound registrations.
AC INI-Param: N/A"
       ::= {acKpiOtherStatsCurrentIpGroupEntry 5}



     acKpiOtherStatsCurrentIpGroupRegisterRateOut OBJECT-TYPE
       SYNTAX Gauge32
       MAX-ACCESS read-only
       STATUS current
       DESCRIPTION
           "Rate of outbound registrations (registrations per second).
AC INI-Param: N/A"
       ::= {acKpiOtherStatsCurrentIpGroupEntry 6}



     acKpiOtherStatsCurrentIpGroupActiveSubscribes OBJECT-TYPE
       SYNTAX Gauge32
       MAX-ACCESS read-only
       STATUS current
       DESCRIPTION
           "Number of active SUBSCRIBE dialogs.
AC INI-Param: N/A"
       ::= {acKpiOtherStatsCurrentIpGroupEntry 7}



     acKpiOtherStatsCurrentIpGroupSubscribeRateIn OBJECT-TYPE
       SYNTAX Gauge32
       MAX-ACCESS read-only
       STATUS current
       DESCRIPTION
           "Inbound SUBSCRIBE Rate (dialogs per second).
AC INI-Param: N/A"
       ::= {acKpiOtherStatsCurrentIpGroupEntry 8}



     acKpiOtherStatsCurrentIpGroupSubscribeRateOut OBJECT-TYPE
       SYNTAX Gauge32
       MAX-ACCESS read-only
       STATUS current
       DESCRIPTION
           "Outbound SUBSCRIBE Rate (dialogs per second).
AC INI-Param: N/A"
       ::= {acKpiOtherStatsCurrentIpGroupEntry 9}



     acKpiOtherStatsCurrentIpGroupOtherDialogs OBJECT-TYPE
       SYNTAX Gauge32
       MAX-ACCESS read-only
       STATUS current
       DESCRIPTION
           "Number of active other dialogs (not INVITE,SUBSCRIBE,REGISTER).
AC INI-Param: N/A"
       ::= {acKpiOtherStatsCurrentIpGroupEntry 10}



     acKpiOtherStatsCurrentIpGroupOtherDialogsRateIn OBJECT-TYPE
       SYNTAX Gauge32
       MAX-ACCESS read-only
       STATUS current
       DESCRIPTION
           "Inbound other dialogs rate (dialogs per second).
AC INI-Param: N/A"
       ::= {acKpiOtherStatsCurrentIpGroupEntry 11}



     acKpiOtherStatsCurrentIpGroupOtherDialogsRateOut OBJECT-TYPE
       SYNTAX Gauge32
       MAX-ACCESS read-only
       STATUS current
       DESCRIPTION
           "Outbound other dialogs rate (dialogs per second).
AC INI-Param: N/A"
       ::= {acKpiOtherStatsCurrentIpGroupEntry 12}



     acKpiOtherStatsCurrentIpGroupTransactionRate OBJECT-TYPE
       SYNTAX Gauge32
       MAX-ACCESS read-only
       STATUS current
       DESCRIPTION
           "SIP transactions rate (transactions per second).
AC INI-Param: N/A"
       ::= {acKpiOtherStatsCurrentIpGroupEntry 13}



     acKpiOtherStatsCurrentIpGroupSbcSuccessfulRegistrationsTotal OBJECT-TYPE
       SYNTAX Counter64
       MAX-ACCESS read-only
       STATUS current
       DESCRIPTION
           "Total number of successful SBC-initiated outbound REGISTER dialogs.
AC INI-Param: N/A"
       ::= {acKpiOtherStatsCurrentIpGroupEntry 14}



     acKpiOtherStatsCurrentIpGroupSbcRegistrationSuccessRatio OBJECT-TYPE
       SYNTAX Gauge32
       MAX-ACCESS read-only
       STATUS current
       DESCRIPTION
           "Success ratio for SBC-initiated REGISTER dialogs (%).
AC INI-Param: N/A"
       ::= {acKpiOtherStatsCurrentIpGroupEntry 15}



     acKpiOtherStatsCurrentIpGroupSbcAttemptedRegistrationsTotal OBJECT-TYPE
       SYNTAX Counter64
       MAX-ACCESS read-only
       STATUS current
       DESCRIPTION
           "Total number of SBC-initiated outbound REGISTER dialogs.
AC INI-Param: N/A"
       ::= {acKpiOtherStatsCurrentIpGroupEntry 16}



     acKpiOtherStatsCurrentIpGroupUserRegistrationSuccessRatio OBJECT-TYPE
       SYNTAX Gauge32
       MAX-ACCESS read-only
       STATUS current
       DESCRIPTION
           "Success ratio for user-initiated REGISTER dialogs (%).
AC INI-Param: N/A"
       ::= {acKpiOtherStatsCurrentIpGroupEntry 17}



     acKpiOtherStatsCurrentIpGroupUserSuccessfulRegistrationsTotal OBJECT-TYPE
       SYNTAX Counter64
       MAX-ACCESS read-only
       STATUS current
       DESCRIPTION
           "Total number of successful user-initiated inbound REGISTER dialogs.
AC INI-Param: N/A"
       ::= {acKpiOtherStatsCurrentIpGroupEntry 18}



     acKpiOtherStatsCurrentIpGroupFailedOtherDialogsOutTotal OBJECT-TYPE
       SYNTAX Counter64
       MAX-ACCESS read-only
       STATUS current
       DESCRIPTION
           "Total number of Failed Outbound other dialogs.
AC INI-Param: N/A"
       ::= {acKpiOtherStatsCurrentIpGroupEntry 19}



     acKpiOtherStatsCurrentIpGroupFailedOtherDialogsInTotal OBJECT-TYPE
       SYNTAX Counter64
       MAX-ACCESS read-only
       STATUS current
       DESCRIPTION
           "Total number of Failed Inbound other dialogs.
AC INI-Param: N/A"
       ::= {acKpiOtherStatsCurrentIpGroupEntry 20}



     acKpiOtherStatsCurrentIpGroupFailedSubscribeOutTotal OBJECT-TYPE
       SYNTAX Counter64
       MAX-ACCESS read-only
       STATUS current
       DESCRIPTION
           "Total number of Failed Outbound SUBSCRIBE dialogs.
AC INI-Param: N/A"
       ::= {acKpiOtherStatsCurrentIpGroupEntry 21}



     acKpiOtherStatsCurrentIpGroupFailedSubscribeInTotal OBJECT-TYPE
       SYNTAX Counter64
       MAX-ACCESS read-only
       STATUS current
       DESCRIPTION
           "Total number of Failed Inbound SUBSCRIBE dialogs.
AC INI-Param: N/A"
       ::= {acKpiOtherStatsCurrentIpGroupEntry 22}



     acKpiOtherStatsCurrentIpGroupFailedRegisterOtherOutTotal OBJECT-TYPE
       SYNTAX Counter64
       MAX-ACCESS read-only
       STATUS current
       DESCRIPTION
           "Total number of outbound REGISTER dialogs failed due to other
reasons.
AC INI-Param: N/A"
       ::= {acKpiOtherStatsCurrentIpGroupEntry 23}



     acKpiOtherStatsCurrentIpGroupFailedRegisterOtherInTotal OBJECT-TYPE
       SYNTAX Counter64
       MAX-ACCESS read-only
       STATUS current
       DESCRIPTION
           "Total number of inbound REGISTER dialogs failed due to other
reasons.
AC INI-Param: N/A"
       ::= {acKpiOtherStatsCurrentIpGroupEntry 24}



     acKpiOtherStatsCurrentIpGroupFailedRegisterNoRouteInTotal OBJECT-TYPE
       SYNTAX Counter64
       MAX-ACCESS read-only
       STATUS current
       DESCRIPTION
           "Total number of inbound REGISTER dialogs failed due to routing
failure.
AC INI-Param: N/A"
       ::= {acKpiOtherStatsCurrentIpGroupEntry 25}



     acKpiOtherStatsCurrentIpGroupFailedRegisterAdmissionOutTotal OBJECT-TYPE
       SYNTAX Counter64
       MAX-ACCESS read-only
       STATUS current
       DESCRIPTION
           "Total number of outbound REGISTER dialogs failed due to admission
control (CAC).
AC INI-Param: N/A"
       ::= {acKpiOtherStatsCurrentIpGroupEntry 26}



     acKpiOtherStatsCurrentIpGroupFailedRegisterAdmissionInTotal OBJECT-TYPE
       SYNTAX Counter64
       MAX-ACCESS read-only
       STATUS current
       DESCRIPTION
           "Total number of inbound REGISTER dialogs failed due to admission
control (CAC).
AC INI-Param: N/A"
       ::= {acKpiOtherStatsCurrentIpGroupEntry 27}



     acKpiOtherStatsCurrentIpGroupFailedRegisterOutTotal OBJECT-TYPE
       SYNTAX Counter64
       MAX-ACCESS read-only
       STATUS current
       DESCRIPTION
           "Total number of failed outbound REGISTER dialogs.
AC INI-Param: N/A"
       ::= {acKpiOtherStatsCurrentIpGroupEntry 28}



     acKpiOtherStatsCurrentIpGroupFailedRegisterInTotal OBJECT-TYPE
       SYNTAX Counter64
       MAX-ACCESS read-only
       STATUS current
       DESCRIPTION
           "Total number of failed inbound REGISTER dialogs.
AC INI-Param: N/A"
       ::= {acKpiOtherStatsCurrentIpGroupEntry 29}



     acKpiOtherStatsCurrentIpGroupOtherDialogsOutTotal OBJECT-TYPE
       SYNTAX Counter64
       MAX-ACCESS read-only
       STATUS current
       DESCRIPTION
           "Total number of outbound other requests (not INVITE,SUBSCRIBE,REGISTER).
AC INI-Param: N/A"
       ::= {acKpiOtherStatsCurrentIpGroupEntry 30}



     acKpiOtherStatsCurrentIpGroupOtherDialogsInTotal OBJECT-TYPE
       SYNTAX Counter64
       MAX-ACCESS read-only
       STATUS current
       DESCRIPTION
           "Total number of inbound other requests (not INVITE,SUBSCRIBE,REGISTER).
AC INI-Param: N/A"
       ::= {acKpiOtherStatsCurrentIpGroupEntry 31}



     acKpiOtherStatsCurrentIpGroupSubscribeOutTotal OBJECT-TYPE
       SYNTAX Counter64
       MAX-ACCESS read-only
       STATUS current
       DESCRIPTION
           "Total number of outbound SUBSCRIBE requests.
AC INI-Param: N/A"
       ::= {acKpiOtherStatsCurrentIpGroupEntry 32}



     acKpiOtherStatsCurrentIpGroupSubscribeInTotal OBJECT-TYPE
       SYNTAX Counter64
       MAX-ACCESS read-only
       STATUS current
       DESCRIPTION
           "Total number of inbound SUBSCRIBE requests.
AC INI-Param: N/A"
       ::= {acKpiOtherStatsCurrentIpGroupEntry 33}



     -- ****************************************
     -- acKpiOtherStatsCurrentSrd table declaration
     -- ****************************************
     acKpiOtherStatsCurrentSrdTable OBJECT-TYPE
       SYNTAX SEQUENCE OF AcKpiOtherStatsCurrentSrdEntry
       MAX-ACCESS not-accessible
       STATUS current
       DESCRIPTION
           ""
       ::= {acKpiOtherStatsCurrentTables 2}



     -- ****************************************
     -- acKpiOtherStatsCurrentSrd table entry
     -- ****************************************
     acKpiOtherStatsCurrentSrdEntry OBJECT-TYPE
       SYNTAX AcKpiOtherStatsCurrentSrdEntry
       MAX-ACCESS not-accessible
       STATUS current
       DESCRIPTION
           ""
       INDEX {acKpiOtherStatsCurrentSrdIndex}
       ::= {acKpiOtherStatsCurrentSrdTable 1}



     -- ****************************************
     -- acKpiOtherStatsCurrentSrd TABLE
     -- ****************************************
     AcKpiOtherStatsCurrentSrdEntry ::= SEQUENCE {
       acKpiOtherStatsCurrentSrdIndex                  Unsigned32,
       acKpiOtherStatsCurrentSrdRegisteredUsers        Gauge32,
       acKpiOtherStatsCurrentSrdRegisterInTotal        Counter64,
       acKpiOtherStatsCurrentSrdRegisterRateIn         Gauge32,
       acKpiOtherStatsCurrentSrdRegisterOutTotal       Counter64,
       acKpiOtherStatsCurrentSrdRegisterRateOut        Gauge32,
       acKpiOtherStatsCurrentSrdActiveSubscribes       Gauge32,
       acKpiOtherStatsCurrentSrdSubscribeRateIn        Gauge32,
       acKpiOtherStatsCurrentSrdSubscribeRateOut       Gauge32,
       acKpiOtherStatsCurrentSrdOtherDialogs           Gauge32,
       acKpiOtherStatsCurrentSrdOtherDialogsRateIn     Gauge32,
       acKpiOtherStatsCurrentSrdOtherDialogsRateOut    Gauge32,
       acKpiOtherStatsCurrentSrdTransactionRate        Gauge32,
       acKpiOtherStatsCurrentSrdSbcSuccessfulRegistrationsTotal 
                                                       Counter64,
       acKpiOtherStatsCurrentSrdSbcRegistrationSuccessRatio 
                                                       Gauge32,
       acKpiOtherStatsCurrentSrdSbcAttemptedRegistrationsTotal 
                                                       Counter64,
       acKpiOtherStatsCurrentSrdUserRegistrationSuccessRatio 
                                                       Gauge32,
       acKpiOtherStatsCurrentSrdUserSuccessfulRegistrationsTotal 
                                                       Counter64,
       acKpiOtherStatsCurrentSrdFailedOtherDialogsOutTotal 
                                                       Counter64,
       acKpiOtherStatsCurrentSrdFailedOtherDialogsInTotal 
                                                       Counter64,
       acKpiOtherStatsCurrentSrdFailedSubscribeOutTotal 
                                                       Counter64,
       acKpiOtherStatsCurrentSrdFailedSubscribeInTotal Counter64,
       acKpiOtherStatsCurrentSrdFailedRegisterOtherOutTotal 
                                                       Counter64,
       acKpiOtherStatsCurrentSrdFailedRegisterOtherInTotal 
                                                       Counter64,
       acKpiOtherStatsCurrentSrdFailedRegisterClassificationInTotal 
                                                       Counter64,
       acKpiOtherStatsCurrentSrdFailedRegisterNoRouteInTotal 
                                                       Counter64,
       acKpiOtherStatsCurrentSrdFailedRegisterAdmissionOutTotal 
                                                       Counter64,
       acKpiOtherStatsCurrentSrdFailedRegisterAdmissionInTotal 
                                                       Counter64,
       acKpiOtherStatsCurrentSrdFailedRegisterOutTotal Counter64,
       acKpiOtherStatsCurrentSrdFailedRegisterInTotal  Counter64,
       acKpiOtherStatsCurrentSrdOtherDialogsOutTotal   Counter64,
       acKpiOtherStatsCurrentSrdOtherDialogsInTotal    Counter64,
       acKpiOtherStatsCurrentSrdSubscribeOutTotal      Counter64,
       acKpiOtherStatsCurrentSrdSubscribeInTotal       Counter64
     }



     acKpiOtherStatsCurrentSrdIndex OBJECT-TYPE
       SYNTAX Unsigned32 (0..32767)
       MAX-ACCESS not-accessible
       STATUS current
       DESCRIPTION
           "
AC INI-Param: N/A"
       ::= {acKpiOtherStatsCurrentSrdEntry 1}



     acKpiOtherStatsCurrentSrdRegisteredUsers OBJECT-TYPE
       SYNTAX Gauge32
       MAX-ACCESS read-only
       STATUS current
       DESCRIPTION
           "Number of registered users.
AC INI-Param: N/A"
       ::= {acKpiOtherStatsCurrentSrdEntry 2}



     acKpiOtherStatsCurrentSrdRegisterInTotal OBJECT-TYPE
       SYNTAX Counter64
       MAX-ACCESS read-only
       STATUS current
       DESCRIPTION
           "Total number of inbound registrations.
AC INI-Param: N/A"
       ::= {acKpiOtherStatsCurrentSrdEntry 3}



     acKpiOtherStatsCurrentSrdRegisterRateIn OBJECT-TYPE
       SYNTAX Gauge32
       MAX-ACCESS read-only
       STATUS current
       DESCRIPTION
           "Rate of inbound registrations (registrations per second).
AC INI-Param: N/A"
       ::= {acKpiOtherStatsCurrentSrdEntry 4}



     acKpiOtherStatsCurrentSrdRegisterOutTotal OBJECT-TYPE
       SYNTAX Counter64
       MAX-ACCESS read-only
       STATUS current
       DESCRIPTION
           "Total number of outbound registrations.
AC INI-Param: N/A"
       ::= {acKpiOtherStatsCurrentSrdEntry 5}



     acKpiOtherStatsCurrentSrdRegisterRateOut OBJECT-TYPE
       SYNTAX Gauge32
       MAX-ACCESS read-only
       STATUS current
       DESCRIPTION
           "Rate of outbound registrations (registrations per second).
AC INI-Param: N/A"
       ::= {acKpiOtherStatsCurrentSrdEntry 6}



     acKpiOtherStatsCurrentSrdActiveSubscribes OBJECT-TYPE
       SYNTAX Gauge32
       MAX-ACCESS read-only
       STATUS current
       DESCRIPTION
           "Number of active SUBSCRIBE dialogs.
AC INI-Param: N/A"
       ::= {acKpiOtherStatsCurrentSrdEntry 7}



     acKpiOtherStatsCurrentSrdSubscribeRateIn OBJECT-TYPE
       SYNTAX Gauge32
       MAX-ACCESS read-only
       STATUS current
       DESCRIPTION
           "Inbound SUBSCRIBE Rate (dialogs per second).
AC INI-Param: N/A"
       ::= {acKpiOtherStatsCurrentSrdEntry 8}



     acKpiOtherStatsCurrentSrdSubscribeRateOut OBJECT-TYPE
       SYNTAX Gauge32
       MAX-ACCESS read-only
       STATUS current
       DESCRIPTION
           "Outbound SUBSCRIBE Rate (dialogs per second).
AC INI-Param: N/A"
       ::= {acKpiOtherStatsCurrentSrdEntry 9}



     acKpiOtherStatsCurrentSrdOtherDialogs OBJECT-TYPE
       SYNTAX Gauge32
       MAX-ACCESS read-only
       STATUS current
       DESCRIPTION
           "Number of active other dialogs (not INVITE,SUBSCRIBE,REGISTER).
AC INI-Param: N/A"
       ::= {acKpiOtherStatsCurrentSrdEntry 10}



     acKpiOtherStatsCurrentSrdOtherDialogsRateIn OBJECT-TYPE
       SYNTAX Gauge32
       MAX-ACCESS read-only
       STATUS current
       DESCRIPTION
           "Inbound other dialogs rate (dialogs per second).
AC INI-Param: N/A"
       ::= {acKpiOtherStatsCurrentSrdEntry 11}



     acKpiOtherStatsCurrentSrdOtherDialogsRateOut OBJECT-TYPE
       SYNTAX Gauge32
       MAX-ACCESS read-only
       STATUS current
       DESCRIPTION
           "Outbound other dialogs rate (dialogs per second).
AC INI-Param: N/A"
       ::= {acKpiOtherStatsCurrentSrdEntry 12}



     acKpiOtherStatsCurrentSrdTransactionRate OBJECT-TYPE
       SYNTAX Gauge32
       MAX-ACCESS read-only
       STATUS current
       DESCRIPTION
           "SIP transactions rate (transactions per second).
AC INI-Param: N/A"
       ::= {acKpiOtherStatsCurrentSrdEntry 13}



     acKpiOtherStatsCurrentSrdSbcSuccessfulRegistrationsTotal OBJECT-TYPE
       SYNTAX Counter64
       MAX-ACCESS read-only
       STATUS current
       DESCRIPTION
           "Total number of successful SBC-initiated outbound REGISTER dialogs.
AC INI-Param: N/A"
       ::= {acKpiOtherStatsCurrentSrdEntry 14}



     acKpiOtherStatsCurrentSrdSbcRegistrationSuccessRatio OBJECT-TYPE
       SYNTAX Gauge32
       MAX-ACCESS read-only
       STATUS current
       DESCRIPTION
           "Success ratio for SBC-initiated REGISTER dialogs (%).
AC INI-Param: N/A"
       ::= {acKpiOtherStatsCurrentSrdEntry 15}



     acKpiOtherStatsCurrentSrdSbcAttemptedRegistrationsTotal OBJECT-TYPE
       SYNTAX Counter64
       MAX-ACCESS read-only
       STATUS current
       DESCRIPTION
           "Total number of SBC-initiated outbound REGISTER dialogs.
AC INI-Param: N/A"
       ::= {acKpiOtherStatsCurrentSrdEntry 16}



     acKpiOtherStatsCurrentSrdUserRegistrationSuccessRatio OBJECT-TYPE
       SYNTAX Gauge32
       MAX-ACCESS read-only
       STATUS current
       DESCRIPTION
           "Success ratio for user-initiated REGISTER dialogs (%).
AC INI-Param: N/A"
       ::= {acKpiOtherStatsCurrentSrdEntry 17}



     acKpiOtherStatsCurrentSrdUserSuccessfulRegistrationsTotal OBJECT-TYPE
       SYNTAX Counter64
       MAX-ACCESS read-only
       STATUS current
       DESCRIPTION
           "Total number of successful user-initiated inbound REGISTER dialogs.
AC INI-Param: N/A"
       ::= {acKpiOtherStatsCurrentSrdEntry 18}



     acKpiOtherStatsCurrentSrdFailedOtherDialogsOutTotal OBJECT-TYPE
       SYNTAX Counter64
       MAX-ACCESS read-only
       STATUS current
       DESCRIPTION
           "Total number of Failed Outbound other dialogs.
AC INI-Param: N/A"
       ::= {acKpiOtherStatsCurrentSrdEntry 19}



     acKpiOtherStatsCurrentSrdFailedOtherDialogsInTotal OBJECT-TYPE
       SYNTAX Counter64
       MAX-ACCESS read-only
       STATUS current
       DESCRIPTION
           "Total number of Failed Inbound other dialogs.
AC INI-Param: N/A"
       ::= {acKpiOtherStatsCurrentSrdEntry 20}



     acKpiOtherStatsCurrentSrdFailedSubscribeOutTotal OBJECT-TYPE
       SYNTAX Counter64
       MAX-ACCESS read-only
       STATUS current
       DESCRIPTION
           "Total number of Failed Outbound SUBSCRIBE dialogs.
AC INI-Param: N/A"
       ::= {acKpiOtherStatsCurrentSrdEntry 21}



     acKpiOtherStatsCurrentSrdFailedSubscribeInTotal OBJECT-TYPE
       SYNTAX Counter64
       MAX-ACCESS read-only
       STATUS current
       DESCRIPTION
           "Total number of Failed Inbound SUBSCRIBE dialogs.
AC INI-Param: N/A"
       ::= {acKpiOtherStatsCurrentSrdEntry 22}



     acKpiOtherStatsCurrentSrdFailedRegisterOtherOutTotal OBJECT-TYPE
       SYNTAX Counter64
       MAX-ACCESS read-only
       STATUS current
       DESCRIPTION
           "Total number of outbound REGISTER dialogs failed due to other
reasons.
AC INI-Param: N/A"
       ::= {acKpiOtherStatsCurrentSrdEntry 23}



     acKpiOtherStatsCurrentSrdFailedRegisterOtherInTotal OBJECT-TYPE
       SYNTAX Counter64
       MAX-ACCESS read-only
       STATUS current
       DESCRIPTION
           "Total number of inbound REGISTER dialogs failed due to other
reasons.
AC INI-Param: N/A"
       ::= {acKpiOtherStatsCurrentSrdEntry 24}



     acKpiOtherStatsCurrentSrdFailedRegisterClassificationInTotal OBJECT-TYPE
       SYNTAX Counter64
       MAX-ACCESS read-only
       STATUS current
       DESCRIPTION
           "Total number of inbound REGISTER dialogs failed due to classification
failure.
AC INI-Param: N/A"
       ::= {acKpiOtherStatsCurrentSrdEntry 25}



     acKpiOtherStatsCurrentSrdFailedRegisterNoRouteInTotal OBJECT-TYPE
       SYNTAX Counter64
       MAX-ACCESS read-only
       STATUS current
       DESCRIPTION
           "Total number of inbound REGISTER dialogs failed due to routing
failure.
AC INI-Param: N/A"
       ::= {acKpiOtherStatsCurrentSrdEntry 26}



     acKpiOtherStatsCurrentSrdFailedRegisterAdmissionOutTotal OBJECT-TYPE
       SYNTAX Counter64
       MAX-ACCESS read-only
       STATUS current
       DESCRIPTION
           "Total number of outbound REGISTER dialogs failed due to admission
control (CAC).
AC INI-Param: N/A"
       ::= {acKpiOtherStatsCurrentSrdEntry 27}



     acKpiOtherStatsCurrentSrdFailedRegisterAdmissionInTotal OBJECT-TYPE
       SYNTAX Counter64
       MAX-ACCESS read-only
       STATUS current
       DESCRIPTION
           "Total number of inbound REGISTER dialogs failed due to admission
control (CAC).
AC INI-Param: N/A"
       ::= {acKpiOtherStatsCurrentSrdEntry 28}



     acKpiOtherStatsCurrentSrdFailedRegisterOutTotal OBJECT-TYPE
       SYNTAX Counter64
       MAX-ACCESS read-only
       STATUS current
       DESCRIPTION
           "Total number of failed outbound REGISTER dialogs.
AC INI-Param: N/A"
       ::= {acKpiOtherStatsCurrentSrdEntry 29}



     acKpiOtherStatsCurrentSrdFailedRegisterInTotal OBJECT-TYPE
       SYNTAX Counter64
       MAX-ACCESS read-only
       STATUS current
       DESCRIPTION
           "Total number of failed inbound REGISTER dialogs.
AC INI-Param: N/A"
       ::= {acKpiOtherStatsCurrentSrdEntry 30}



     acKpiOtherStatsCurrentSrdOtherDialogsOutTotal OBJECT-TYPE
       SYNTAX Counter64
       MAX-ACCESS read-only
       STATUS current
       DESCRIPTION
           "Total number of outbound other requests (not INVITE,SUBSCRIBE,REGISTER).
AC INI-Param: N/A"
       ::= {acKpiOtherStatsCurrentSrdEntry 31}



     acKpiOtherStatsCurrentSrdOtherDialogsInTotal OBJECT-TYPE
       SYNTAX Counter64
       MAX-ACCESS read-only
       STATUS current
       DESCRIPTION
           "Total number of inbound other requests (not INVITE,SUBSCRIBE,REGISTER).
AC INI-Param: N/A"
       ::= {acKpiOtherStatsCurrentSrdEntry 32}



     acKpiOtherStatsCurrentSrdSubscribeOutTotal OBJECT-TYPE
       SYNTAX Counter64
       MAX-ACCESS read-only
       STATUS current
       DESCRIPTION
           "Total number of outbound SUBSCRIBE requests.
AC INI-Param: N/A"
       ::= {acKpiOtherStatsCurrentSrdEntry 33}



     acKpiOtherStatsCurrentSrdSubscribeInTotal OBJECT-TYPE
       SYNTAX Counter64
       MAX-ACCESS read-only
       STATUS current
       DESCRIPTION
           "Total number of inbound SUBSCRIBE requests.
AC INI-Param: N/A"
       ::= {acKpiOtherStatsCurrentSrdEntry 34}



     acKpiOtherStatsInterval OBJECT IDENTIFIER ::= {acKpiOtherStats 2}


     acKpiOtherStatsIntervalGlobal OBJECT IDENTIFIER ::= {acKpiOtherStatsInterval 1}


     -- ****************************************
     -- acKpiOtherStatsIntervalGlobal table declaration
     -- ****************************************
     acKpiOtherStatsIntervalGlobalTable OBJECT-TYPE
       SYNTAX SEQUENCE OF AcKpiOtherStatsIntervalGlobalEntry
       MAX-ACCESS not-accessible
       STATUS current
       DESCRIPTION
           ""
       ::= {acKpiOtherStatsIntervalGlobal 1}



     -- ****************************************
     -- acKpiOtherStatsIntervalGlobal table entry
     -- ****************************************
     acKpiOtherStatsIntervalGlobalEntry OBJECT-TYPE
       SYNTAX AcKpiOtherStatsIntervalGlobalEntry
       MAX-ACCESS not-accessible
       STATUS current
       DESCRIPTION
           ""
       INDEX {acKpiOtherStatsIntervalGlobalInterval}
       ::= {acKpiOtherStatsIntervalGlobalTable 1}



     -- ****************************************
     -- acKpiOtherStatsIntervalGlobal TABLE
     -- ****************************************
     AcKpiOtherStatsIntervalGlobalEntry ::= SEQUENCE {
       acKpiOtherStatsIntervalGlobalInterval           Unsigned32,
       acKpiOtherStatsIntervalGlobalRegisteredUsersAvg Gauge32,
       acKpiOtherStatsIntervalGlobalRegisteredUsersMax Gauge32,
       acKpiOtherStatsIntervalGlobalRegisterIn         Counter64,
       acKpiOtherStatsIntervalGlobalRegisterRateInAvg  Gauge32,
       acKpiOtherStatsIntervalGlobalRegisterRateInMax  Gauge32,
       acKpiOtherStatsIntervalGlobalRegisterOut        Counter64,
       acKpiOtherStatsIntervalGlobalRegisterRateOutAvg Gauge32,
       acKpiOtherStatsIntervalGlobalRegisterRateOutMax Gauge32,
       acKpiOtherStatsIntervalGlobalActiveSubscribesAvg 
                                                       Gauge32,
       acKpiOtherStatsIntervalGlobalActiveSubscribesMax 
                                                       Gauge32,
       acKpiOtherStatsIntervalGlobalSubscribeRateInAvg Gauge32,
       acKpiOtherStatsIntervalGlobalSubscribeRateInMax Gauge32,
       acKpiOtherStatsIntervalGlobalSubscribeRateOutAvg 
                                                       Gauge32,
       acKpiOtherStatsIntervalGlobalSubscribeRateOutMax 
                                                       Gauge32,
       acKpiOtherStatsIntervalGlobalOtherDialogsAvg    Gauge32,
       acKpiOtherStatsIntervalGlobalOtherDialogsRateInAvg 
                                                       Gauge32,
       acKpiOtherStatsIntervalGlobalOtherDialogsRateInMax 
                                                       Gauge32,
       acKpiOtherStatsIntervalGlobalOtherDialogsRateOutAvg 
                                                       Gauge32,
       acKpiOtherStatsIntervalGlobalOtherDialogsRateOutMax 
                                                       Gauge32,
       acKpiOtherStatsIntervalGlobalTransactionRateAvg Gauge32,
       acKpiOtherStatsIntervalGlobalTransactionRateMax Gauge32,
       acKpiOtherStatsIntervalGlobalSbcSuccessfulRegistrations 
                                                       Counter64,
       acKpiOtherStatsIntervalGlobalSbcRegistrationSuccessRatioAvg 
                                                       Gauge32,
       acKpiOtherStatsIntervalGlobalSbcAttemptedRegistrations 
                                                       Counter64,
       acKpiOtherStatsIntervalGlobalUserRegistrationSuccessRatioAvg 
                                                       Gauge32,
       acKpiOtherStatsIntervalGlobalUserSuccessfulRegistrations 
                                                       Counter64,
       acKpiOtherStatsIntervalGlobalFailedOtherDialogsOut 
                                                       Counter64,
       acKpiOtherStatsIntervalGlobalFailedOtherDialogsIn 
                                                       Counter64,
       acKpiOtherStatsIntervalGlobalFailedSubscribeOut Counter64,
       acKpiOtherStatsIntervalGlobalFailedSubscribeIn  Counter64,
       acKpiOtherStatsIntervalGlobalFailedRegisterOtherOut 
                                                       Counter64,
       acKpiOtherStatsIntervalGlobalFailedRegisterOtherIn 
                                                       Counter64,
       acKpiOtherStatsIntervalGlobalFailedRegisterClassificationIn 
                                                       Counter64,
       acKpiOtherStatsIntervalGlobalFailedRegisterNoRouteIn 
                                                       Counter64,
       acKpiOtherStatsIntervalGlobalFailedRegisterAdmissionOut 
                                                       Counter64,
       acKpiOtherStatsIntervalGlobalFailedRegisterAdmissionIn 
                                                       Counter64,
       acKpiOtherStatsIntervalGlobalFailedRegisterOut  Counter64,
       acKpiOtherStatsIntervalGlobalFailedRegisterIn   Counter64,
       acKpiOtherStatsIntervalGlobalOtherDialogsOut    Counter64,
       acKpiOtherStatsIntervalGlobalOtherDialogsIn     Counter64,
       acKpiOtherStatsIntervalGlobalSubscribeOut       Counter64,
       acKpiOtherStatsIntervalGlobalSubscribeIn        Counter64
     }



     acKpiOtherStatsIntervalGlobalInterval OBJECT-TYPE
       SYNTAX Unsigned32 (1..200)
       MAX-ACCESS not-accessible
       STATUS current
       DESCRIPTION
           "
AC INI-Param: N/A"
       ::= {acKpiOtherStatsIntervalGlobalEntry 1}



     acKpiOtherStatsIntervalGlobalRegisteredUsersAvg OBJECT-TYPE
       SYNTAX Gauge32
       MAX-ACCESS read-only
       STATUS current
       DESCRIPTION
           "Average number of registered users.
AC INI-Param: N/A"
       ::= {acKpiOtherStatsIntervalGlobalEntry 2}



     acKpiOtherStatsIntervalGlobalRegisteredUsersMax OBJECT-TYPE
       SYNTAX Gauge32
       MAX-ACCESS read-only
       STATUS current
       DESCRIPTION
           "Maximum number of registered users.
AC INI-Param: N/A"
       ::= {acKpiOtherStatsIntervalGlobalEntry 3}



     acKpiOtherStatsIntervalGlobalRegisterIn OBJECT-TYPE
       SYNTAX Counter64
       MAX-ACCESS read-only
       STATUS current
       DESCRIPTION
           "Number of inbound registrations.
AC INI-Param: N/A"
       ::= {acKpiOtherStatsIntervalGlobalEntry 4}



     acKpiOtherStatsIntervalGlobalRegisterRateInAvg OBJECT-TYPE
       SYNTAX Gauge32
       MAX-ACCESS read-only
       STATUS current
       DESCRIPTION
           "Average rate of inbound registrations (registrations per second).
AC INI-Param: N/A"
       ::= {acKpiOtherStatsIntervalGlobalEntry 5}



     acKpiOtherStatsIntervalGlobalRegisterRateInMax OBJECT-TYPE
       SYNTAX Gauge32
       MAX-ACCESS read-only
       STATUS current
       DESCRIPTION
           "Maximum rate of inbound registrations (registrations per second).
AC INI-Param: N/A"
       ::= {acKpiOtherStatsIntervalGlobalEntry 6}



     acKpiOtherStatsIntervalGlobalRegisterOut OBJECT-TYPE
       SYNTAX Counter64
       MAX-ACCESS read-only
       STATUS current
       DESCRIPTION
           "Number of outbound registrations.
AC INI-Param: N/A"
       ::= {acKpiOtherStatsIntervalGlobalEntry 7}



     acKpiOtherStatsIntervalGlobalRegisterRateOutAvg OBJECT-TYPE
       SYNTAX Gauge32
       MAX-ACCESS read-only
       STATUS current
       DESCRIPTION
           "Average rate of outbound registrations (registrations per second).
AC INI-Param: N/A"
       ::= {acKpiOtherStatsIntervalGlobalEntry 8}



     acKpiOtherStatsIntervalGlobalRegisterRateOutMax OBJECT-TYPE
       SYNTAX Gauge32
       MAX-ACCESS read-only
       STATUS current
       DESCRIPTION
           "Maximum rate of outbound registrations (registrations per second).
AC INI-Param: N/A"
       ::= {acKpiOtherStatsIntervalGlobalEntry 9}



     acKpiOtherStatsIntervalGlobalActiveSubscribesAvg OBJECT-TYPE
       SYNTAX Gauge32
       MAX-ACCESS read-only
       STATUS current
       DESCRIPTION
           "Average number of active SUBSCRIBE dialogs.
AC INI-Param: N/A"
       ::= {acKpiOtherStatsIntervalGlobalEntry 10}



     acKpiOtherStatsIntervalGlobalActiveSubscribesMax OBJECT-TYPE
       SYNTAX Gauge32
       MAX-ACCESS read-only
       STATUS current
       DESCRIPTION
           "Maximum number of active SUBSCRIBE dialogs.
AC INI-Param: N/A"
       ::= {acKpiOtherStatsIntervalGlobalEntry 11}



     acKpiOtherStatsIntervalGlobalSubscribeRateInAvg OBJECT-TYPE
       SYNTAX Gauge32
       MAX-ACCESS read-only
       STATUS current
       DESCRIPTION
           "Average inbound SUBSCRIBE Rate (dialogs per second).
AC INI-Param: N/A"
       ::= {acKpiOtherStatsIntervalGlobalEntry 12}



     acKpiOtherStatsIntervalGlobalSubscribeRateInMax OBJECT-TYPE
       SYNTAX Gauge32
       MAX-ACCESS read-only
       STATUS current
       DESCRIPTION
           "Maximum inbound SUBSCRIBE Rate (dialogs per second).
AC INI-Param: N/A"
       ::= {acKpiOtherStatsIntervalGlobalEntry 13}



     acKpiOtherStatsIntervalGlobalSubscribeRateOutAvg OBJECT-TYPE
       SYNTAX Gauge32
       MAX-ACCESS read-only
       STATUS current
       DESCRIPTION
           "Average outbound SUBSCRIBE Rate (dialogs per second).
AC INI-Param: N/A"
       ::= {acKpiOtherStatsIntervalGlobalEntry 14}



     acKpiOtherStatsIntervalGlobalSubscribeRateOutMax OBJECT-TYPE
       SYNTAX Gauge32
       MAX-ACCESS read-only
       STATUS current
       DESCRIPTION
           "Maximum outbound SUBSCRIBE Rate (dialogs per second).
AC INI-Param: N/A"
       ::= {acKpiOtherStatsIntervalGlobalEntry 15}



     acKpiOtherStatsIntervalGlobalOtherDialogsAvg OBJECT-TYPE
       SYNTAX Gauge32
       MAX-ACCESS read-only
       STATUS current
       DESCRIPTION
           "Average number of active other dialogs (not INVITE,SUBSCRIBE,REGISTER).
AC INI-Param: N/A"
       ::= {acKpiOtherStatsIntervalGlobalEntry 16}



     acKpiOtherStatsIntervalGlobalOtherDialogsRateInAvg OBJECT-TYPE
       SYNTAX Gauge32
       MAX-ACCESS read-only
       STATUS current
       DESCRIPTION
           "Average inbound other dialogs rate (dialogs per second).
AC INI-Param: N/A"
       ::= {acKpiOtherStatsIntervalGlobalEntry 17}



     acKpiOtherStatsIntervalGlobalOtherDialogsRateInMax OBJECT-TYPE
       SYNTAX Gauge32
       MAX-ACCESS read-only
       STATUS current
       DESCRIPTION
           "Maximum inbound other dialogs rate (dialogs per second).
AC INI-Param: N/A"
       ::= {acKpiOtherStatsIntervalGlobalEntry 18}



     acKpiOtherStatsIntervalGlobalOtherDialogsRateOutAvg OBJECT-TYPE
       SYNTAX Gauge32
       MAX-ACCESS read-only
       STATUS current
       DESCRIPTION
           "Average outbound other dialogs rate (dialogs per second).
AC INI-Param: N/A"
       ::= {acKpiOtherStatsIntervalGlobalEntry 19}



     acKpiOtherStatsIntervalGlobalOtherDialogsRateOutMax OBJECT-TYPE
       SYNTAX Gauge32
       MAX-ACCESS read-only
       STATUS current
       DESCRIPTION
           "Maximum outbound other dialogs rate (dialogs per second).
AC INI-Param: N/A"
       ::= {acKpiOtherStatsIntervalGlobalEntry 20}



     acKpiOtherStatsIntervalGlobalTransactionRateAvg OBJECT-TYPE
       SYNTAX Gauge32
       MAX-ACCESS read-only
       STATUS current
       DESCRIPTION
           "Average SIP rransactions rate (transactions per second).
AC INI-Param: N/A"
       ::= {acKpiOtherStatsIntervalGlobalEntry 21}



     acKpiOtherStatsIntervalGlobalTransactionRateMax OBJECT-TYPE
       SYNTAX Gauge32
       MAX-ACCESS read-only
       STATUS current
       DESCRIPTION
           "Maximum SIP transactions rate (transactions per second).
AC INI-Param: N/A"
       ::= {acKpiOtherStatsIntervalGlobalEntry 22}



     acKpiOtherStatsIntervalGlobalSbcSuccessfulRegistrations OBJECT-TYPE
       SYNTAX Counter64
       MAX-ACCESS read-only
       STATUS current
       DESCRIPTION
           "Number of successful SBC-initiated outbound REGISTER dialogs.
AC INI-Param: N/A"
       ::= {acKpiOtherStatsIntervalGlobalEntry 23}



     acKpiOtherStatsIntervalGlobalSbcRegistrationSuccessRatioAvg OBJECT-TYPE
       SYNTAX Gauge32
       MAX-ACCESS read-only
       STATUS current
       DESCRIPTION
           "Average success ratio for SBC-initiated REGISTER dialogs (%).
AC INI-Param: N/A"
       ::= {acKpiOtherStatsIntervalGlobalEntry 24}



     acKpiOtherStatsIntervalGlobalSbcAttemptedRegistrations OBJECT-TYPE
       SYNTAX Counter64
       MAX-ACCESS read-only
       STATUS current
       DESCRIPTION
           "Number of SBC-initiated outbound REGISTER dialogs.
AC INI-Param: N/A"
       ::= {acKpiOtherStatsIntervalGlobalEntry 25}



     acKpiOtherStatsIntervalGlobalUserRegistrationSuccessRatioAvg OBJECT-TYPE
       SYNTAX Gauge32
       MAX-ACCESS read-only
       STATUS current
       DESCRIPTION
           "Average success ratio for user-initiated REGISTER dialogs (%).
AC INI-Param: N/A"
       ::= {acKpiOtherStatsIntervalGlobalEntry 26}



     acKpiOtherStatsIntervalGlobalUserSuccessfulRegistrations OBJECT-TYPE
       SYNTAX Counter64
       MAX-ACCESS read-only
       STATUS current
       DESCRIPTION
           "Number of successful user-initiated inbound REGISTER dialogs.
AC INI-Param: N/A"
       ::= {acKpiOtherStatsIntervalGlobalEntry 27}



     acKpiOtherStatsIntervalGlobalFailedOtherDialogsOut OBJECT-TYPE
       SYNTAX Counter64
       MAX-ACCESS read-only
       STATUS current
       DESCRIPTION
           "Number of Failed Outbound other dialogs.
AC INI-Param: N/A"
       ::= {acKpiOtherStatsIntervalGlobalEntry 28}



     acKpiOtherStatsIntervalGlobalFailedOtherDialogsIn OBJECT-TYPE
       SYNTAX Counter64
       MAX-ACCESS read-only
       STATUS current
       DESCRIPTION
           "Number of Failed Inbound other dialogs.
AC INI-Param: N/A"
       ::= {acKpiOtherStatsIntervalGlobalEntry 29}



     acKpiOtherStatsIntervalGlobalFailedSubscribeOut OBJECT-TYPE
       SYNTAX Counter64
       MAX-ACCESS read-only
       STATUS current
       DESCRIPTION
           "Number of Failed Outbound SUBSCRIBE dialogs.
AC INI-Param: N/A"
       ::= {acKpiOtherStatsIntervalGlobalEntry 30}



     acKpiOtherStatsIntervalGlobalFailedSubscribeIn OBJECT-TYPE
       SYNTAX Counter64
       MAX-ACCESS read-only
       STATUS current
       DESCRIPTION
           "Number of Failed Inbound SUBSCRIBE dialogs.
AC INI-Param: N/A"
       ::= {acKpiOtherStatsIntervalGlobalEntry 31}



     acKpiOtherStatsIntervalGlobalFailedRegisterOtherOut OBJECT-TYPE
       SYNTAX Counter64
       MAX-ACCESS read-only
       STATUS current
       DESCRIPTION
           "Number of outbound REGISTER dialogs failed due to other reasons.
AC INI-Param: N/A"
       ::= {acKpiOtherStatsIntervalGlobalEntry 32}



     acKpiOtherStatsIntervalGlobalFailedRegisterOtherIn OBJECT-TYPE
       SYNTAX Counter64
       MAX-ACCESS read-only
       STATUS current
       DESCRIPTION
           "Number of inbound REGISTER dialogs failed due to other reasons.
AC INI-Param: N/A"
       ::= {acKpiOtherStatsIntervalGlobalEntry 33}



     acKpiOtherStatsIntervalGlobalFailedRegisterClassificationIn OBJECT-TYPE
       SYNTAX Counter64
       MAX-ACCESS read-only
       STATUS current
       DESCRIPTION
           "Number of inbound REGISTER dialogs failed due to classification
failure.
AC INI-Param: N/A"
       ::= {acKpiOtherStatsIntervalGlobalEntry 34}



     acKpiOtherStatsIntervalGlobalFailedRegisterNoRouteIn OBJECT-TYPE
       SYNTAX Counter64
       MAX-ACCESS read-only
       STATUS current
       DESCRIPTION
           "Number of inbound REGISTER dialogs failed due to routing failure.
AC INI-Param: N/A"
       ::= {acKpiOtherStatsIntervalGlobalEntry 35}



     acKpiOtherStatsIntervalGlobalFailedRegisterAdmissionOut OBJECT-TYPE
       SYNTAX Counter64
       MAX-ACCESS read-only
       STATUS current
       DESCRIPTION
           "Number of outbound REGISTER dialogs failed due to admission
control (CAC).
AC INI-Param: N/A"
       ::= {acKpiOtherStatsIntervalGlobalEntry 36}



     acKpiOtherStatsIntervalGlobalFailedRegisterAdmissionIn OBJECT-TYPE
       SYNTAX Counter64
       MAX-ACCESS read-only
       STATUS current
       DESCRIPTION
           "Number of inbound REGISTER dialogs failed due to admission control
(CAC).
AC INI-Param: N/A"
       ::= {acKpiOtherStatsIntervalGlobalEntry 37}



     acKpiOtherStatsIntervalGlobalFailedRegisterOut OBJECT-TYPE
       SYNTAX Counter64
       MAX-ACCESS read-only
       STATUS current
       DESCRIPTION
           "Number of failed outbound REGISTER dialogs.
AC INI-Param: N/A"
       ::= {acKpiOtherStatsIntervalGlobalEntry 38}



     acKpiOtherStatsIntervalGlobalFailedRegisterIn OBJECT-TYPE
       SYNTAX Counter64
       MAX-ACCESS read-only
       STATUS current
       DESCRIPTION
           "Number of failed inbound REGISTER dialogs.
AC INI-Param: N/A"
       ::= {acKpiOtherStatsIntervalGlobalEntry 39}



     acKpiOtherStatsIntervalGlobalOtherDialogsOut OBJECT-TYPE
       SYNTAX Counter64
       MAX-ACCESS read-only
       STATUS current
       DESCRIPTION
           "Number of outbound other requests (not INVITE,SUBSCRIBE,REGISTER).
AC INI-Param: N/A"
       ::= {acKpiOtherStatsIntervalGlobalEntry 40}



     acKpiOtherStatsIntervalGlobalOtherDialogsIn OBJECT-TYPE
       SYNTAX Counter64
       MAX-ACCESS read-only
       STATUS current
       DESCRIPTION
           "Number of inbound other requests (not INVITE,SUBSCRIBE,REGISTER).
AC INI-Param: N/A"
       ::= {acKpiOtherStatsIntervalGlobalEntry 41}



     acKpiOtherStatsIntervalGlobalSubscribeOut OBJECT-TYPE
       SYNTAX Counter64
       MAX-ACCESS read-only
       STATUS current
       DESCRIPTION
           "Number of outbound SUBSCRIBE requests.
AC INI-Param: N/A"
       ::= {acKpiOtherStatsIntervalGlobalEntry 42}



     acKpiOtherStatsIntervalGlobalSubscribeIn OBJECT-TYPE
       SYNTAX Counter64
       MAX-ACCESS read-only
       STATUS current
       DESCRIPTION
           "Number of inbound SUBSCRIBE requests.
AC INI-Param: N/A"
       ::= {acKpiOtherStatsIntervalGlobalEntry 43}



     acKpiOtherStatsIntervalTables OBJECT IDENTIFIER ::= {acKpiOtherStatsInterval 2}


     -- ****************************************
     -- acKpiOtherStatsIntervalIpGroup table declaration
     -- ****************************************
     acKpiOtherStatsIntervalIpGroupTable OBJECT-TYPE
       SYNTAX SEQUENCE OF AcKpiOtherStatsIntervalIpGroupEntry
       MAX-ACCESS not-accessible
       STATUS current
       DESCRIPTION
           ""
       ::= {acKpiOtherStatsIntervalTables 1}



     -- ****************************************
     -- acKpiOtherStatsIntervalIpGroup table entry
     -- ****************************************
     acKpiOtherStatsIntervalIpGroupEntry OBJECT-TYPE
       SYNTAX AcKpiOtherStatsIntervalIpGroupEntry
       MAX-ACCESS not-accessible
       STATUS current
       DESCRIPTION
           ""
       INDEX {acKpiOtherStatsIntervalIpGroupIndex,acKpiOtherStatsIntervalIpGroupInterval}
       ::= {acKpiOtherStatsIntervalIpGroupTable 1}



     -- ****************************************
     -- acKpiOtherStatsIntervalIpGroup TABLE
     -- ****************************************
     AcKpiOtherStatsIntervalIpGroupEntry ::= SEQUENCE {
       acKpiOtherStatsIntervalIpGroupIndex             Unsigned32,
       acKpiOtherStatsIntervalIpGroupInterval          Unsigned32,
       acKpiOtherStatsIntervalIpGroupRegisteredUsersAvg 
                                                       Gauge32,
       acKpiOtherStatsIntervalIpGroupRegisteredUsersMax 
                                                       Gauge32,
       acKpiOtherStatsIntervalIpGroupRegisterIn        Counter64,
       acKpiOtherStatsIntervalIpGroupRegisterRateInAvg Gauge32,
       acKpiOtherStatsIntervalIpGroupRegisterRateInMax Gauge32,
       acKpiOtherStatsIntervalIpGroupRegisterOut       Counter64,
       acKpiOtherStatsIntervalIpGroupRegisterRateOutAvg 
                                                       Gauge32,
       acKpiOtherStatsIntervalIpGroupRegisterRateOutMax 
                                                       Gauge32,
       acKpiOtherStatsIntervalIpGroupActiveSubscribesAvg 
                                                       Gauge32,
       acKpiOtherStatsIntervalIpGroupActiveSubscribesMax 
                                                       Gauge32,
       acKpiOtherStatsIntervalIpGroupSubscribeRateInAvg 
                                                       Gauge32,
       acKpiOtherStatsIntervalIpGroupSubscribeRateInMax 
                                                       Gauge32,
       acKpiOtherStatsIntervalIpGroupSubscribeRateOutAvg 
                                                       Gauge32,
       acKpiOtherStatsIntervalIpGroupSubscribeRateOutMax 
                                                       Gauge32,
       acKpiOtherStatsIntervalIpGroupOtherDialogsAvg   Gauge32,
       acKpiOtherStatsIntervalIpGroupOtherDialogsRateInAvg 
                                                       Gauge32,
       acKpiOtherStatsIntervalIpGroupOtherDialogsRateInMax 
                                                       Gauge32,
       acKpiOtherStatsIntervalIpGroupOtherDialogsRateOutAvg 
                                                       Gauge32,
       acKpiOtherStatsIntervalIpGroupOtherDialogsRateOutMax 
                                                       Gauge32,
       acKpiOtherStatsIntervalIpGroupTransactionRateAvg 
                                                       Gauge32,
       acKpiOtherStatsIntervalIpGroupTransactionRateMax 
                                                       Gauge32,
       acKpiOtherStatsIntervalIpGroupSbcSuccessfulRegistrations 
                                                       Counter64,
       acKpiOtherStatsIntervalIpGroupSbcRegistrationSuccessRatioAvg 
                                                       Gauge32,
       acKpiOtherStatsIntervalIpGroupSbcAttemptedRegistrations 
                                                       Counter64,
       acKpiOtherStatsIntervalIpGroupUserRegistrationSuccessRatioAvg 
                                                       Gauge32,
       acKpiOtherStatsIntervalIpGroupUserSuccessfulRegistrations 
                                                       Counter64,
       acKpiOtherStatsIntervalIpGroupSubscribeIn       Counter64,
       acKpiOtherStatsIntervalIpGroupSubscribeOut      Counter64,
       acKpiOtherStatsIntervalIpGroupOtherDialogsIn    Counter64,
       acKpiOtherStatsIntervalIpGroupOtherDialogsOut   Counter64,
       acKpiOtherStatsIntervalIpGroupFailedRegisterIn  Counter64,
       acKpiOtherStatsIntervalIpGroupFailedRegisterOut Counter64,
       acKpiOtherStatsIntervalIpGroupFailedRegisterAdmissionIn 
                                                       Counter64,
       acKpiOtherStatsIntervalIpGroupFailedRegisterAdmissionOut 
                                                       Counter64,
       acKpiOtherStatsIntervalIpGroupFailedRegisterNoRouteIn 
                                                       Counter64,
       acKpiOtherStatsIntervalIpGroupFailedRegisterOtherIn 
                                                       Counter64,
       acKpiOtherStatsIntervalIpGroupFailedRegisterOtherOut 
                                                       Counter64,
       acKpiOtherStatsIntervalIpGroupFailedSubscribeIn Counter64,
       acKpiOtherStatsIntervalIpGroupFailedSubscribeOut 
                                                       Counter64,
       acKpiOtherStatsIntervalIpGroupFailedOtherDialogsIn 
                                                       Counter64,
       acKpiOtherStatsIntervalIpGroupFailedOtherDialogsOut 
                                                       Counter64
     }



     acKpiOtherStatsIntervalIpGroupIndex OBJECT-TYPE
       SYNTAX Unsigned32 (0..32767)
       MAX-ACCESS not-accessible
       STATUS current
       DESCRIPTION
           "
AC INI-Param: N/A"
       ::= {acKpiOtherStatsIntervalIpGroupEntry 1}



     acKpiOtherStatsIntervalIpGroupInterval OBJECT-TYPE
       SYNTAX Unsigned32 (1..200)
       MAX-ACCESS not-accessible
       STATUS current
       DESCRIPTION
           "
AC INI-Param: N/A"
       ::= {acKpiOtherStatsIntervalIpGroupEntry 2}



     acKpiOtherStatsIntervalIpGroupRegisteredUsersAvg OBJECT-TYPE
       SYNTAX Gauge32
       MAX-ACCESS read-only
       STATUS current
       DESCRIPTION
           "Average number of registered users.
AC INI-Param: N/A"
       ::= {acKpiOtherStatsIntervalIpGroupEntry 3}



     acKpiOtherStatsIntervalIpGroupRegisteredUsersMax OBJECT-TYPE
       SYNTAX Gauge32
       MAX-ACCESS read-only
       STATUS current
       DESCRIPTION
           "Maximum number of registered users.
AC INI-Param: N/A"
       ::= {acKpiOtherStatsIntervalIpGroupEntry 4}



     acKpiOtherStatsIntervalIpGroupRegisterIn OBJECT-TYPE
       SYNTAX Counter64
       MAX-ACCESS read-only
       STATUS current
       DESCRIPTION
           "Number of inbound registrations.
AC INI-Param: N/A"
       ::= {acKpiOtherStatsIntervalIpGroupEntry 5}



     acKpiOtherStatsIntervalIpGroupRegisterRateInAvg OBJECT-TYPE
       SYNTAX Gauge32
       MAX-ACCESS read-only
       STATUS current
       DESCRIPTION
           "Average rate of inbound registrations (registrations per second).
AC INI-Param: N/A"
       ::= {acKpiOtherStatsIntervalIpGroupEntry 6}



     acKpiOtherStatsIntervalIpGroupRegisterRateInMax OBJECT-TYPE
       SYNTAX Gauge32
       MAX-ACCESS read-only
       STATUS current
       DESCRIPTION
           "Maximum rate of inbound registrations (registrations per second).
AC INI-Param: N/A"
       ::= {acKpiOtherStatsIntervalIpGroupEntry 7}



     acKpiOtherStatsIntervalIpGroupRegisterOut OBJECT-TYPE
       SYNTAX Counter64
       MAX-ACCESS read-only
       STATUS current
       DESCRIPTION
           "Number of outbound registrations.
AC INI-Param: N/A"
       ::= {acKpiOtherStatsIntervalIpGroupEntry 8}



     acKpiOtherStatsIntervalIpGroupRegisterRateOutAvg OBJECT-TYPE
       SYNTAX Gauge32
       MAX-ACCESS read-only
       STATUS current
       DESCRIPTION
           "Average rate of outbound registrations (registrations per second).
AC INI-Param: N/A"
       ::= {acKpiOtherStatsIntervalIpGroupEntry 9}



     acKpiOtherStatsIntervalIpGroupRegisterRateOutMax OBJECT-TYPE
       SYNTAX Gauge32
       MAX-ACCESS read-only
       STATUS current
       DESCRIPTION
           "Maximum rate of outbound registrations (registrations per second).
AC INI-Param: N/A"
       ::= {acKpiOtherStatsIntervalIpGroupEntry 10}



     acKpiOtherStatsIntervalIpGroupActiveSubscribesAvg OBJECT-TYPE
       SYNTAX Gauge32
       MAX-ACCESS read-only
       STATUS current
       DESCRIPTION
           "Average number of active SUBSCRIBE dialogs.
AC INI-Param: N/A"
       ::= {acKpiOtherStatsIntervalIpGroupEntry 11}



     acKpiOtherStatsIntervalIpGroupActiveSubscribesMax OBJECT-TYPE
       SYNTAX Gauge32
       MAX-ACCESS read-only
       STATUS current
       DESCRIPTION
           "Maximum number of active SUBSCRIBE dialogs.
AC INI-Param: N/A"
       ::= {acKpiOtherStatsIntervalIpGroupEntry 12}



     acKpiOtherStatsIntervalIpGroupSubscribeRateInAvg OBJECT-TYPE
       SYNTAX Gauge32
       MAX-ACCESS read-only
       STATUS current
       DESCRIPTION
           "Average inbound SUBSCRIBE Rate (dialogs per second).
AC INI-Param: N/A"
       ::= {acKpiOtherStatsIntervalIpGroupEntry 13}



     acKpiOtherStatsIntervalIpGroupSubscribeRateInMax OBJECT-TYPE
       SYNTAX Gauge32
       MAX-ACCESS read-only
       STATUS current
       DESCRIPTION
           "Maximum inbound SUBSCRIBE Rate (dialogs per second).
AC INI-Param: N/A"
       ::= {acKpiOtherStatsIntervalIpGroupEntry 14}



     acKpiOtherStatsIntervalIpGroupSubscribeRateOutAvg OBJECT-TYPE
       SYNTAX Gauge32
       MAX-ACCESS read-only
       STATUS current
       DESCRIPTION
           "Average outbound SUBSCRIBE Rate (dialogs per second).
AC INI-Param: N/A"
       ::= {acKpiOtherStatsIntervalIpGroupEntry 15}



     acKpiOtherStatsIntervalIpGroupSubscribeRateOutMax OBJECT-TYPE
       SYNTAX Gauge32
       MAX-ACCESS read-only
       STATUS current
       DESCRIPTION
           "Maximum outbound SUBSCRIBE Rate (dialogs per second).
AC INI-Param: N/A"
       ::= {acKpiOtherStatsIntervalIpGroupEntry 16}



     acKpiOtherStatsIntervalIpGroupOtherDialogsAvg OBJECT-TYPE
       SYNTAX Gauge32
       MAX-ACCESS read-only
       STATUS current
       DESCRIPTION
           "Average number of active other dialogs (not INVITE,SUBSCRIBE,REGISTER).
AC INI-Param: N/A"
       ::= {acKpiOtherStatsIntervalIpGroupEntry 17}



     acKpiOtherStatsIntervalIpGroupOtherDialogsRateInAvg OBJECT-TYPE
       SYNTAX Gauge32
       MAX-ACCESS read-only
       STATUS current
       DESCRIPTION
           "Average inbound other dialogs rate (dialogs per second).
AC INI-Param: N/A"
       ::= {acKpiOtherStatsIntervalIpGroupEntry 18}



     acKpiOtherStatsIntervalIpGroupOtherDialogsRateInMax OBJECT-TYPE
       SYNTAX Gauge32
       MAX-ACCESS read-only
       STATUS current
       DESCRIPTION
           "Maximum inbound other dialogs rate (dialogs per second).
AC INI-Param: N/A"
       ::= {acKpiOtherStatsIntervalIpGroupEntry 19}



     acKpiOtherStatsIntervalIpGroupOtherDialogsRateOutAvg OBJECT-TYPE
       SYNTAX Gauge32
       MAX-ACCESS read-only
       STATUS current
       DESCRIPTION
           "Average outbound other dialogs rate (dialogs per second).
AC INI-Param: N/A"
       ::= {acKpiOtherStatsIntervalIpGroupEntry 20}



     acKpiOtherStatsIntervalIpGroupOtherDialogsRateOutMax OBJECT-TYPE
       SYNTAX Gauge32
       MAX-ACCESS read-only
       STATUS current
       DESCRIPTION
           "Maximum outbound other dialogs rate (dialogs per second).
AC INI-Param: N/A"
       ::= {acKpiOtherStatsIntervalIpGroupEntry 21}



     acKpiOtherStatsIntervalIpGroupTransactionRateAvg OBJECT-TYPE
       SYNTAX Gauge32
       MAX-ACCESS read-only
       STATUS current
       DESCRIPTION
           "Average SIP rransactions rate (transactions per second).
AC INI-Param: N/A"
       ::= {acKpiOtherStatsIntervalIpGroupEntry 22}



     acKpiOtherStatsIntervalIpGroupTransactionRateMax OBJECT-TYPE
       SYNTAX Gauge32
       MAX-ACCESS read-only
       STATUS current
       DESCRIPTION
           "Maximum SIP transactions rate (transactions per second).
AC INI-Param: N/A"
       ::= {acKpiOtherStatsIntervalIpGroupEntry 23}



     acKpiOtherStatsIntervalIpGroupSbcSuccessfulRegistrations OBJECT-TYPE
       SYNTAX Counter64
       MAX-ACCESS read-only
       STATUS current
       DESCRIPTION
           "Number of successful SBC-initiated outbound REGISTER dialogs.
AC INI-Param: N/A"
       ::= {acKpiOtherStatsIntervalIpGroupEntry 24}



     acKpiOtherStatsIntervalIpGroupSbcRegistrationSuccessRatioAvg OBJECT-TYPE
       SYNTAX Gauge32
       MAX-ACCESS read-only
       STATUS current
       DESCRIPTION
           "Average success ratio for SBC-initiated REGISTER dialogs (%).
AC INI-Param: N/A"
       ::= {acKpiOtherStatsIntervalIpGroupEntry 25}



     acKpiOtherStatsIntervalIpGroupSbcAttemptedRegistrations OBJECT-TYPE
       SYNTAX Counter64
       MAX-ACCESS read-only
       STATUS current
       DESCRIPTION
           "Number of SBC-initiated outbound REGISTER dialogs.
AC INI-Param: N/A"
       ::= {acKpiOtherStatsIntervalIpGroupEntry 26}



     acKpiOtherStatsIntervalIpGroupUserRegistrationSuccessRatioAvg OBJECT-TYPE
       SYNTAX Gauge32
       MAX-ACCESS read-only
       STATUS current
       DESCRIPTION
           "Average success ratio for user-initiated REGISTER dialogs (%).
AC INI-Param: N/A"
       ::= {acKpiOtherStatsIntervalIpGroupEntry 27}



     acKpiOtherStatsIntervalIpGroupUserSuccessfulRegistrations OBJECT-TYPE
       SYNTAX Counter64
       MAX-ACCESS read-only
       STATUS current
       DESCRIPTION
           "Number of successful user-initiated inbound REGISTER dialogs.
AC INI-Param: N/A"
       ::= {acKpiOtherStatsIntervalIpGroupEntry 28}



     acKpiOtherStatsIntervalIpGroupSubscribeIn OBJECT-TYPE
       SYNTAX Counter64
       MAX-ACCESS read-only
       STATUS current
       DESCRIPTION
           "Number of inbound SUBSCRIBE requests.
AC INI-Param: N/A"
       ::= {acKpiOtherStatsIntervalIpGroupEntry 29}



     acKpiOtherStatsIntervalIpGroupSubscribeOut OBJECT-TYPE
       SYNTAX Counter64
       MAX-ACCESS read-only
       STATUS current
       DESCRIPTION
           "Number of outbound SUBSCRIBE requests.
AC INI-Param: N/A"
       ::= {acKpiOtherStatsIntervalIpGroupEntry 30}



     acKpiOtherStatsIntervalIpGroupOtherDialogsIn OBJECT-TYPE
       SYNTAX Counter64
       MAX-ACCESS read-only
       STATUS current
       DESCRIPTION
           "Number of inbound other requests (not INVITE,SUBSCRIBE,REGISTER).
AC INI-Param: N/A"
       ::= {acKpiOtherStatsIntervalIpGroupEntry 31}



     acKpiOtherStatsIntervalIpGroupOtherDialogsOut OBJECT-TYPE
       SYNTAX Counter64
       MAX-ACCESS read-only
       STATUS current
       DESCRIPTION
           "Number of outbound other requests (not INVITE,SUBSCRIBE,REGISTER).
AC INI-Param: N/A"
       ::= {acKpiOtherStatsIntervalIpGroupEntry 32}



     acKpiOtherStatsIntervalIpGroupFailedRegisterIn OBJECT-TYPE
       SYNTAX Counter64
       MAX-ACCESS read-only
       STATUS current
       DESCRIPTION
           "Number of failed inbound REGISTER dialogs.
AC INI-Param: N/A"
       ::= {acKpiOtherStatsIntervalIpGroupEntry 33}



     acKpiOtherStatsIntervalIpGroupFailedRegisterOut OBJECT-TYPE
       SYNTAX Counter64
       MAX-ACCESS read-only
       STATUS current
       DESCRIPTION
           "Number of failed outbound REGISTER dialogs.
AC INI-Param: N/A"
       ::= {acKpiOtherStatsIntervalIpGroupEntry 34}



     acKpiOtherStatsIntervalIpGroupFailedRegisterAdmissionIn OBJECT-TYPE
       SYNTAX Counter64
       MAX-ACCESS read-only
       STATUS current
       DESCRIPTION
           "Number of inbound REGISTER dialogs failed due to admission control
(CAC).
AC INI-Param: N/A"
       ::= {acKpiOtherStatsIntervalIpGroupEntry 35}



     acKpiOtherStatsIntervalIpGroupFailedRegisterAdmissionOut OBJECT-TYPE
       SYNTAX Counter64
       MAX-ACCESS read-only
       STATUS current
       DESCRIPTION
           "Number of outbound REGISTER dialogs failed due to admission
control (CAC).
AC INI-Param: N/A"
       ::= {acKpiOtherStatsIntervalIpGroupEntry 36}



     acKpiOtherStatsIntervalIpGroupFailedRegisterNoRouteIn OBJECT-TYPE
       SYNTAX Counter64
       MAX-ACCESS read-only
       STATUS current
       DESCRIPTION
           "Number of inbound REGISTER dialogs failed due to routing failure.
AC INI-Param: N/A"
       ::= {acKpiOtherStatsIntervalIpGroupEntry 37}



     acKpiOtherStatsIntervalIpGroupFailedRegisterOtherIn OBJECT-TYPE
       SYNTAX Counter64
       MAX-ACCESS read-only
       STATUS current
       DESCRIPTION
           "Number of inbound REGISTER dialogs failed due to other reasons.
AC INI-Param: N/A"
       ::= {acKpiOtherStatsIntervalIpGroupEntry 38}



     acKpiOtherStatsIntervalIpGroupFailedRegisterOtherOut OBJECT-TYPE
       SYNTAX Counter64
       MAX-ACCESS read-only
       STATUS current
       DESCRIPTION
           "Number of outbound REGISTER dialogs failed due to other reasons.
AC INI-Param: N/A"
       ::= {acKpiOtherStatsIntervalIpGroupEntry 39}



     acKpiOtherStatsIntervalIpGroupFailedSubscribeIn OBJECT-TYPE
       SYNTAX Counter64
       MAX-ACCESS read-only
       STATUS current
       DESCRIPTION
           "Number of Failed Inbound SUBSCRIBE dialogs.
AC INI-Param: N/A"
       ::= {acKpiOtherStatsIntervalIpGroupEntry 40}



     acKpiOtherStatsIntervalIpGroupFailedSubscribeOut OBJECT-TYPE
       SYNTAX Counter64
       MAX-ACCESS read-only
       STATUS current
       DESCRIPTION
           "Number of Failed Outbound SUBSCRIBE dialogs.
AC INI-Param: N/A"
       ::= {acKpiOtherStatsIntervalIpGroupEntry 41}



     acKpiOtherStatsIntervalIpGroupFailedOtherDialogsIn OBJECT-TYPE
       SYNTAX Counter64
       MAX-ACCESS read-only
       STATUS current
       DESCRIPTION
           "Number of Failed Inbound other dialogs.
AC INI-Param: N/A"
       ::= {acKpiOtherStatsIntervalIpGroupEntry 42}



     acKpiOtherStatsIntervalIpGroupFailedOtherDialogsOut OBJECT-TYPE
       SYNTAX Counter64
       MAX-ACCESS read-only
       STATUS current
       DESCRIPTION
           "Number of Failed Outbound other dialogs.
AC INI-Param: N/A"
       ::= {acKpiOtherStatsIntervalIpGroupEntry 43}



     -- ****************************************
     -- acKpiOtherStatsIntervalSrd table declaration
     -- ****************************************
     acKpiOtherStatsIntervalSrdTable OBJECT-TYPE
       SYNTAX SEQUENCE OF AcKpiOtherStatsIntervalSrdEntry
       MAX-ACCESS not-accessible
       STATUS current
       DESCRIPTION
           ""
       ::= {acKpiOtherStatsIntervalTables 2}



     -- ****************************************
     -- acKpiOtherStatsIntervalSrd table entry
     -- ****************************************
     acKpiOtherStatsIntervalSrdEntry OBJECT-TYPE
       SYNTAX AcKpiOtherStatsIntervalSrdEntry
       MAX-ACCESS not-accessible
       STATUS current
       DESCRIPTION
           ""
       INDEX {acKpiOtherStatsIntervalSrdIndex,acKpiOtherStatsIntervalSrdInterval}
       ::= {acKpiOtherStatsIntervalSrdTable 1}



     -- ****************************************
     -- acKpiOtherStatsIntervalSrd TABLE
     -- ****************************************
     AcKpiOtherStatsIntervalSrdEntry ::= SEQUENCE {
       acKpiOtherStatsIntervalSrdIndex                 Unsigned32,
       acKpiOtherStatsIntervalSrdInterval              Unsigned32,
       acKpiOtherStatsIntervalSrdRegisteredUsersAvg    Gauge32,
       acKpiOtherStatsIntervalSrdRegisteredUsersMax    Gauge32,
       acKpiOtherStatsIntervalSrdRegisterIn            Counter64,
       acKpiOtherStatsIntervalSrdRegisterRateInAvg     Gauge32,
       acKpiOtherStatsIntervalSrdRegisterRateInMax     Gauge32,
       acKpiOtherStatsIntervalSrdRegisterOut           Counter64,
       acKpiOtherStatsIntervalSrdRegisterRateOutAvg    Gauge32,
       acKpiOtherStatsIntervalSrdRegisterRateOutMax    Gauge32,
       acKpiOtherStatsIntervalSrdActiveSubscribesAvg   Gauge32,
       acKpiOtherStatsIntervalSrdActiveSubscribesMax   Gauge32,
       acKpiOtherStatsIntervalSrdSubscribeRateInAvg    Gauge32,
       acKpiOtherStatsIntervalSrdSubscribeRateInMax    Gauge32,
       acKpiOtherStatsIntervalSrdSubscribeRateOutAvg   Gauge32,
       acKpiOtherStatsIntervalSrdSubscribeRateOutMax   Gauge32,
       acKpiOtherStatsIntervalSrdOtherDialogsAvg       Gauge32,
       acKpiOtherStatsIntervalSrdOtherDialogsRateInAvg Gauge32,
       acKpiOtherStatsIntervalSrdOtherDialogsRateInMax Gauge32,
       acKpiOtherStatsIntervalSrdOtherDialogsRateOutAvg 
                                                       Gauge32,
       acKpiOtherStatsIntervalSrdOtherDialogsRateOutMax 
                                                       Gauge32,
       acKpiOtherStatsIntervalSrdTransactionRateAvg    Gauge32,
       acKpiOtherStatsIntervalSrdTransactionRateMax    Gauge32,
       acKpiOtherStatsIntervalSrdSbcSuccessfulRegistrations 
                                                       Counter64,
       acKpiOtherStatsIntervalSrdSbcRegistrationSuccessRatioAvg 
                                                       Gauge32,
       acKpiOtherStatsIntervalSrdSbcAttemptedRegistrations 
                                                       Counter64,
       acKpiOtherStatsIntervalSrdUserRegistrationSuccessRatioAvg 
                                                       Gauge32,
       acKpiOtherStatsIntervalSrdUserSuccessfulRegistrations 
                                                       Counter64,
       acKpiOtherStatsIntervalSrdSubscribeIn           Counter64,
       acKpiOtherStatsIntervalSrdSubscribeOut          Counter64,
       acKpiOtherStatsIntervalSrdOtherDialogsIn        Counter64,
       acKpiOtherStatsIntervalSrdOtherDialogsOut       Counter64,
       acKpiOtherStatsIntervalSrdFailedRegisterIn      Counter64,
       acKpiOtherStatsIntervalSrdFailedRegisterOut     Counter64,
       acKpiOtherStatsIntervalSrdFailedRegisterAdmissionIn 
                                                       Counter64,
       acKpiOtherStatsIntervalSrdFailedRegisterAdmissionOut 
                                                       Counter64,
       acKpiOtherStatsIntervalSrdFailedRegisterNoRouteIn 
                                                       Counter64,
       acKpiOtherStatsIntervalSrdFailedRegisterClassificationIn 
                                                       Counter64,
       acKpiOtherStatsIntervalSrdFailedRegisterOtherIn Counter64,
       acKpiOtherStatsIntervalSrdFailedRegisterOtherOut 
                                                       Counter64,
       acKpiOtherStatsIntervalSrdFailedSubscribeIn     Counter64,
       acKpiOtherStatsIntervalSrdFailedSubscribeOut    Counter64,
       acKpiOtherStatsIntervalSrdFailedOtherDialogsIn  Counter64,
       acKpiOtherStatsIntervalSrdFailedOtherDialogsOut Counter64
     }



     acKpiOtherStatsIntervalSrdIndex OBJECT-TYPE
       SYNTAX Unsigned32 (0..32767)
       MAX-ACCESS not-accessible
       STATUS current
       DESCRIPTION
           "
AC INI-Param: N/A"
       ::= {acKpiOtherStatsIntervalSrdEntry 1}



     acKpiOtherStatsIntervalSrdInterval OBJECT-TYPE
       SYNTAX Unsigned32 (1..200)
       MAX-ACCESS not-accessible
       STATUS current
       DESCRIPTION
           "
AC INI-Param: N/A"
       ::= {acKpiOtherStatsIntervalSrdEntry 2}



     acKpiOtherStatsIntervalSrdRegisteredUsersAvg OBJECT-TYPE
       SYNTAX Gauge32
       MAX-ACCESS read-only
       STATUS current
       DESCRIPTION
           "Average number of registered users.
AC INI-Param: N/A"
       ::= {acKpiOtherStatsIntervalSrdEntry 3}



     acKpiOtherStatsIntervalSrdRegisteredUsersMax OBJECT-TYPE
       SYNTAX Gauge32
       MAX-ACCESS read-only
       STATUS current
       DESCRIPTION
           "Maximum number of registered users.
AC INI-Param: N/A"
       ::= {acKpiOtherStatsIntervalSrdEntry 4}



     acKpiOtherStatsIntervalSrdRegisterIn OBJECT-TYPE
       SYNTAX Counter64
       MAX-ACCESS read-only
       STATUS current
       DESCRIPTION
           "Number of inbound registrations.
AC INI-Param: N/A"
       ::= {acKpiOtherStatsIntervalSrdEntry 5}



     acKpiOtherStatsIntervalSrdRegisterRateInAvg OBJECT-TYPE
       SYNTAX Gauge32
       MAX-ACCESS read-only
       STATUS current
       DESCRIPTION
           "Average rate of inbound registrations (registrations per second).
AC INI-Param: N/A"
       ::= {acKpiOtherStatsIntervalSrdEntry 6}



     acKpiOtherStatsIntervalSrdRegisterRateInMax OBJECT-TYPE
       SYNTAX Gauge32
       MAX-ACCESS read-only
       STATUS current
       DESCRIPTION
           "Maximum rate of inbound registrations (registrations per second).
AC INI-Param: N/A"
       ::= {acKpiOtherStatsIntervalSrdEntry 7}



     acKpiOtherStatsIntervalSrdRegisterOut OBJECT-TYPE
       SYNTAX Counter64
       MAX-ACCESS read-only
       STATUS current
       DESCRIPTION
           "Number of outbound registrations.
AC INI-Param: N/A"
       ::= {acKpiOtherStatsIntervalSrdEntry 8}



     acKpiOtherStatsIntervalSrdRegisterRateOutAvg OBJECT-TYPE
       SYNTAX Gauge32
       MAX-ACCESS read-only
       STATUS current
       DESCRIPTION
           "Average rate of outbound registrations (registrations per second).
AC INI-Param: N/A"
       ::= {acKpiOtherStatsIntervalSrdEntry 9}



     acKpiOtherStatsIntervalSrdRegisterRateOutMax OBJECT-TYPE
       SYNTAX Gauge32
       MAX-ACCESS read-only
       STATUS current
       DESCRIPTION
           "Maximum rate of outbound registrations (registrations per second).
AC INI-Param: N/A"
       ::= {acKpiOtherStatsIntervalSrdEntry 10}



     acKpiOtherStatsIntervalSrdActiveSubscribesAvg OBJECT-TYPE
       SYNTAX Gauge32
       MAX-ACCESS read-only
       STATUS current
       DESCRIPTION
           "Average number of active SUBSCRIBE dialogs.
AC INI-Param: N/A"
       ::= {acKpiOtherStatsIntervalSrdEntry 11}



     acKpiOtherStatsIntervalSrdActiveSubscribesMax OBJECT-TYPE
       SYNTAX Gauge32
       MAX-ACCESS read-only
       STATUS current
       DESCRIPTION
           "Maximum number of active SUBSCRIBE dialogs.
AC INI-Param: N/A"
       ::= {acKpiOtherStatsIntervalSrdEntry 12}



     acKpiOtherStatsIntervalSrdSubscribeRateInAvg OBJECT-TYPE
       SYNTAX Gauge32
       MAX-ACCESS read-only
       STATUS current
       DESCRIPTION
           "Average inbound SUBSCRIBE Rate (dialogs per second).
AC INI-Param: N/A"
       ::= {acKpiOtherStatsIntervalSrdEntry 13}



     acKpiOtherStatsIntervalSrdSubscribeRateInMax OBJECT-TYPE
       SYNTAX Gauge32
       MAX-ACCESS read-only
       STATUS current
       DESCRIPTION
           "Maximum inbound SUBSCRIBE Rate (dialogs per second).
AC INI-Param: N/A"
       ::= {acKpiOtherStatsIntervalSrdEntry 14}



     acKpiOtherStatsIntervalSrdSubscribeRateOutAvg OBJECT-TYPE
       SYNTAX Gauge32
       MAX-ACCESS read-only
       STATUS current
       DESCRIPTION
           "Average outbound SUBSCRIBE Rate (dialogs per second).
AC INI-Param: N/A"
       ::= {acKpiOtherStatsIntervalSrdEntry 15}



     acKpiOtherStatsIntervalSrdSubscribeRateOutMax OBJECT-TYPE
       SYNTAX Gauge32
       MAX-ACCESS read-only
       STATUS current
       DESCRIPTION
           "Maximum outbound SUBSCRIBE Rate (dialogs per second).
AC INI-Param: N/A"
       ::= {acKpiOtherStatsIntervalSrdEntry 16}



     acKpiOtherStatsIntervalSrdOtherDialogsAvg OBJECT-TYPE
       SYNTAX Gauge32
       MAX-ACCESS read-only
       STATUS current
       DESCRIPTION
           "Average number of active other dialogs (not INVITE,SUBSCRIBE,REGISTER).
AC INI-Param: N/A"
       ::= {acKpiOtherStatsIntervalSrdEntry 17}



     acKpiOtherStatsIntervalSrdOtherDialogsRateInAvg OBJECT-TYPE
       SYNTAX Gauge32
       MAX-ACCESS read-only
       STATUS current
       DESCRIPTION
           "Average inbound other dialogs rate (dialogs per second).
AC INI-Param: N/A"
       ::= {acKpiOtherStatsIntervalSrdEntry 18}



     acKpiOtherStatsIntervalSrdOtherDialogsRateInMax OBJECT-TYPE
       SYNTAX Gauge32
       MAX-ACCESS read-only
       STATUS current
       DESCRIPTION
           "Maximum inbound other dialogs rate (dialogs per second).
AC INI-Param: N/A"
       ::= {acKpiOtherStatsIntervalSrdEntry 19}



     acKpiOtherStatsIntervalSrdOtherDialogsRateOutAvg OBJECT-TYPE
       SYNTAX Gauge32
       MAX-ACCESS read-only
       STATUS current
       DESCRIPTION
           "Average outbound other dialogs rate (dialogs per second).
AC INI-Param: N/A"
       ::= {acKpiOtherStatsIntervalSrdEntry 20}



     acKpiOtherStatsIntervalSrdOtherDialogsRateOutMax OBJECT-TYPE
       SYNTAX Gauge32
       MAX-ACCESS read-only
       STATUS current
       DESCRIPTION
           "Maximum outbound other dialogs rate (dialogs per second).
AC INI-Param: N/A"
       ::= {acKpiOtherStatsIntervalSrdEntry 21}



     acKpiOtherStatsIntervalSrdTransactionRateAvg OBJECT-TYPE
       SYNTAX Gauge32
       MAX-ACCESS read-only
       STATUS current
       DESCRIPTION
           "Average SIP rransactions rate (transactions per second).
AC INI-Param: N/A"
       ::= {acKpiOtherStatsIntervalSrdEntry 22}



     acKpiOtherStatsIntervalSrdTransactionRateMax OBJECT-TYPE
       SYNTAX Gauge32
       MAX-ACCESS read-only
       STATUS current
       DESCRIPTION
           "Maximum SIP transactions rate (transactions per second).
AC INI-Param: N/A"
       ::= {acKpiOtherStatsIntervalSrdEntry 23}



     acKpiOtherStatsIntervalSrdSbcSuccessfulRegistrations OBJECT-TYPE
       SYNTAX Counter64
       MAX-ACCESS read-only
       STATUS current
       DESCRIPTION
           "Number of successful SBC-initiated outbound REGISTER dialogs.
AC INI-Param: N/A"
       ::= {acKpiOtherStatsIntervalSrdEntry 24}



     acKpiOtherStatsIntervalSrdSbcRegistrationSuccessRatioAvg OBJECT-TYPE
       SYNTAX Gauge32
       MAX-ACCESS read-only
       STATUS current
       DESCRIPTION
           "Average success ratio for SBC-initiated REGISTER dialogs (%).
AC INI-Param: N/A"
       ::= {acKpiOtherStatsIntervalSrdEntry 25}



     acKpiOtherStatsIntervalSrdSbcAttemptedRegistrations OBJECT-TYPE
       SYNTAX Counter64
       MAX-ACCESS read-only
       STATUS current
       DESCRIPTION
           "Number of SBC-initiated outbound REGISTER dialogs.
AC INI-Param: N/A"
       ::= {acKpiOtherStatsIntervalSrdEntry 26}



     acKpiOtherStatsIntervalSrdUserRegistrationSuccessRatioAvg OBJECT-TYPE
       SYNTAX Gauge32
       MAX-ACCESS read-only
       STATUS current
       DESCRIPTION
           "Average success ratio for user-initiated REGISTER dialogs (%).
AC INI-Param: N/A"
       ::= {acKpiOtherStatsIntervalSrdEntry 27}



     acKpiOtherStatsIntervalSrdUserSuccessfulRegistrations OBJECT-TYPE
       SYNTAX Counter64
       MAX-ACCESS read-only
       STATUS current
       DESCRIPTION
           "Number of successful user-initiated inbound REGISTER dialogs.
AC INI-Param: N/A"
       ::= {acKpiOtherStatsIntervalSrdEntry 28}



     acKpiOtherStatsIntervalSrdSubscribeIn OBJECT-TYPE
       SYNTAX Counter64
       MAX-ACCESS read-only
       STATUS current
       DESCRIPTION
           "Number of inbound SUBSCRIBE requests.
AC INI-Param: N/A"
       ::= {acKpiOtherStatsIntervalSrdEntry 29}



     acKpiOtherStatsIntervalSrdSubscribeOut OBJECT-TYPE
       SYNTAX Counter64
       MAX-ACCESS read-only
       STATUS current
       DESCRIPTION
           "Number of outbound SUBSCRIBE requests.
AC INI-Param: N/A"
       ::= {acKpiOtherStatsIntervalSrdEntry 30}



     acKpiOtherStatsIntervalSrdOtherDialogsIn OBJECT-TYPE
       SYNTAX Counter64
       MAX-ACCESS read-only
       STATUS current
       DESCRIPTION
           "Number of inbound other requests (not INVITE,SUBSCRIBE,REGISTER).
AC INI-Param: N/A"
       ::= {acKpiOtherStatsIntervalSrdEntry 31}



     acKpiOtherStatsIntervalSrdOtherDialogsOut OBJECT-TYPE
       SYNTAX Counter64
       MAX-ACCESS read-only
       STATUS current
       DESCRIPTION
           "Number of outbound other requests (not INVITE,SUBSCRIBE,REGISTER).
AC INI-Param: N/A"
       ::= {acKpiOtherStatsIntervalSrdEntry 32}



     acKpiOtherStatsIntervalSrdFailedRegisterIn OBJECT-TYPE
       SYNTAX Counter64
       MAX-ACCESS read-only
       STATUS current
       DESCRIPTION
           "Number of failed inbound REGISTER dialogs.
AC INI-Param: N/A"
       ::= {acKpiOtherStatsIntervalSrdEntry 33}



     acKpiOtherStatsIntervalSrdFailedRegisterOut OBJECT-TYPE
       SYNTAX Counter64
       MAX-ACCESS read-only
       STATUS current
       DESCRIPTION
           "Number of failed outbound REGISTER dialogs.
AC INI-Param: N/A"
       ::= {acKpiOtherStatsIntervalSrdEntry 34}



     acKpiOtherStatsIntervalSrdFailedRegisterAdmissionIn OBJECT-TYPE
       SYNTAX Counter64
       MAX-ACCESS read-only
       STATUS current
       DESCRIPTION
           "Number of inbound REGISTER dialogs failed due to admission control
(CAC).
AC INI-Param: N/A"
       ::= {acKpiOtherStatsIntervalSrdEntry 35}



     acKpiOtherStatsIntervalSrdFailedRegisterAdmissionOut OBJECT-TYPE
       SYNTAX Counter64
       MAX-ACCESS read-only
       STATUS current
       DESCRIPTION
           "Number of outbound REGISTER dialogs failed due to admission
control (CAC).
AC INI-Param: N/A"
       ::= {acKpiOtherStatsIntervalSrdEntry 36}



     acKpiOtherStatsIntervalSrdFailedRegisterNoRouteIn OBJECT-TYPE
       SYNTAX Counter64
       MAX-ACCESS read-only
       STATUS current
       DESCRIPTION
           "Number of inbound REGISTER dialogs failed due to routing failure.
AC INI-Param: N/A"
       ::= {acKpiOtherStatsIntervalSrdEntry 37}



     acKpiOtherStatsIntervalSrdFailedRegisterClassificationIn OBJECT-TYPE
       SYNTAX Counter64
       MAX-ACCESS read-only
       STATUS current
       DESCRIPTION
           "Number of inbound REGISTER dialogs failed due to classification
failure.
AC INI-Param: N/A"
       ::= {acKpiOtherStatsIntervalSrdEntry 38}



     acKpiOtherStatsIntervalSrdFailedRegisterOtherIn OBJECT-TYPE
       SYNTAX Counter64
       MAX-ACCESS read-only
       STATUS current
       DESCRIPTION
           "Number of inbound REGISTER dialogs failed due to other reasons.
AC INI-Param: N/A"
       ::= {acKpiOtherStatsIntervalSrdEntry 39}



     acKpiOtherStatsIntervalSrdFailedRegisterOtherOut OBJECT-TYPE
       SYNTAX Counter64
       MAX-ACCESS read-only
       STATUS current
       DESCRIPTION
           "Number of outbound REGISTER dialogs failed due to other reasons.
AC INI-Param: N/A"
       ::= {acKpiOtherStatsIntervalSrdEntry 40}



     acKpiOtherStatsIntervalSrdFailedSubscribeIn OBJECT-TYPE
       SYNTAX Counter64
       MAX-ACCESS read-only
       STATUS current
       DESCRIPTION
           "Number of Failed Inbound SUBSCRIBE dialogs.
AC INI-Param: N/A"
       ::= {acKpiOtherStatsIntervalSrdEntry 41}



     acKpiOtherStatsIntervalSrdFailedSubscribeOut OBJECT-TYPE
       SYNTAX Counter64
       MAX-ACCESS read-only
       STATUS current
       DESCRIPTION
           "Number of Failed Outbound SUBSCRIBE dialogs.
AC INI-Param: N/A"
       ::= {acKpiOtherStatsIntervalSrdEntry 42}



     acKpiOtherStatsIntervalSrdFailedOtherDialogsIn OBJECT-TYPE
       SYNTAX Counter64
       MAX-ACCESS read-only
       STATUS current
       DESCRIPTION
           "Number of Failed Inbound other dialogs.
AC INI-Param: N/A"
       ::= {acKpiOtherStatsIntervalSrdEntry 43}



     acKpiOtherStatsIntervalSrdFailedOtherDialogsOut OBJECT-TYPE
       SYNTAX Counter64
       MAX-ACCESS read-only
       STATUS current
       DESCRIPTION
           "Number of Failed Outbound other dialogs.
AC INI-Param: N/A"
       ::= {acKpiOtherStatsIntervalSrdEntry 44}



     acKpiSipRecStats OBJECT IDENTIFIER ::= {acKpiSbc 4}


     acKpiSipRecStatsCurrent OBJECT IDENTIFIER ::= {acKpiSipRecStats 1}


     acKpiSipRecStatsCurrentGlobal OBJECT IDENTIFIER ::= {acKpiSipRecStatsCurrent 1}


     acKpiSipRecStatsCurrentGlobalSipRecSessions OBJECT-TYPE
       SYNTAX Gauge32
       MAX-ACCESS read-only
       STATUS current
       DESCRIPTION
           "Number of active SIP-REC sessions.
AC INI-Param: N/A"
       ::= {acKpiSipRecStatsCurrentGlobal 1}



     acKpiSipRecStatsCurrentGlobalSipRecRate OBJECT-TYPE
       SYNTAX Gauge32
       MAX-ACCESS read-only
       STATUS current
       DESCRIPTION
           "Establishment rate for SIP-REC sessions (sessions per second).
AC INI-Param: N/A"
       ::= {acKpiSipRecStatsCurrentGlobal 2}



     acKpiSipRecStatsCurrentTables OBJECT IDENTIFIER ::= {acKpiSipRecStatsCurrent 2}


     -- ****************************************
     -- acKpiSipRecStatsCurrentIpGroup table declaration
     -- ****************************************
     acKpiSipRecStatsCurrentIpGroupTable OBJECT-TYPE
       SYNTAX SEQUENCE OF AcKpiSipRecStatsCurrentIpGroupEntry
       MAX-ACCESS not-accessible
       STATUS current
       DESCRIPTION
           ""
       ::= {acKpiSipRecStatsCurrentTables 1}



     -- ****************************************
     -- acKpiSipRecStatsCurrentIpGroup table entry
     -- ****************************************
     acKpiSipRecStatsCurrentIpGroupEntry OBJECT-TYPE
       SYNTAX AcKpiSipRecStatsCurrentIpGroupEntry
       MAX-ACCESS not-accessible
       STATUS current
       DESCRIPTION
           ""
       INDEX {acKpiSipRecStatsCurrentIpGroupIndex}
       ::= {acKpiSipRecStatsCurrentIpGroupTable 1}



     -- ****************************************
     -- acKpiSipRecStatsCurrentIpGroup TABLE
     -- ****************************************
     AcKpiSipRecStatsCurrentIpGroupEntry ::= SEQUENCE {
       acKpiSipRecStatsCurrentIpGroupIndex             Unsigned32,
       acKpiSipRecStatsCurrentIpGroupSipRecSessions    Gauge32,
       acKpiSipRecStatsCurrentIpGroupSipRecRate        Gauge32
     }



     acKpiSipRecStatsCurrentIpGroupIndex OBJECT-TYPE
       SYNTAX Unsigned32 (0..32767)
       MAX-ACCESS not-accessible
       STATUS current
       DESCRIPTION
           "
AC INI-Param: N/A"
       ::= {acKpiSipRecStatsCurrentIpGroupEntry 1}



     acKpiSipRecStatsCurrentIpGroupSipRecSessions OBJECT-TYPE
       SYNTAX Gauge32
       MAX-ACCESS read-only
       STATUS current
       DESCRIPTION
           "Number of active SIP-REC sessions.
AC INI-Param: N/A"
       ::= {acKpiSipRecStatsCurrentIpGroupEntry 2}



     acKpiSipRecStatsCurrentIpGroupSipRecRate OBJECT-TYPE
       SYNTAX Gauge32
       MAX-ACCESS read-only
       STATUS current
       DESCRIPTION
           "Establishment rate for SIP-REC sessions (sessions per second).
AC INI-Param: N/A"
       ::= {acKpiSipRecStatsCurrentIpGroupEntry 3}



     -- ****************************************
     -- acKpiSipRecStatsCurrentSrd table declaration
     -- ****************************************
     acKpiSipRecStatsCurrentSrdTable OBJECT-TYPE
       SYNTAX SEQUENCE OF AcKpiSipRecStatsCurrentSrdEntry
       MAX-ACCESS not-accessible
       STATUS current
       DESCRIPTION
           ""
       ::= {acKpiSipRecStatsCurrentTables 2}



     -- ****************************************
     -- acKpiSipRecStatsCurrentSrd table entry
     -- ****************************************
     acKpiSipRecStatsCurrentSrdEntry OBJECT-TYPE
       SYNTAX AcKpiSipRecStatsCurrentSrdEntry
       MAX-ACCESS not-accessible
       STATUS current
       DESCRIPTION
           ""
       INDEX {acKpiSipRecStatsCurrentSrdIndex}
       ::= {acKpiSipRecStatsCurrentSrdTable 1}



     -- ****************************************
     -- acKpiSipRecStatsCurrentSrd TABLE
     -- ****************************************
     AcKpiSipRecStatsCurrentSrdEntry ::= SEQUENCE {
       acKpiSipRecStatsCurrentSrdIndex                 Unsigned32,
       acKpiSipRecStatsCurrentSrdSipRecSessions        Gauge32,
       acKpiSipRecStatsCurrentSrdSipRecRate            Gauge32
     }



     acKpiSipRecStatsCurrentSrdIndex OBJECT-TYPE
       SYNTAX Unsigned32 (0..32767)
       MAX-ACCESS not-accessible
       STATUS current
       DESCRIPTION
           "
AC INI-Param: N/A"
       ::= {acKpiSipRecStatsCurrentSrdEntry 1}



     acKpiSipRecStatsCurrentSrdSipRecSessions OBJECT-TYPE
       SYNTAX Gauge32
       MAX-ACCESS read-only
       STATUS current
       DESCRIPTION
           "Number of active SIP-REC sessions.
AC INI-Param: N/A"
       ::= {acKpiSipRecStatsCurrentSrdEntry 2}



     acKpiSipRecStatsCurrentSrdSipRecRate OBJECT-TYPE
       SYNTAX Gauge32
       MAX-ACCESS read-only
       STATUS current
       DESCRIPTION
           "Establishment rate for SIP-REC sessions (sessions per second).
AC INI-Param: N/A"
       ::= {acKpiSipRecStatsCurrentSrdEntry 3}



     acKpiSipRecStatsInterval OBJECT IDENTIFIER ::= {acKpiSipRecStats 2}


     acKpiSipRecStatsIntervalGlobal OBJECT IDENTIFIER ::= {acKpiSipRecStatsInterval 1}


     -- ****************************************
     -- acKpiSipRecStatsIntervalGlobal table declaration
     -- ****************************************
     acKpiSipRecStatsIntervalGlobalTable OBJECT-TYPE
       SYNTAX SEQUENCE OF AcKpiSipRecStatsIntervalGlobalEntry
       MAX-ACCESS not-accessible
       STATUS current
       DESCRIPTION
           ""
       ::= {acKpiSipRecStatsIntervalGlobal 1}



     -- ****************************************
     -- acKpiSipRecStatsIntervalGlobal table entry
     -- ****************************************
     acKpiSipRecStatsIntervalGlobalEntry OBJECT-TYPE
       SYNTAX AcKpiSipRecStatsIntervalGlobalEntry
       MAX-ACCESS not-accessible
       STATUS current
       DESCRIPTION
           ""
       INDEX {acKpiSipRecStatsIntervalGlobalInterval}
       ::= {acKpiSipRecStatsIntervalGlobalTable 1}



     -- ****************************************
     -- acKpiSipRecStatsIntervalGlobal TABLE
     -- ****************************************
     AcKpiSipRecStatsIntervalGlobalEntry ::= SEQUENCE {
       acKpiSipRecStatsIntervalGlobalInterval          Unsigned32,
       acKpiSipRecStatsIntervalGlobalSipRecSessionsAvg Gauge32,
       acKpiSipRecStatsIntervalGlobalSipRecSessionsMax Gauge32,
       acKpiSipRecStatsIntervalGlobalSipRecRateAvg     Gauge32
     }



     acKpiSipRecStatsIntervalGlobalInterval OBJECT-TYPE
       SYNTAX Unsigned32 (1..200)
       MAX-ACCESS not-accessible
       STATUS current
       DESCRIPTION
           "
AC INI-Param: N/A"
       ::= {acKpiSipRecStatsIntervalGlobalEntry 1}



     acKpiSipRecStatsIntervalGlobalSipRecSessionsAvg OBJECT-TYPE
       SYNTAX Gauge32
       MAX-ACCESS read-only
       STATUS current
       DESCRIPTION
           "Average Number of active SIP-REC sessions.
AC INI-Param: N/A"
       ::= {acKpiSipRecStatsIntervalGlobalEntry 2}



     acKpiSipRecStatsIntervalGlobalSipRecSessionsMax OBJECT-TYPE
       SYNTAX Gauge32
       MAX-ACCESS read-only
       STATUS current
       DESCRIPTION
           "Maximum number of active SIP-REC sessions.
AC INI-Param: N/A"
       ::= {acKpiSipRecStatsIntervalGlobalEntry 3}



     acKpiSipRecStatsIntervalGlobalSipRecRateAvg OBJECT-TYPE
       SYNTAX Gauge32
       MAX-ACCESS read-only
       STATUS current
       DESCRIPTION
           "Average establishment rate for SIP-REC sessions (sessions per
second).
AC INI-Param: N/A"
       ::= {acKpiSipRecStatsIntervalGlobalEntry 4}



     acKpiSipRecStatsIntervalTables OBJECT IDENTIFIER ::= {acKpiSipRecStatsInterval 2}


     -- ****************************************
     -- acKpiSipRecStatsIntervalIpGroup table declaration
     -- ****************************************
     acKpiSipRecStatsIntervalIpGroupTable OBJECT-TYPE
       SYNTAX SEQUENCE OF AcKpiSipRecStatsIntervalIpGroupEntry
       MAX-ACCESS not-accessible
       STATUS current
       DESCRIPTION
           ""
       ::= {acKpiSipRecStatsIntervalTables 1}



     -- ****************************************
     -- acKpiSipRecStatsIntervalIpGroup table entry
     -- ****************************************
     acKpiSipRecStatsIntervalIpGroupEntry OBJECT-TYPE
       SYNTAX AcKpiSipRecStatsIntervalIpGroupEntry
       MAX-ACCESS not-accessible
       STATUS current
       DESCRIPTION
           ""
       INDEX {acKpiSipRecStatsIntervalIpGroupIndex,acKpiSipRecStatsIntervalIpGroupInterval}
       ::= {acKpiSipRecStatsIntervalIpGroupTable 1}



     -- ****************************************
     -- acKpiSipRecStatsIntervalIpGroup TABLE
     -- ****************************************
     AcKpiSipRecStatsIntervalIpGroupEntry ::= SEQUENCE {
       acKpiSipRecStatsIntervalIpGroupIndex            Unsigned32,
       acKpiSipRecStatsIntervalIpGroupInterval         Unsigned32,
       acKpiSipRecStatsIntervalIpGroupSipRecSessionsAvg 
                                                       Gauge32,
       acKpiSipRecStatsIntervalIpGroupSipRecSessionsMax 
                                                       Gauge32,
       acKpiSipRecStatsIntervalIpGroupSipRecRateAvg    Gauge32
     }



     acKpiSipRecStatsIntervalIpGroupIndex OBJECT-TYPE
       SYNTAX Unsigned32 (0..32767)
       MAX-ACCESS not-accessible
       STATUS current
       DESCRIPTION
           "
AC INI-Param: N/A"
       ::= {acKpiSipRecStatsIntervalIpGroupEntry 1}



     acKpiSipRecStatsIntervalIpGroupInterval OBJECT-TYPE
       SYNTAX Unsigned32 (1..200)
       MAX-ACCESS not-accessible
       STATUS current
       DESCRIPTION
           "
AC INI-Param: N/A"
       ::= {acKpiSipRecStatsIntervalIpGroupEntry 2}



     acKpiSipRecStatsIntervalIpGroupSipRecSessionsAvg OBJECT-TYPE
       SYNTAX Gauge32
       MAX-ACCESS read-only
       STATUS current
       DESCRIPTION
           "Average number of active SIP-REC sessions.
AC INI-Param: N/A"
       ::= {acKpiSipRecStatsIntervalIpGroupEntry 3}



     acKpiSipRecStatsIntervalIpGroupSipRecSessionsMax OBJECT-TYPE
       SYNTAX Gauge32
       MAX-ACCESS read-only
       STATUS current
       DESCRIPTION
           "Maximum number of active SIP-REC sessions.
AC INI-Param: N/A"
       ::= {acKpiSipRecStatsIntervalIpGroupEntry 4}



     acKpiSipRecStatsIntervalIpGroupSipRecRateAvg OBJECT-TYPE
       SYNTAX Gauge32
       MAX-ACCESS read-only
       STATUS current
       DESCRIPTION
           "Average establishment rate for SIP-REC sessions (sessions per
second).
AC INI-Param: N/A"
       ::= {acKpiSipRecStatsIntervalIpGroupEntry 5}



     -- ****************************************
     -- acKpiSipRecStatsIntervalSrd table declaration
     -- ****************************************
     acKpiSipRecStatsIntervalSrdTable OBJECT-TYPE
       SYNTAX SEQUENCE OF AcKpiSipRecStatsIntervalSrdEntry
       MAX-ACCESS not-accessible
       STATUS current
       DESCRIPTION
           ""
       ::= {acKpiSipRecStatsIntervalTables 2}



     -- ****************************************
     -- acKpiSipRecStatsIntervalSrd table entry
     -- ****************************************
     acKpiSipRecStatsIntervalSrdEntry OBJECT-TYPE
       SYNTAX AcKpiSipRecStatsIntervalSrdEntry
       MAX-ACCESS not-accessible
       STATUS current
       DESCRIPTION
           ""
       INDEX {acKpiSipRecStatsIntervalSrdIndex,acKpiSipRecStatsIntervalSrdInterval}
       ::= {acKpiSipRecStatsIntervalSrdTable 1}



     -- ****************************************
     -- acKpiSipRecStatsIntervalSrd TABLE
     -- ****************************************
     AcKpiSipRecStatsIntervalSrdEntry ::= SEQUENCE {
       acKpiSipRecStatsIntervalSrdIndex                Unsigned32,
       acKpiSipRecStatsIntervalSrdInterval             Unsigned32,
       acKpiSipRecStatsIntervalSrdSipRecSessionsAvg    Gauge32,
       acKpiSipRecStatsIntervalSrdSipRecSessionsMax    Gauge32,
       acKpiSipRecStatsIntervalSrdSipRecRateAvg        Gauge32
     }



     acKpiSipRecStatsIntervalSrdIndex OBJECT-TYPE
       SYNTAX Unsigned32 (0..32767)
       MAX-ACCESS not-accessible
       STATUS current
       DESCRIPTION
           "
AC INI-Param: N/A"
       ::= {acKpiSipRecStatsIntervalSrdEntry 1}



     acKpiSipRecStatsIntervalSrdInterval OBJECT-TYPE
       SYNTAX Unsigned32 (1..200)
       MAX-ACCESS not-accessible
       STATUS current
       DESCRIPTION
           "
AC INI-Param: N/A"
       ::= {acKpiSipRecStatsIntervalSrdEntry 2}



     acKpiSipRecStatsIntervalSrdSipRecSessionsAvg OBJECT-TYPE
       SYNTAX Gauge32
       MAX-ACCESS read-only
       STATUS current
       DESCRIPTION
           "Average number of active SIP-REC sessions.
AC INI-Param: N/A"
       ::= {acKpiSipRecStatsIntervalSrdEntry 3}



     acKpiSipRecStatsIntervalSrdSipRecSessionsMax OBJECT-TYPE
       SYNTAX Gauge32
       MAX-ACCESS read-only
       STATUS current
       DESCRIPTION
           "Maximum number of active SIP-REC sessions.
AC INI-Param: N/A"
       ::= {acKpiSipRecStatsIntervalSrdEntry 4}



     acKpiSipRecStatsIntervalSrdSipRecRateAvg OBJECT-TYPE
       SYNTAX Gauge32
       MAX-ACCESS read-only
       STATUS current
       DESCRIPTION
           "Average establishment rate for SIP-REC sessions (sessions per
second).
AC INI-Param: N/A"
       ::= {acKpiSipRecStatsIntervalSrdEntry 5}



     acKpiGateway OBJECT IDENTIFIER ::= {acKpi 4}


     acKpiGatewayCallStats OBJECT IDENTIFIER ::= {acKpiGateway 1}


     acKpiGatewayCallStatsCurrent OBJECT IDENTIFIER ::= {acKpiGatewayCallStats 1}


     acKpiGatewayCallStatsCurrentGlobal OBJECT IDENTIFIER ::= {acKpiGatewayCallStatsCurrent 1}


     acKpiGatewayCallStatsCurrentGlobalAnswerSeizureRatio OBJECT-TYPE
       SYNTAX Gauge32
       MAX-ACCESS read-only
       STATUS current
       DESCRIPTION
           "Answer/seizure ratio (ASR, %) over 1 min sliding window.
AC INI-Param: N/A"
       ::= {acKpiGatewayCallStatsCurrentGlobal 1}



     acKpiGatewayCallStatsCurrentGlobalForwardedCallsTel2IpTotal OBJECT-TYPE
       SYNTAX Counter64
       MAX-ACCESS read-only
       STATUS current
       DESCRIPTION
           "Total number of forwarded Tel->IP calls.
AC INI-Param: N/A"
       ::= {acKpiGatewayCallStatsCurrentGlobal 2}



     acKpiGatewayCallStatsCurrentGlobalForwardedCallsIp2TelTotal OBJECT-TYPE
       SYNTAX Counter64
       MAX-ACCESS read-only
       STATUS current
       DESCRIPTION
           "Total number of forwarded IP->Tel calls.
AC INI-Param: N/A"
       ::= {acKpiGatewayCallStatsCurrentGlobal 3}



     acKpiGatewayCallStatsCurrentGlobalFailedCallsOtherTel2IpTotal OBJECT-TYPE
       SYNTAX Counter64
       MAX-ACCESS read-only
       STATUS current
       DESCRIPTION
           "Total number of failed Tel->IP calls due to other reasons.
AC INI-Param: N/A"
       ::= {acKpiGatewayCallStatsCurrentGlobal 4}



     acKpiGatewayCallStatsCurrentGlobalFailedCallsOtherIp2TelTotal OBJECT-TYPE
       SYNTAX Counter64
       MAX-ACCESS read-only
       STATUS current
       DESCRIPTION
           "Total number of failed IP->Tel calls due to other reasons.
AC INI-Param: N/A"
       ::= {acKpiGatewayCallStatsCurrentGlobal 5}



     acKpiGatewayCallStatsCurrentGlobalFailedCallsNoRouteTel2IpTotal OBJECT-TYPE
       SYNTAX Counter64
       MAX-ACCESS read-only
       STATUS current
       DESCRIPTION
           "Total number of failed Tel->IP calls due to routing failure.
AC INI-Param: N/A"
       ::= {acKpiGatewayCallStatsCurrentGlobal 6}



     acKpiGatewayCallStatsCurrentGlobalFailedCallsNoRouteIp2TelTotal OBJECT-TYPE
       SYNTAX Counter64
       MAX-ACCESS read-only
       STATUS current
       DESCRIPTION
           "Total number of failed IP->Tel calls due to routing failure.
AC INI-Param: N/A"
       ::= {acKpiGatewayCallStatsCurrentGlobal 7}



     acKpiGatewayCallStatsCurrentGlobalFailedCallsNoRscTel2IpTotal OBJECT-TYPE
       SYNTAX Counter64
       MAX-ACCESS read-only
       STATUS current
       DESCRIPTION
           "Total number of failed Tel->IP calls due to lack of internal
resources.
AC INI-Param: N/A"
       ::= {acKpiGatewayCallStatsCurrentGlobal 8}



     acKpiGatewayCallStatsCurrentGlobalFailedCallsNoRscIp2TelTotal OBJECT-TYPE
       SYNTAX Counter64
       MAX-ACCESS read-only
       STATUS current
       DESCRIPTION
           "Total number of failed IP->Tel calls due to lack of internal
resources.
AC INI-Param: N/A"
       ::= {acKpiGatewayCallStatsCurrentGlobal 9}



     acKpiGatewayCallStatsCurrentGlobalFailedCallsNoCapMatchTel2IpTotal OBJECT-TYPE
       SYNTAX Counter64
       MAX-ACCESS read-only
       STATUS current
       DESCRIPTION
           "Total number of failed Tel->IP calls due to media mismatch.
AC INI-Param: N/A"
       ::= {acKpiGatewayCallStatsCurrentGlobal 10}



     acKpiGatewayCallStatsCurrentGlobalFailedCallsNoCapMatchIp2TelTotal OBJECT-TYPE
       SYNTAX Counter64
       MAX-ACCESS read-only
       STATUS current
       DESCRIPTION
           "Total number of failed IP->Tel calls due to media mismatch.
AC INI-Param: N/A"
       ::= {acKpiGatewayCallStatsCurrentGlobal 11}



     acKpiGatewayCallStatsCurrentGlobalFailedCallsNoAnswerTel2IpTotal OBJECT-TYPE
       SYNTAX Counter64
       MAX-ACCESS read-only
       STATUS current
       DESCRIPTION
           "Total number of failed Tel->IP calls due to no answer from the
callee.
AC INI-Param: N/A"
       ::= {acKpiGatewayCallStatsCurrentGlobal 12}



     acKpiGatewayCallStatsCurrentGlobalFailedCallsNoAnswerIp2TelTotal OBJECT-TYPE
       SYNTAX Counter64
       MAX-ACCESS read-only
       STATUS current
       DESCRIPTION
           "Total number of failed IP->Tel calls due to no answer from the
callee.
AC INI-Param: N/A"
       ::= {acKpiGatewayCallStatsCurrentGlobal 13}



     acKpiGatewayCallStatsCurrentGlobalFailedCallsBusyTel2IpTotal OBJECT-TYPE
       SYNTAX Counter64
       MAX-ACCESS read-only
       STATUS current
       DESCRIPTION
           "Total number of failed Tel->IP calls due to callee being busy.
AC INI-Param: N/A"
       ::= {acKpiGatewayCallStatsCurrentGlobal 14}



     acKpiGatewayCallStatsCurrentGlobalFailedCallsBusyIp2TelTotal OBJECT-TYPE
       SYNTAX Counter64
       MAX-ACCESS read-only
       STATUS current
       DESCRIPTION
           "Total number of failed IP->Tel calls due to callee being busy.
AC INI-Param: N/A"
       ::= {acKpiGatewayCallStatsCurrentGlobal 15}



     acKpiGatewayCallStatsCurrentGlobalAverageCallDuration OBJECT-TYPE
       SYNTAX Gauge32
       MAX-ACCESS read-only
       STATUS current
       DESCRIPTION
           "Average call duration (ACD, seconds) over 1 min sliding window.
AC INI-Param: N/A"
       ::= {acKpiGatewayCallStatsCurrentGlobal 16}



     acKpiGatewayCallStatsCurrentGlobalEstablishedCallsRateTel2Ip OBJECT-TYPE
       SYNTAX Gauge32
       MAX-ACCESS read-only
       STATUS current
       DESCRIPTION
           "Rate of established Tel->IP calls (call establish per second).
AC INI-Param: N/A"
       ::= {acKpiGatewayCallStatsCurrentGlobal 17}



     acKpiGatewayCallStatsCurrentGlobalEstablishedCallsRateIp2Tel OBJECT-TYPE
       SYNTAX Gauge32
       MAX-ACCESS read-only
       STATUS current
       DESCRIPTION
           "Rate of established IP->Tel calls (call attempts per second).
AC INI-Param: N/A"
       ::= {acKpiGatewayCallStatsCurrentGlobal 18}



     acKpiGatewayCallStatsCurrentGlobalEstablishedFaxTel2IpTotal OBJECT-TYPE
       SYNTAX Counter64
       MAX-ACCESS read-only
       STATUS current
       DESCRIPTION
           "Total number of established Tel->IP fax calls.
AC INI-Param: N/A"
       ::= {acKpiGatewayCallStatsCurrentGlobal 19}



     acKpiGatewayCallStatsCurrentGlobalEstablishedFaxIp2TelTotal OBJECT-TYPE
       SYNTAX Counter64
       MAX-ACCESS read-only
       STATUS current
       DESCRIPTION
           "Total number of established IP->Tel fax calls.
AC INI-Param: N/A"
       ::= {acKpiGatewayCallStatsCurrentGlobal 20}



     acKpiGatewayCallStatsCurrentGlobalEstablishedCallsTel2IpTotal OBJECT-TYPE
       SYNTAX Counter64
       MAX-ACCESS read-only
       STATUS current
       DESCRIPTION
           "Total number of established Tel->IP calls.
AC INI-Param: N/A"
       ::= {acKpiGatewayCallStatsCurrentGlobal 21}



     acKpiGatewayCallStatsCurrentGlobalEstablishedCallsIp2TelTotal OBJECT-TYPE
       SYNTAX Counter64
       MAX-ACCESS read-only
       STATUS current
       DESCRIPTION
           "Total number of established IP->Tel calls.
AC INI-Param: N/A"
       ::= {acKpiGatewayCallStatsCurrentGlobal 22}



     acKpiGatewayCallStatsCurrentGlobalAttemptedFaxTel2IpTotal OBJECT-TYPE
       SYNTAX Counter64
       MAX-ACCESS read-only
       STATUS current
       DESCRIPTION
           "Total number of attempted fax calls.
AC INI-Param: N/A"
       ::= {acKpiGatewayCallStatsCurrentGlobal 23}



     acKpiGatewayCallStatsCurrentGlobalAttemptedFaxIp2TelTotal OBJECT-TYPE
       SYNTAX Counter64
       MAX-ACCESS read-only
       STATUS current
       DESCRIPTION
           "Total number of attempted IP->Tel fax calls.
AC INI-Param: N/A"
       ::= {acKpiGatewayCallStatsCurrentGlobal 24}



     acKpiGatewayCallStatsCurrentGlobalAttemptedCallsRateTel2Ip OBJECT-TYPE
       SYNTAX Gauge32
       MAX-ACCESS read-only
       STATUS current
       DESCRIPTION
           "Rate of attempted Tel->IP calls (call attempts per second).
AC INI-Param: N/A"
       ::= {acKpiGatewayCallStatsCurrentGlobal 25}



     acKpiGatewayCallStatsCurrentGlobalAttemptedCallsTel2IpTotal OBJECT-TYPE
       SYNTAX Counter64
       MAX-ACCESS read-only
       STATUS current
       DESCRIPTION
           "Total number of attempted Tel->IP calls.
AC INI-Param: N/A"
       ::= {acKpiGatewayCallStatsCurrentGlobal 26}



     acKpiGatewayCallStatsCurrentGlobalAttemptedCallsRateIp2Tel OBJECT-TYPE
       SYNTAX Gauge32
       MAX-ACCESS read-only
       STATUS current
       DESCRIPTION
           "Rate of attempted IP->Tel calls (call attempts per second).
AC INI-Param: N/A"
       ::= {acKpiGatewayCallStatsCurrentGlobal 27}



     acKpiGatewayCallStatsCurrentGlobalAttemptedCallsIp2TelTotal OBJECT-TYPE
       SYNTAX Counter64
       MAX-ACCESS read-only
       STATUS current
       DESCRIPTION
           "Total number of attempted IP->Tel calls.
AC INI-Param: N/A"
       ::= {acKpiGatewayCallStatsCurrentGlobal 28}



     acKpiGatewayCallStatsCurrentGlobalActiveCallsTel2Ip OBJECT-TYPE
       SYNTAX Gauge32
       MAX-ACCESS read-only
       STATUS current
       DESCRIPTION
           "Number of active Tel->IP calls.
AC INI-Param: N/A"
       ::= {acKpiGatewayCallStatsCurrentGlobal 29}



     acKpiGatewayCallStatsCurrentGlobalActiveCallsIp2Tel OBJECT-TYPE
       SYNTAX Gauge32
       MAX-ACCESS read-only
       STATUS current
       DESCRIPTION
           "Number of active IP->Tel calls.
AC INI-Param: N/A"
       ::= {acKpiGatewayCallStatsCurrentGlobal 30}



     acKpiGatewayCallStatsCurrentGlobalActiveCalls OBJECT-TYPE
       SYNTAX Gauge32
       MAX-ACCESS read-only
       STATUS current
       DESCRIPTION
           "Number of active calls.
AC INI-Param: N/A"
       ::= {acKpiGatewayCallStatsCurrentGlobal 31}



     acKpiGatewayCallStatsCurrentTables OBJECT IDENTIFIER ::= {acKpiGatewayCallStatsCurrent 2}


     -- ****************************************
     -- acKpiGatewayCallStatsCurrentIpGroup table declaration
     -- ****************************************
     acKpiGatewayCallStatsCurrentIpGroupTable OBJECT-TYPE
       SYNTAX SEQUENCE OF AcKpiGatewayCallStatsCurrentIpGroupEntry
       MAX-ACCESS not-accessible
       STATUS current
       DESCRIPTION
           ""
       ::= {acKpiGatewayCallStatsCurrentTables 1}



     -- ****************************************
     -- acKpiGatewayCallStatsCurrentIpGroup table entry
     -- ****************************************
     acKpiGatewayCallStatsCurrentIpGroupEntry OBJECT-TYPE
       SYNTAX AcKpiGatewayCallStatsCurrentIpGroupEntry
       MAX-ACCESS not-accessible
       STATUS current
       DESCRIPTION
           ""
       INDEX {acKpiGatewayCallStatsCurrentIpGroupIndex}
       ::= {acKpiGatewayCallStatsCurrentIpGroupTable 1}



     -- ****************************************
     -- acKpiGatewayCallStatsCurrentIpGroup TABLE
     -- ****************************************
     AcKpiGatewayCallStatsCurrentIpGroupEntry ::= SEQUENCE {
       acKpiGatewayCallStatsCurrentIpGroupIndex        Unsigned32,
       acKpiGatewayCallStatsCurrentIpGroupAnswerSeizureRatio 
                                                       Gauge32,
       acKpiGatewayCallStatsCurrentIpGroupForwardedCallsTel2IpTotal 
                                                       Counter64,
       acKpiGatewayCallStatsCurrentIpGroupForwardedCallsIp2TelTotal 
                                                       Counter64,
       acKpiGatewayCallStatsCurrentIpGroupFailedCallsOtherTel2IpTotal 
                                                       Counter64,
       acKpiGatewayCallStatsCurrentIpGroupFailedCallsOtherIp2TelTotal 
                                                       Counter64,
       acKpiGatewayCallStatsCurrentIpGroupFailedCallsNoRouteTel2IpTotal 
                                                       Counter64,
       acKpiGatewayCallStatsCurrentIpGroupFailedCallsNoRouteIp2TelTotal 
                                                       Counter64,
       acKpiGatewayCallStatsCurrentIpGroupFailedCallsNoRscTel2IpTotal 
                                                       Counter64,
       acKpiGatewayCallStatsCurrentIpGroupFailedCallsNoRscIp2TelTotal 
                                                       Counter64,
       acKpiGatewayCallStatsCurrentIpGroupFailedCallsNoCapMatchTel2IpTotal 
                                                       Counter64,
       acKpiGatewayCallStatsCurrentIpGroupFailedCallsNoCapMatchIp2TelTotal 
                                                       Counter64,
       acKpiGatewayCallStatsCurrentIpGroupFailedCallsNoAnswerTel2IpTotal 
                                                       Counter64,
       acKpiGatewayCallStatsCurrentIpGroupFailedCallsNoAnswerIp2TelTotal 
                                                       Counter64,
       acKpiGatewayCallStatsCurrentIpGroupFailedCallsBusyTel2IpTotal 
                                                       Counter64,
       acKpiGatewayCallStatsCurrentIpGroupFailedCallsBusyIp2TelTotal 
                                                       Counter64,
       acKpiGatewayCallStatsCurrentIpGroupAverageCallDuration 
                                                       Gauge32,
       acKpiGatewayCallStatsCurrentIpGroupEstablishedCallsRateTel2Ip 
                                                       Gauge32,
       acKpiGatewayCallStatsCurrentIpGroupEstablishedCallsRateIp2Tel 
                                                       Gauge32,
       acKpiGatewayCallStatsCurrentIpGroupEstablishedFaxTel2IpTotal 
                                                       Counter64,
       acKpiGatewayCallStatsCurrentIpGroupEstablishedFaxIp2TelTotal 
                                                       Counter64,
       acKpiGatewayCallStatsCurrentIpGroupEstablishedCallsTel2IpTotal 
                                                       Counter64,
       acKpiGatewayCallStatsCurrentIpGroupEstablishedCallsIp2TelTotal 
                                                       Counter64,
       acKpiGatewayCallStatsCurrentIpGroupAttemptedFaxTel2IpTotal 
                                                       Counter64,
       acKpiGatewayCallStatsCurrentIpGroupAttemptedFaxIp2TelTotal 
                                                       Counter64,
       acKpiGatewayCallStatsCurrentIpGroupAttemptedCallsRateTel2Ip 
                                                       Gauge32,
       acKpiGatewayCallStatsCurrentIpGroupAttemptedCallsTel2IpTotal 
                                                       Counter64,
       acKpiGatewayCallStatsCurrentIpGroupAttemptedCallsRateIp2Tel 
                                                       Gauge32,
       acKpiGatewayCallStatsCurrentIpGroupAttemptedCallsIp2TelTotal 
                                                       Counter64,
       acKpiGatewayCallStatsCurrentIpGroupActiveCallsTel2Ip 
                                                       Gauge32,
       acKpiGatewayCallStatsCurrentIpGroupActiveCallsIp2Tel 
                                                       Gauge32,
       acKpiGatewayCallStatsCurrentIpGroupActiveCalls  Gauge32
     }



     acKpiGatewayCallStatsCurrentIpGroupIndex OBJECT-TYPE
       SYNTAX Unsigned32 (0..32767)
       MAX-ACCESS not-accessible
       STATUS current
       DESCRIPTION
           "
AC INI-Param: N/A"
       ::= {acKpiGatewayCallStatsCurrentIpGroupEntry 1}



     acKpiGatewayCallStatsCurrentIpGroupAnswerSeizureRatio OBJECT-TYPE
       SYNTAX Gauge32
       MAX-ACCESS read-only
       STATUS current
       DESCRIPTION
           "Answer/seizure ratio (ASR, %) over 1 min sliding window.
AC INI-Param: N/A"
       ::= {acKpiGatewayCallStatsCurrentIpGroupEntry 2}



     acKpiGatewayCallStatsCurrentIpGroupForwardedCallsTel2IpTotal OBJECT-TYPE
       SYNTAX Counter64
       MAX-ACCESS read-only
       STATUS current
       DESCRIPTION
           "Total number of forwarded Tel->IP calls.
AC INI-Param: N/A"
       ::= {acKpiGatewayCallStatsCurrentIpGroupEntry 3}



     acKpiGatewayCallStatsCurrentIpGroupForwardedCallsIp2TelTotal OBJECT-TYPE
       SYNTAX Counter64
       MAX-ACCESS read-only
       STATUS current
       DESCRIPTION
           "Total number of forwarded IP->Tel calls.
AC INI-Param: N/A"
       ::= {acKpiGatewayCallStatsCurrentIpGroupEntry 4}



     acKpiGatewayCallStatsCurrentIpGroupFailedCallsOtherTel2IpTotal OBJECT-TYPE
       SYNTAX Counter64
       MAX-ACCESS read-only
       STATUS current
       DESCRIPTION
           "Total number of failed Tel->IP calls due to other reasons.
AC INI-Param: N/A"
       ::= {acKpiGatewayCallStatsCurrentIpGroupEntry 5}



     acKpiGatewayCallStatsCurrentIpGroupFailedCallsOtherIp2TelTotal OBJECT-TYPE
       SYNTAX Counter64
       MAX-ACCESS read-only
       STATUS current
       DESCRIPTION
           "Total number of failed IP->Tel calls due to other reasons.
AC INI-Param: N/A"
       ::= {acKpiGatewayCallStatsCurrentIpGroupEntry 6}



     acKpiGatewayCallStatsCurrentIpGroupFailedCallsNoRouteTel2IpTotal OBJECT-TYPE
       SYNTAX Counter64
       MAX-ACCESS read-only
       STATUS current
       DESCRIPTION
           "Total number of failed Tel->IP calls due to routing failure.
AC INI-Param: N/A"
       ::= {acKpiGatewayCallStatsCurrentIpGroupEntry 7}



     acKpiGatewayCallStatsCurrentIpGroupFailedCallsNoRouteIp2TelTotal OBJECT-TYPE
       SYNTAX Counter64
       MAX-ACCESS read-only
       STATUS current
       DESCRIPTION
           "Total number of failed IP->Tel calls due to routing failure.
AC INI-Param: N/A"
       ::= {acKpiGatewayCallStatsCurrentIpGroupEntry 8}



     acKpiGatewayCallStatsCurrentIpGroupFailedCallsNoRscTel2IpTotal OBJECT-TYPE
       SYNTAX Counter64
       MAX-ACCESS read-only
       STATUS current
       DESCRIPTION
           "Total number of failed Tel->IP calls due to lack of internal
resources.
AC INI-Param: N/A"
       ::= {acKpiGatewayCallStatsCurrentIpGroupEntry 9}



     acKpiGatewayCallStatsCurrentIpGroupFailedCallsNoRscIp2TelTotal OBJECT-TYPE
       SYNTAX Counter64
       MAX-ACCESS read-only
       STATUS current
       DESCRIPTION
           "Total number of failed IP->Tel calls due to lack of internal
resources.
AC INI-Param: N/A"
       ::= {acKpiGatewayCallStatsCurrentIpGroupEntry 10}



     acKpiGatewayCallStatsCurrentIpGroupFailedCallsNoCapMatchTel2IpTotal OBJECT-TYPE
       SYNTAX Counter64
       MAX-ACCESS read-only
       STATUS current
       DESCRIPTION
           "Total number of failed Tel->IP calls due to media mismatch.
AC INI-Param: N/A"
       ::= {acKpiGatewayCallStatsCurrentIpGroupEntry 11}



     acKpiGatewayCallStatsCurrentIpGroupFailedCallsNoCapMatchIp2TelTotal OBJECT-TYPE
       SYNTAX Counter64
       MAX-ACCESS read-only
       STATUS current
       DESCRIPTION
           "Total number of failed IP->Tel calls due to media mismatch.
AC INI-Param: N/A"
       ::= {acKpiGatewayCallStatsCurrentIpGroupEntry 12}



     acKpiGatewayCallStatsCurrentIpGroupFailedCallsNoAnswerTel2IpTotal OBJECT-TYPE
       SYNTAX Counter64
       MAX-ACCESS read-only
       STATUS current
       DESCRIPTION
           "Total number of failed Tel->IP calls due to no answer from the
callee.
AC INI-Param: N/A"
       ::= {acKpiGatewayCallStatsCurrentIpGroupEntry 13}



     acKpiGatewayCallStatsCurrentIpGroupFailedCallsNoAnswerIp2TelTotal OBJECT-TYPE
       SYNTAX Counter64
       MAX-ACCESS read-only
       STATUS current
       DESCRIPTION
           "Total number of failed IP->Tel calls due to no answer from the
callee.
AC INI-Param: N/A"
       ::= {acKpiGatewayCallStatsCurrentIpGroupEntry 14}



     acKpiGatewayCallStatsCurrentIpGroupFailedCallsBusyTel2IpTotal OBJECT-TYPE
       SYNTAX Counter64
       MAX-ACCESS read-only
       STATUS current
       DESCRIPTION
           "Total number of failed Tel->IP calls due to callee being busy.
AC INI-Param: N/A"
       ::= {acKpiGatewayCallStatsCurrentIpGroupEntry 15}



     acKpiGatewayCallStatsCurrentIpGroupFailedCallsBusyIp2TelTotal OBJECT-TYPE
       SYNTAX Counter64
       MAX-ACCESS read-only
       STATUS current
       DESCRIPTION
           "Total number of failed IP->Tel calls due to callee being busy.
AC INI-Param: N/A"
       ::= {acKpiGatewayCallStatsCurrentIpGroupEntry 16}



     acKpiGatewayCallStatsCurrentIpGroupAverageCallDuration OBJECT-TYPE
       SYNTAX Gauge32
       MAX-ACCESS read-only
       STATUS current
       DESCRIPTION
           "Average call duration (ACD, seconds) over 1 min sliding window.
AC INI-Param: N/A"
       ::= {acKpiGatewayCallStatsCurrentIpGroupEntry 17}



     acKpiGatewayCallStatsCurrentIpGroupEstablishedCallsRateTel2Ip OBJECT-TYPE
       SYNTAX Gauge32
       MAX-ACCESS read-only
       STATUS current
       DESCRIPTION
           "Rate of established Tel->IP calls (call establish per second).
AC INI-Param: N/A"
       ::= {acKpiGatewayCallStatsCurrentIpGroupEntry 18}



     acKpiGatewayCallStatsCurrentIpGroupEstablishedCallsRateIp2Tel OBJECT-TYPE
       SYNTAX Gauge32
       MAX-ACCESS read-only
       STATUS current
       DESCRIPTION
           "Rate of established IP->Tel calls (call establish per second).
AC INI-Param: N/A"
       ::= {acKpiGatewayCallStatsCurrentIpGroupEntry 19}



     acKpiGatewayCallStatsCurrentIpGroupEstablishedFaxTel2IpTotal OBJECT-TYPE
       SYNTAX Counter64
       MAX-ACCESS read-only
       STATUS current
       DESCRIPTION
           "Total number of established Tel->IP fax calls.
AC INI-Param: N/A"
       ::= {acKpiGatewayCallStatsCurrentIpGroupEntry 20}



     acKpiGatewayCallStatsCurrentIpGroupEstablishedFaxIp2TelTotal OBJECT-TYPE
       SYNTAX Counter64
       MAX-ACCESS read-only
       STATUS current
       DESCRIPTION
           "Total number of established IP->Tel fax calls.
AC INI-Param: N/A"
       ::= {acKpiGatewayCallStatsCurrentIpGroupEntry 21}



     acKpiGatewayCallStatsCurrentIpGroupEstablishedCallsTel2IpTotal OBJECT-TYPE
       SYNTAX Counter64
       MAX-ACCESS read-only
       STATUS current
       DESCRIPTION
           "Total number of established Tel->IP calls.
AC INI-Param: N/A"
       ::= {acKpiGatewayCallStatsCurrentIpGroupEntry 22}



     acKpiGatewayCallStatsCurrentIpGroupEstablishedCallsIp2TelTotal OBJECT-TYPE
       SYNTAX Counter64
       MAX-ACCESS read-only
       STATUS current
       DESCRIPTION
           "Total number of established IP->Tel calls.
AC INI-Param: N/A"
       ::= {acKpiGatewayCallStatsCurrentIpGroupEntry 23}



     acKpiGatewayCallStatsCurrentIpGroupAttemptedFaxTel2IpTotal OBJECT-TYPE
       SYNTAX Counter64
       MAX-ACCESS read-only
       STATUS current
       DESCRIPTION
           "Total number of attempted fax calls.
AC INI-Param: N/A"
       ::= {acKpiGatewayCallStatsCurrentIpGroupEntry 24}



     acKpiGatewayCallStatsCurrentIpGroupAttemptedFaxIp2TelTotal OBJECT-TYPE
       SYNTAX Counter64
       MAX-ACCESS read-only
       STATUS current
       DESCRIPTION
           "Total number of attempted IP->Tel fax calls.
AC INI-Param: N/A"
       ::= {acKpiGatewayCallStatsCurrentIpGroupEntry 25}



     acKpiGatewayCallStatsCurrentIpGroupAttemptedCallsRateTel2Ip OBJECT-TYPE
       SYNTAX Gauge32
       MAX-ACCESS read-only
       STATUS current
       DESCRIPTION
           "Rate of attempted Tel->IP calls (call attempts per second).
AC INI-Param: N/A"
       ::= {acKpiGatewayCallStatsCurrentIpGroupEntry 26}



     acKpiGatewayCallStatsCurrentIpGroupAttemptedCallsTel2IpTotal OBJECT-TYPE
       SYNTAX Counter64
       MAX-ACCESS read-only
       STATUS current
       DESCRIPTION
           "Total number of attempted Tel->IP calls.
AC INI-Param: N/A"
       ::= {acKpiGatewayCallStatsCurrentIpGroupEntry 27}



     acKpiGatewayCallStatsCurrentIpGroupAttemptedCallsRateIp2Tel OBJECT-TYPE
       SYNTAX Gauge32
       MAX-ACCESS read-only
       STATUS current
       DESCRIPTION
           "Rate of attempted IP->Tel calls (call attempts per second).
AC INI-Param: N/A"
       ::= {acKpiGatewayCallStatsCurrentIpGroupEntry 28}



     acKpiGatewayCallStatsCurrentIpGroupAttemptedCallsIp2TelTotal OBJECT-TYPE
       SYNTAX Counter64
       MAX-ACCESS read-only
       STATUS current
       DESCRIPTION
           "Total number of attempted IP->Tel calls.
AC INI-Param: N/A"
       ::= {acKpiGatewayCallStatsCurrentIpGroupEntry 29}



     acKpiGatewayCallStatsCurrentIpGroupActiveCallsTel2Ip OBJECT-TYPE
       SYNTAX Gauge32
       MAX-ACCESS read-only
       STATUS current
       DESCRIPTION
           "Number of active Tel->IP calls.
AC INI-Param: N/A"
       ::= {acKpiGatewayCallStatsCurrentIpGroupEntry 30}



     acKpiGatewayCallStatsCurrentIpGroupActiveCallsIp2Tel OBJECT-TYPE
       SYNTAX Gauge32
       MAX-ACCESS read-only
       STATUS current
       DESCRIPTION
           "Number of active IP->Tel calls.
AC INI-Param: N/A"
       ::= {acKpiGatewayCallStatsCurrentIpGroupEntry 31}



     acKpiGatewayCallStatsCurrentIpGroupActiveCalls OBJECT-TYPE
       SYNTAX Gauge32
       MAX-ACCESS read-only
       STATUS current
       DESCRIPTION
           "Number of active calls.
AC INI-Param: N/A"
       ::= {acKpiGatewayCallStatsCurrentIpGroupEntry 32}



     -- ****************************************
     -- acKpiGatewayCallStatsCurrentTrunkGroup table declaration
     -- ****************************************
     acKpiGatewayCallStatsCurrentTrunkGroupTable OBJECT-TYPE
       SYNTAX SEQUENCE OF AcKpiGatewayCallStatsCurrentTrunkGroupEntry
       MAX-ACCESS not-accessible
       STATUS current
       DESCRIPTION
           ""
       ::= {acKpiGatewayCallStatsCurrentTables 2}



     -- ****************************************
     -- acKpiGatewayCallStatsCurrentTrunkGroup table entry
     -- ****************************************
     acKpiGatewayCallStatsCurrentTrunkGroupEntry OBJECT-TYPE
       SYNTAX AcKpiGatewayCallStatsCurrentTrunkGroupEntry
       MAX-ACCESS not-accessible
       STATUS current
       DESCRIPTION
           ""
       INDEX {acKpiGatewayCallStatsCurrentTrunkGroupIndex}
       ::= {acKpiGatewayCallStatsCurrentTrunkGroupTable 1}



     -- ****************************************
     -- acKpiGatewayCallStatsCurrentTrunkGroup TABLE
     -- ****************************************
     AcKpiGatewayCallStatsCurrentTrunkGroupEntry ::= SEQUENCE {
       acKpiGatewayCallStatsCurrentTrunkGroupIndex     Unsigned32,
       acKpiGatewayCallStatsCurrentTrunkGroupAnswerSeizureRatio 
                                                       Gauge32,
       acKpiGatewayCallStatsCurrentTrunkGroupForwardedCallsTel2IpTotal 
                                                       Counter64,
       acKpiGatewayCallStatsCurrentTrunkGroupForwardedCallsIp2TelTotal 
                                                       Counter64,
       acKpiGatewayCallStatsCurrentTrunkGroupFailedCallsOtherTel2IpTotal 
                                                       Counter64,
       acKpiGatewayCallStatsCurrentTrunkGroupFailedCallsOtherIp2TelTotal 
                                                       Counter64,
       acKpiGatewayCallStatsCurrentTrunkGroupFailedCallsNoRouteTel2IpTotal 
                                                       Counter64,
       acKpiGatewayCallStatsCurrentTrunkGroupFailedCallsNoRouteIp2TelTotal 
                                                       Counter64,
       acKpiGatewayCallStatsCurrentTrunkGroupFailedCallsNoRscTel2IpTotal 
                                                       Counter64,
       acKpiGatewayCallStatsCurrentTrunkGroupFailedCallsNoRscIp2TelTotal 
                                                       Counter64,
       acKpiGatewayCallStatsCurrentTrunkGroupFailedCallsNoCapMatchTel2IpTotal 
                                                       Counter64,
       acKpiGatewayCallStatsCurrentTrunkGroupFailedCallsNoCapMatchIp2TelTotal 
                                                       Counter64,
       acKpiGatewayCallStatsCurrentTrunkGroupFailedCallsNoAnswerTel2IpTotal 
                                                       Counter64,
       acKpiGatewayCallStatsCurrentTrunkGroupFailedCallsNoAnswerIp2TelTotal 
                                                       Counter64,
       acKpiGatewayCallStatsCurrentTrunkGroupFailedCallsBusyTel2IpTotal 
                                                       Counter64,
       acKpiGatewayCallStatsCurrentTrunkGroupFailedCallsBusyIp2TelTotal 
                                                       Counter64,
       acKpiGatewayCallStatsCurrentTrunkGroupAverageCallDuration 
                                                       Gauge32,
       acKpiGatewayCallStatsCurrentTrunkGroupEstablishedCallsRateTel2Ip 
                                                       Gauge32,
       acKpiGatewayCallStatsCurrentTrunkGroupEstablishedCallsRateIp2Tel 
                                                       Gauge32,
       acKpiGatewayCallStatsCurrentTrunkGroupEstablishedFaxTel2IpTotal 
                                                       Counter64,
       acKpiGatewayCallStatsCurrentTrunkGroupEstablishedFaxIp2TelTotal 
                                                       Counter64,
       acKpiGatewayCallStatsCurrentTrunkGroupEstablishedCallsTel2IpTotal 
                                                       Counter64,
       acKpiGatewayCallStatsCurrentTrunkGroupEstablishedCallsIp2TelTotal 
                                                       Counter64,
       acKpiGatewayCallStatsCurrentTrunkGroupAttemptedFaxTel2IpTotal 
                                                       Counter64,
       acKpiGatewayCallStatsCurrentTrunkGroupAttemptedFaxIp2TelTotal 
                                                       Counter64,
       acKpiGatewayCallStatsCurrentTrunkGroupAttemptedCallsRateTel2Ip 
                                                       Gauge32,
       acKpiGatewayCallStatsCurrentTrunkGroupAttemptedCallsTel2IpTotal 
                                                       Counter64,
       acKpiGatewayCallStatsCurrentTrunkGroupAttemptedCallsRateIp2Tel 
                                                       Gauge32,
       acKpiGatewayCallStatsCurrentTrunkGroupAttemptedCallsIp2TelTotal 
                                                       Counter64,
       acKpiGatewayCallStatsCurrentTrunkGroupActiveCallsTel2Ip 
                                                       Gauge32,
       acKpiGatewayCallStatsCurrentTrunkGroupActiveCallsIp2Tel 
                                                       Gauge32,
       acKpiGatewayCallStatsCurrentTrunkGroupActiveCalls 
                                                       Gauge32
     }



     acKpiGatewayCallStatsCurrentTrunkGroupIndex OBJECT-TYPE
       SYNTAX Unsigned32 (0..32767)
       MAX-ACCESS not-accessible
       STATUS current
       DESCRIPTION
           "
AC INI-Param: N/A"
       ::= {acKpiGatewayCallStatsCurrentTrunkGroupEntry 1}



     acKpiGatewayCallStatsCurrentTrunkGroupAnswerSeizureRatio OBJECT-TYPE
       SYNTAX Gauge32
       MAX-ACCESS read-only
       STATUS current
       DESCRIPTION
           "Answer/seizure ratio (ASR, %) over 1 min sliding window.
AC INI-Param: N/A"
       ::= {acKpiGatewayCallStatsCurrentTrunkGroupEntry 2}



     acKpiGatewayCallStatsCurrentTrunkGroupForwardedCallsTel2IpTotal OBJECT-TYPE
       SYNTAX Counter64
       MAX-ACCESS read-only
       STATUS current
       DESCRIPTION
           "Total number of forwarded Tel->IP calls.
AC INI-Param: N/A"
       ::= {acKpiGatewayCallStatsCurrentTrunkGroupEntry 3}



     acKpiGatewayCallStatsCurrentTrunkGroupForwardedCallsIp2TelTotal OBJECT-TYPE
       SYNTAX Counter64
       MAX-ACCESS read-only
       STATUS current
       DESCRIPTION
           "Total number of forwarded IP->Tel calls.
AC INI-Param: N/A"
       ::= {acKpiGatewayCallStatsCurrentTrunkGroupEntry 4}



     acKpiGatewayCallStatsCurrentTrunkGroupFailedCallsOtherTel2IpTotal OBJECT-TYPE
       SYNTAX Counter64
       MAX-ACCESS read-only
       STATUS current
       DESCRIPTION
           "Total number of failed Tel->IP calls due to other reasons.
AC INI-Param: N/A"
       ::= {acKpiGatewayCallStatsCurrentTrunkGroupEntry 5}



     acKpiGatewayCallStatsCurrentTrunkGroupFailedCallsOtherIp2TelTotal OBJECT-TYPE
       SYNTAX Counter64
       MAX-ACCESS read-only
       STATUS current
       DESCRIPTION
           "Total number of failed IP->Tel calls due to other reasons.
AC INI-Param: N/A"
       ::= {acKpiGatewayCallStatsCurrentTrunkGroupEntry 6}



     acKpiGatewayCallStatsCurrentTrunkGroupFailedCallsNoRouteTel2IpTotal OBJECT-TYPE
       SYNTAX Counter64
       MAX-ACCESS read-only
       STATUS current
       DESCRIPTION
           "Total number of failed Tel->IP calls due to routing failure.
AC INI-Param: N/A"
       ::= {acKpiGatewayCallStatsCurrentTrunkGroupEntry 7}



     acKpiGatewayCallStatsCurrentTrunkGroupFailedCallsNoRouteIp2TelTotal OBJECT-TYPE
       SYNTAX Counter64
       MAX-ACCESS read-only
       STATUS current
       DESCRIPTION
           "Total number of failed IP->Tel calls due to routing failure.
AC INI-Param: N/A"
       ::= {acKpiGatewayCallStatsCurrentTrunkGroupEntry 8}



     acKpiGatewayCallStatsCurrentTrunkGroupFailedCallsNoRscTel2IpTotal OBJECT-TYPE
       SYNTAX Counter64
       MAX-ACCESS read-only
       STATUS current
       DESCRIPTION
           "Total number of failed Tel->IP calls due to lack of internal
resources.
AC INI-Param: N/A"
       ::= {acKpiGatewayCallStatsCurrentTrunkGroupEntry 9}



     acKpiGatewayCallStatsCurrentTrunkGroupFailedCallsNoRscIp2TelTotal OBJECT-TYPE
       SYNTAX Counter64
       MAX-ACCESS read-only
       STATUS current
       DESCRIPTION
           "Total number of failed IP->Tel calls due to lack of internal
resources.
AC INI-Param: N/A"
       ::= {acKpiGatewayCallStatsCurrentTrunkGroupEntry 10}



     acKpiGatewayCallStatsCurrentTrunkGroupFailedCallsNoCapMatchTel2IpTotal OBJECT-TYPE
       SYNTAX Counter64
       MAX-ACCESS read-only
       STATUS current
       DESCRIPTION
           "Total number of failed Tel->IP calls due to media mismatch.
AC INI-Param: N/A"
       ::= {acKpiGatewayCallStatsCurrentTrunkGroupEntry 11}



     acKpiGatewayCallStatsCurrentTrunkGroupFailedCallsNoCapMatchIp2TelTotal OBJECT-TYPE
       SYNTAX Counter64
       MAX-ACCESS read-only
       STATUS current
       DESCRIPTION
           "Total number of failed IP->Tel calls due to media mismatch.
AC INI-Param: N/A"
       ::= {acKpiGatewayCallStatsCurrentTrunkGroupEntry 12}



     acKpiGatewayCallStatsCurrentTrunkGroupFailedCallsNoAnswerTel2IpTotal OBJECT-TYPE
       SYNTAX Counter64
       MAX-ACCESS read-only
       STATUS current
       DESCRIPTION
           "Total number of failed Tel->IP calls due to no answer from the
callee.
AC INI-Param: N/A"
       ::= {acKpiGatewayCallStatsCurrentTrunkGroupEntry 13}



     acKpiGatewayCallStatsCurrentTrunkGroupFailedCallsNoAnswerIp2TelTotal OBJECT-TYPE
       SYNTAX Counter64
       MAX-ACCESS read-only
       STATUS current
       DESCRIPTION
           "Total number of failed IP->Tel calls due to no answer from the
callee.
AC INI-Param: N/A"
       ::= {acKpiGatewayCallStatsCurrentTrunkGroupEntry 14}



     acKpiGatewayCallStatsCurrentTrunkGroupFailedCallsBusyTel2IpTotal OBJECT-TYPE
       SYNTAX Counter64
       MAX-ACCESS read-only
       STATUS current
       DESCRIPTION
           "Total number of failed Tel->IP calls due to callee being busy.
AC INI-Param: N/A"
       ::= {acKpiGatewayCallStatsCurrentTrunkGroupEntry 15}



     acKpiGatewayCallStatsCurrentTrunkGroupFailedCallsBusyIp2TelTotal OBJECT-TYPE
       SYNTAX Counter64
       MAX-ACCESS read-only
       STATUS current
       DESCRIPTION
           "Total number of failed IP->Tel calls due to callee being busy.
AC INI-Param: N/A"
       ::= {acKpiGatewayCallStatsCurrentTrunkGroupEntry 16}



     acKpiGatewayCallStatsCurrentTrunkGroupAverageCallDuration OBJECT-TYPE
       SYNTAX Gauge32
       MAX-ACCESS read-only
       STATUS current
       DESCRIPTION
           "Average call duration (ACD, seconds) over 1 min sliding window.
AC INI-Param: N/A"
       ::= {acKpiGatewayCallStatsCurrentTrunkGroupEntry 17}



     acKpiGatewayCallStatsCurrentTrunkGroupEstablishedCallsRateTel2Ip OBJECT-TYPE
       SYNTAX Gauge32
       MAX-ACCESS read-only
       STATUS current
       DESCRIPTION
           "Rate of established Tel->IP calls (call establish per second).
AC INI-Param: N/A"
       ::= {acKpiGatewayCallStatsCurrentTrunkGroupEntry 18}



     acKpiGatewayCallStatsCurrentTrunkGroupEstablishedCallsRateIp2Tel OBJECT-TYPE
       SYNTAX Gauge32
       MAX-ACCESS read-only
       STATUS current
       DESCRIPTION
           "Rate of established IP->Tel calls (call establish per second).
AC INI-Param: N/A"
       ::= {acKpiGatewayCallStatsCurrentTrunkGroupEntry 19}



     acKpiGatewayCallStatsCurrentTrunkGroupEstablishedFaxTel2IpTotal OBJECT-TYPE
       SYNTAX Counter64
       MAX-ACCESS read-only
       STATUS current
       DESCRIPTION
           "Total number of established Tel->IP fax calls.
AC INI-Param: N/A"
       ::= {acKpiGatewayCallStatsCurrentTrunkGroupEntry 20}



     acKpiGatewayCallStatsCurrentTrunkGroupEstablishedFaxIp2TelTotal OBJECT-TYPE
       SYNTAX Counter64
       MAX-ACCESS read-only
       STATUS current
       DESCRIPTION
           "Total number of established IP->Tel fax calls.
AC INI-Param: N/A"
       ::= {acKpiGatewayCallStatsCurrentTrunkGroupEntry 21}



     acKpiGatewayCallStatsCurrentTrunkGroupEstablishedCallsTel2IpTotal OBJECT-TYPE
       SYNTAX Counter64
       MAX-ACCESS read-only
       STATUS current
       DESCRIPTION
           "Total number of established Tel->IP calls.
AC INI-Param: N/A"
       ::= {acKpiGatewayCallStatsCurrentTrunkGroupEntry 22}



     acKpiGatewayCallStatsCurrentTrunkGroupEstablishedCallsIp2TelTotal OBJECT-TYPE
       SYNTAX Counter64
       MAX-ACCESS read-only
       STATUS current
       DESCRIPTION
           "Total number of established IP->Tel calls.
AC INI-Param: N/A"
       ::= {acKpiGatewayCallStatsCurrentTrunkGroupEntry 23}



     acKpiGatewayCallStatsCurrentTrunkGroupAttemptedFaxTel2IpTotal OBJECT-TYPE
       SYNTAX Counter64
       MAX-ACCESS read-only
       STATUS current
       DESCRIPTION
           "Total number of attempted fax calls.
AC INI-Param: N/A"
       ::= {acKpiGatewayCallStatsCurrentTrunkGroupEntry 24}



     acKpiGatewayCallStatsCurrentTrunkGroupAttemptedFaxIp2TelTotal OBJECT-TYPE
       SYNTAX Counter64
       MAX-ACCESS read-only
       STATUS current
       DESCRIPTION
           "Total number of attempted IP->Tel fax calls.
AC INI-Param: N/A"
       ::= {acKpiGatewayCallStatsCurrentTrunkGroupEntry 25}



     acKpiGatewayCallStatsCurrentTrunkGroupAttemptedCallsRateTel2Ip OBJECT-TYPE
       SYNTAX Gauge32
       MAX-ACCESS read-only
       STATUS current
       DESCRIPTION
           "Rate of attempted Tel->IP calls (call attempts per second).
AC INI-Param: N/A"
       ::= {acKpiGatewayCallStatsCurrentTrunkGroupEntry 26}



     acKpiGatewayCallStatsCurrentTrunkGroupAttemptedCallsTel2IpTotal OBJECT-TYPE
       SYNTAX Counter64
       MAX-ACCESS read-only
       STATUS current
       DESCRIPTION
           "Total number of attempted Tel->IP calls.
AC INI-Param: N/A"
       ::= {acKpiGatewayCallStatsCurrentTrunkGroupEntry 27}



     acKpiGatewayCallStatsCurrentTrunkGroupAttemptedCallsRateIp2Tel OBJECT-TYPE
       SYNTAX Gauge32
       MAX-ACCESS read-only
       STATUS current
       DESCRIPTION
           "Rate of attempted IP->Tel calls (call attempts per second).
AC INI-Param: N/A"
       ::= {acKpiGatewayCallStatsCurrentTrunkGroupEntry 28}



     acKpiGatewayCallStatsCurrentTrunkGroupAttemptedCallsIp2TelTotal OBJECT-TYPE
       SYNTAX Counter64
       MAX-ACCESS read-only
       STATUS current
       DESCRIPTION
           "Total number of attempted IP->Tel calls.
AC INI-Param: N/A"
       ::= {acKpiGatewayCallStatsCurrentTrunkGroupEntry 29}



     acKpiGatewayCallStatsCurrentTrunkGroupActiveCallsTel2Ip OBJECT-TYPE
       SYNTAX Gauge32
       MAX-ACCESS read-only
       STATUS current
       DESCRIPTION
           "Number of active Tel->IP calls.
AC INI-Param: N/A"
       ::= {acKpiGatewayCallStatsCurrentTrunkGroupEntry 30}



     acKpiGatewayCallStatsCurrentTrunkGroupActiveCallsIp2Tel OBJECT-TYPE
       SYNTAX Gauge32
       MAX-ACCESS read-only
       STATUS current
       DESCRIPTION
           "Number of active IP->Tel calls.
AC INI-Param: N/A"
       ::= {acKpiGatewayCallStatsCurrentTrunkGroupEntry 31}



     acKpiGatewayCallStatsCurrentTrunkGroupActiveCalls OBJECT-TYPE
       SYNTAX Gauge32
       MAX-ACCESS read-only
       STATUS current
       DESCRIPTION
           "Number of active calls.
AC INI-Param: N/A"
       ::= {acKpiGatewayCallStatsCurrentTrunkGroupEntry 32}



     acKpiGatewayCallStatsInterval OBJECT IDENTIFIER ::= {acKpiGatewayCallStats 2}


     acKpiGatewayCallStatsIntervalGlobal OBJECT IDENTIFIER ::= {acKpiGatewayCallStatsInterval 1}


     -- ****************************************
     -- acKpiGatewayCallStatsIntervalGlobal table declaration
     -- ****************************************
     acKpiGatewayCallStatsIntervalGlobalTable OBJECT-TYPE
       SYNTAX SEQUENCE OF AcKpiGatewayCallStatsIntervalGlobalEntry
       MAX-ACCESS not-accessible
       STATUS current
       DESCRIPTION
           ""
       ::= {acKpiGatewayCallStatsIntervalGlobal 1}



     -- ****************************************
     -- acKpiGatewayCallStatsIntervalGlobal table entry
     -- ****************************************
     acKpiGatewayCallStatsIntervalGlobalEntry OBJECT-TYPE
       SYNTAX AcKpiGatewayCallStatsIntervalGlobalEntry
       MAX-ACCESS not-accessible
       STATUS current
       DESCRIPTION
           ""
       INDEX {acKpiGatewayCallStatsIntervalGlobalInterval}
       ::= {acKpiGatewayCallStatsIntervalGlobalTable 1}



     -- ****************************************
     -- acKpiGatewayCallStatsIntervalGlobal TABLE
     -- ****************************************
     AcKpiGatewayCallStatsIntervalGlobalEntry ::= SEQUENCE {
       acKpiGatewayCallStatsIntervalGlobalInterval     Unsigned32,
       acKpiGatewayCallStatsIntervalGlobalAnswerSeizureRatioAvg 
                                                       Gauge32,
       acKpiGatewayCallStatsIntervalGlobalForwardedCallsTel2Ip 
                                                       Counter64,
       acKpiGatewayCallStatsIntervalGlobalForwardedCallsIp2Tel 
                                                       Counter64,
       acKpiGatewayCallStatsIntervalGlobalFailedCallsOtherTel2Ip 
                                                       Counter64,
       acKpiGatewayCallStatsIntervalGlobalFailedCallsOtherIp2Tel 
                                                       Counter64,
       acKpiGatewayCallStatsIntervalGlobalFailedCallsNoRouteTel2Ip 
                                                       Counter64,
       acKpiGatewayCallStatsIntervalGlobalFailedCallsNoRouteIp2Tel 
                                                       Counter64,
       acKpiGatewayCallStatsIntervalGlobalFailedCallsNoRscTel2Ip 
                                                       Counter64,
       acKpiGatewayCallStatsIntervalGlobalFailedCallsNoRscIp2Tel 
                                                       Counter64,
       acKpiGatewayCallStatsIntervalGlobalFailedCallsNoCapMatchTel2Ip 
                                                       Counter64,
       acKpiGatewayCallStatsIntervalGlobalFailedCallsNoCapMatchIp2Tel 
                                                       Counter64,
       acKpiGatewayCallStatsIntervalGlobalFailedCallsNoAnswerTel2Ip 
                                                       Counter64,
       acKpiGatewayCallStatsIntervalGlobalFailedCallsNoAnswerIp2Tel 
                                                       Counter64,
       acKpiGatewayCallStatsIntervalGlobalFailedCallsBusyTel2Ip 
                                                       Counter64,
       acKpiGatewayCallStatsIntervalGlobalFailedCallsBusyIp2Tel 
                                                       Counter64,
       acKpiGatewayCallStatsIntervalGlobalAverageCallDurationAvg 
                                                       Gauge32,
       acKpiGatewayCallStatsIntervalGlobalEstablishedCallsRateTel2IpMax 
                                                       Gauge32,
       acKpiGatewayCallStatsIntervalGlobalEstablishedCallsRateTel2IpAvg 
                                                       Gauge32,
       acKpiGatewayCallStatsIntervalGlobalEstablishedCallsRateIp2TelMax 
                                                       Gauge32,
       acKpiGatewayCallStatsIntervalGlobalEstablishedCallsRateIp2TelAvg 
                                                       Gauge32,
       acKpiGatewayCallStatsIntervalGlobalEstablishedFaxTel2Ip 
                                                       Counter64,
       acKpiGatewayCallStatsIntervalGlobalEstablishedFaxIp2Tel 
                                                       Counter64,
       acKpiGatewayCallStatsIntervalGlobalEstablishedCallsTel2Ip 
                                                       Counter64,
       acKpiGatewayCallStatsIntervalGlobalEstablishedCallsIp2Tel 
                                                       Counter64,
       acKpiGatewayCallStatsIntervalGlobalAttemptedFaxTel2Ip 
                                                       Counter64,
       acKpiGatewayCallStatsIntervalGlobalAttemptedFaxIp2Tel 
                                                       Counter64,
       acKpiGatewayCallStatsIntervalGlobalAttemptedCallsRateTel2IpMax 
                                                       Gauge32,
       acKpiGatewayCallStatsIntervalGlobalAttemptedCallsRateTel2IpAvg 
                                                       Gauge32,
       acKpiGatewayCallStatsIntervalGlobalAttemptedCallsTel2Ip 
                                                       Counter64,
       acKpiGatewayCallStatsIntervalGlobalAttemptedCallsRateIp2TelMax 
                                                       Gauge32,
       acKpiGatewayCallStatsIntervalGlobalAttemptedCallsRateIp2TelAvg 
                                                       Gauge32,
       acKpiGatewayCallStatsIntervalGlobalAttemptedCallsIp2Tel 
                                                       Counter64,
       acKpiGatewayCallStatsIntervalGlobalActiveCallsTel2IpMax 
                                                       Gauge32,
       acKpiGatewayCallStatsIntervalGlobalActiveCallsTel2IpAvg 
                                                       Gauge32,
       acKpiGatewayCallStatsIntervalGlobalActiveCallsIp2TelMax 
                                                       Gauge32,
       acKpiGatewayCallStatsIntervalGlobalActiveCallsIp2TelAvg 
                                                       Gauge32,
       acKpiGatewayCallStatsIntervalGlobalActiveCallsMax 
                                                       Gauge32,
       acKpiGatewayCallStatsIntervalGlobalActiveCallsAvg 
                                                       Gauge32
     }



     acKpiGatewayCallStatsIntervalGlobalInterval OBJECT-TYPE
       SYNTAX Unsigned32 (1..200)
       MAX-ACCESS not-accessible
       STATUS current
       DESCRIPTION
           "
AC INI-Param: N/A"
       ::= {acKpiGatewayCallStatsIntervalGlobalEntry 1}



     acKpiGatewayCallStatsIntervalGlobalAnswerSeizureRatioAvg OBJECT-TYPE
       SYNTAX Gauge32
       MAX-ACCESS read-only
       STATUS current
       DESCRIPTION
           "Average answer/seizure ratio (ASR, %).
AC INI-Param: N/A"
       ::= {acKpiGatewayCallStatsIntervalGlobalEntry 2}



     acKpiGatewayCallStatsIntervalGlobalForwardedCallsTel2Ip OBJECT-TYPE
       SYNTAX Counter64
       MAX-ACCESS read-only
       STATUS current
       DESCRIPTION
           "Number of forwarded Tel->IP calls.
AC INI-Param: N/A"
       ::= {acKpiGatewayCallStatsIntervalGlobalEntry 3}



     acKpiGatewayCallStatsIntervalGlobalForwardedCallsIp2Tel OBJECT-TYPE
       SYNTAX Counter64
       MAX-ACCESS read-only
       STATUS current
       DESCRIPTION
           "Number of forwarded IP->Tel calls.
AC INI-Param: N/A"
       ::= {acKpiGatewayCallStatsIntervalGlobalEntry 4}



     acKpiGatewayCallStatsIntervalGlobalFailedCallsOtherTel2Ip OBJECT-TYPE
       SYNTAX Counter64
       MAX-ACCESS read-only
       STATUS current
       DESCRIPTION
           "Number of failed Tel->IP calls due to other reasons.
AC INI-Param: N/A"
       ::= {acKpiGatewayCallStatsIntervalGlobalEntry 5}



     acKpiGatewayCallStatsIntervalGlobalFailedCallsOtherIp2Tel OBJECT-TYPE
       SYNTAX Counter64
       MAX-ACCESS read-only
       STATUS current
       DESCRIPTION
           "Number of failed IP->Tel calls due to other reasons.
AC INI-Param: N/A"
       ::= {acKpiGatewayCallStatsIntervalGlobalEntry 6}



     acKpiGatewayCallStatsIntervalGlobalFailedCallsNoRouteTel2Ip OBJECT-TYPE
       SYNTAX Counter64
       MAX-ACCESS read-only
       STATUS current
       DESCRIPTION
           "Number of failed Tel->IP calls due to routing failure.
AC INI-Param: N/A"
       ::= {acKpiGatewayCallStatsIntervalGlobalEntry 7}



     acKpiGatewayCallStatsIntervalGlobalFailedCallsNoRouteIp2Tel OBJECT-TYPE
       SYNTAX Counter64
       MAX-ACCESS read-only
       STATUS current
       DESCRIPTION
           "Number of failed IP->Tel calls due to routing failure.
AC INI-Param: N/A"
       ::= {acKpiGatewayCallStatsIntervalGlobalEntry 8}



     acKpiGatewayCallStatsIntervalGlobalFailedCallsNoRscTel2Ip OBJECT-TYPE
       SYNTAX Counter64
       MAX-ACCESS read-only
       STATUS current
       DESCRIPTION
           "Number of failed Tel->IP calls due to lack of internal resources.
AC INI-Param: N/A"
       ::= {acKpiGatewayCallStatsIntervalGlobalEntry 9}



     acKpiGatewayCallStatsIntervalGlobalFailedCallsNoRscIp2Tel OBJECT-TYPE
       SYNTAX Counter64
       MAX-ACCESS read-only
       STATUS current
       DESCRIPTION
           "Number of failed IP->Tel calls due to lack of internal resources.
AC INI-Param: N/A"
       ::= {acKpiGatewayCallStatsIntervalGlobalEntry 10}



     acKpiGatewayCallStatsIntervalGlobalFailedCallsNoCapMatchTel2Ip OBJECT-TYPE
       SYNTAX Counter64
       MAX-ACCESS read-only
       STATUS current
       DESCRIPTION
           "Number of failed Tel->IP calls due to media mismatch.
AC INI-Param: N/A"
       ::= {acKpiGatewayCallStatsIntervalGlobalEntry 11}



     acKpiGatewayCallStatsIntervalGlobalFailedCallsNoCapMatchIp2Tel OBJECT-TYPE
       SYNTAX Counter64
       MAX-ACCESS read-only
       STATUS current
       DESCRIPTION
           "Number of failed IP->Tel calls due to media mismatch.
AC INI-Param: N/A"
       ::= {acKpiGatewayCallStatsIntervalGlobalEntry 12}



     acKpiGatewayCallStatsIntervalGlobalFailedCallsNoAnswerTel2Ip OBJECT-TYPE
       SYNTAX Counter64
       MAX-ACCESS read-only
       STATUS current
       DESCRIPTION
           "Number of failed Tel->IP calls due to no answer from the callee.
AC INI-Param: N/A"
       ::= {acKpiGatewayCallStatsIntervalGlobalEntry 13}



     acKpiGatewayCallStatsIntervalGlobalFailedCallsNoAnswerIp2Tel OBJECT-TYPE
       SYNTAX Counter64
       MAX-ACCESS read-only
       STATUS current
       DESCRIPTION
           "Number of failed IP->Tel calls due to no answer from the callee.
AC INI-Param: N/A"
       ::= {acKpiGatewayCallStatsIntervalGlobalEntry 14}



     acKpiGatewayCallStatsIntervalGlobalFailedCallsBusyTel2Ip OBJECT-TYPE
       SYNTAX Counter64
       MAX-ACCESS read-only
       STATUS current
       DESCRIPTION
           "Number of failed Tel->IP Calls due to callee being busy.
AC INI-Param: N/A"
       ::= {acKpiGatewayCallStatsIntervalGlobalEntry 15}



     acKpiGatewayCallStatsIntervalGlobalFailedCallsBusyIp2Tel OBJECT-TYPE
       SYNTAX Counter64
       MAX-ACCESS read-only
       STATUS current
       DESCRIPTION
           "Number of failed IP->Tel calls due to callee being busy.
AC INI-Param: N/A"
       ::= {acKpiGatewayCallStatsIntervalGlobalEntry 16}



     acKpiGatewayCallStatsIntervalGlobalAverageCallDurationAvg OBJECT-TYPE
       SYNTAX Gauge32
       MAX-ACCESS read-only
       STATUS current
       DESCRIPTION
           "Average call duration (ACD, seconds).
AC INI-Param: N/A"
       ::= {acKpiGatewayCallStatsIntervalGlobalEntry 17}



     acKpiGatewayCallStatsIntervalGlobalEstablishedCallsRateTel2IpMax OBJECT-TYPE
       SYNTAX Gauge32
       MAX-ACCESS read-only
       STATUS current
       DESCRIPTION
           "Maximum rate of established Tel->IP calls (call establish per
second).
AC INI-Param: N/A"
       ::= {acKpiGatewayCallStatsIntervalGlobalEntry 18}



     acKpiGatewayCallStatsIntervalGlobalEstablishedCallsRateTel2IpAvg OBJECT-TYPE
       SYNTAX Gauge32
       MAX-ACCESS read-only
       STATUS current
       DESCRIPTION
           "Average rate of established Tel->IP calls (call establish per
second).
AC INI-Param: N/A"
       ::= {acKpiGatewayCallStatsIntervalGlobalEntry 19}



     acKpiGatewayCallStatsIntervalGlobalEstablishedCallsRateIp2TelMax OBJECT-TYPE
       SYNTAX Gauge32
       MAX-ACCESS read-only
       STATUS current
       DESCRIPTION
           "Maximum rate of established IP->Tel calls (call establish per
second).
AC INI-Param: N/A"
       ::= {acKpiGatewayCallStatsIntervalGlobalEntry 20}



     acKpiGatewayCallStatsIntervalGlobalEstablishedCallsRateIp2TelAvg OBJECT-TYPE
       SYNTAX Gauge32
       MAX-ACCESS read-only
       STATUS current
       DESCRIPTION
           "Average rate of established IP->Tel calls (call establish per
second).
AC INI-Param: N/A"
       ::= {acKpiGatewayCallStatsIntervalGlobalEntry 21}



     acKpiGatewayCallStatsIntervalGlobalEstablishedFaxTel2Ip OBJECT-TYPE
       SYNTAX Counter64
       MAX-ACCESS read-only
       STATUS current
       DESCRIPTION
           "Number of established Tel->IP fax calls.
AC INI-Param: N/A"
       ::= {acKpiGatewayCallStatsIntervalGlobalEntry 22}



     acKpiGatewayCallStatsIntervalGlobalEstablishedFaxIp2Tel OBJECT-TYPE
       SYNTAX Counter64
       MAX-ACCESS read-only
       STATUS current
       DESCRIPTION
           "Number of established IP->Tel fax calls.
AC INI-Param: N/A"
       ::= {acKpiGatewayCallStatsIntervalGlobalEntry 23}



     acKpiGatewayCallStatsIntervalGlobalEstablishedCallsTel2Ip OBJECT-TYPE
       SYNTAX Counter64
       MAX-ACCESS read-only
       STATUS current
       DESCRIPTION
           "Number of established Tel->IP calls.
AC INI-Param: N/A"
       ::= {acKpiGatewayCallStatsIntervalGlobalEntry 24}



     acKpiGatewayCallStatsIntervalGlobalEstablishedCallsIp2Tel OBJECT-TYPE
       SYNTAX Counter64
       MAX-ACCESS read-only
       STATUS current
       DESCRIPTION
           "Number of established IP->Tel calls.
AC INI-Param: N/A"
       ::= {acKpiGatewayCallStatsIntervalGlobalEntry 25}



     acKpiGatewayCallStatsIntervalGlobalAttemptedFaxTel2Ip OBJECT-TYPE
       SYNTAX Counter64
       MAX-ACCESS read-only
       STATUS current
       DESCRIPTION
           "Number of attempted Tel->IP fax calls.
AC INI-Param: N/A"
       ::= {acKpiGatewayCallStatsIntervalGlobalEntry 26}



     acKpiGatewayCallStatsIntervalGlobalAttemptedFaxIp2Tel OBJECT-TYPE
       SYNTAX Counter64
       MAX-ACCESS read-only
       STATUS current
       DESCRIPTION
           "Number of attempted IP->Tel fax calls.
AC INI-Param: N/A"
       ::= {acKpiGatewayCallStatsIntervalGlobalEntry 27}



     acKpiGatewayCallStatsIntervalGlobalAttemptedCallsRateTel2IpMax OBJECT-TYPE
       SYNTAX Gauge32
       MAX-ACCESS read-only
       STATUS current
       DESCRIPTION
           "Maximum rate of attempted Tel->IP calls (call attempts per second).
AC INI-Param: N/A"
       ::= {acKpiGatewayCallStatsIntervalGlobalEntry 28}



     acKpiGatewayCallStatsIntervalGlobalAttemptedCallsRateTel2IpAvg OBJECT-TYPE
       SYNTAX Gauge32
       MAX-ACCESS read-only
       STATUS current
       DESCRIPTION
           "Average rate of attempted Tel->IP calls (call attempts per second).
AC INI-Param: N/A"
       ::= {acKpiGatewayCallStatsIntervalGlobalEntry 29}



     acKpiGatewayCallStatsIntervalGlobalAttemptedCallsTel2Ip OBJECT-TYPE
       SYNTAX Counter64
       MAX-ACCESS read-only
       STATUS current
       DESCRIPTION
           "Number of attempted Tel->IP calls.
AC INI-Param: N/A"
       ::= {acKpiGatewayCallStatsIntervalGlobalEntry 30}



     acKpiGatewayCallStatsIntervalGlobalAttemptedCallsRateIp2TelMax OBJECT-TYPE
       SYNTAX Gauge32
       MAX-ACCESS read-only
       STATUS current
       DESCRIPTION
           "Maximum rate of attempted IP->Tel calls (call attempts per second).
AC INI-Param: N/A"
       ::= {acKpiGatewayCallStatsIntervalGlobalEntry 31}



     acKpiGatewayCallStatsIntervalGlobalAttemptedCallsRateIp2TelAvg OBJECT-TYPE
       SYNTAX Gauge32
       MAX-ACCESS read-only
       STATUS current
       DESCRIPTION
           "Average rate of attempted IP->Tel calls (call attempts per second).
AC INI-Param: N/A"
       ::= {acKpiGatewayCallStatsIntervalGlobalEntry 32}



     acKpiGatewayCallStatsIntervalGlobalAttemptedCallsIp2Tel OBJECT-TYPE
       SYNTAX Counter64
       MAX-ACCESS read-only
       STATUS current
       DESCRIPTION
           "Number of attempted IP->Tel calls.
AC INI-Param: N/A"
       ::= {acKpiGatewayCallStatsIntervalGlobalEntry 33}



     acKpiGatewayCallStatsIntervalGlobalActiveCallsTel2IpMax OBJECT-TYPE
       SYNTAX Gauge32
       MAX-ACCESS read-only
       STATUS current
       DESCRIPTION
           "Maximum number of active Tel->IP calls.
AC INI-Param: N/A"
       ::= {acKpiGatewayCallStatsIntervalGlobalEntry 34}



     acKpiGatewayCallStatsIntervalGlobalActiveCallsTel2IpAvg OBJECT-TYPE
       SYNTAX Gauge32
       MAX-ACCESS read-only
       STATUS current
       DESCRIPTION
           "Average number of active Tel->IP calls.
AC INI-Param: N/A"
       ::= {acKpiGatewayCallStatsIntervalGlobalEntry 35}



     acKpiGatewayCallStatsIntervalGlobalActiveCallsIp2TelMax OBJECT-TYPE
       SYNTAX Gauge32
       MAX-ACCESS read-only
       STATUS current
       DESCRIPTION
           "Maximum number of active IP->Tel calls.
AC INI-Param: N/A"
       ::= {acKpiGatewayCallStatsIntervalGlobalEntry 36}



     acKpiGatewayCallStatsIntervalGlobalActiveCallsIp2TelAvg OBJECT-TYPE
       SYNTAX Gauge32
       MAX-ACCESS read-only
       STATUS current
       DESCRIPTION
           "Average number of active IP->Tel calls.
AC INI-Param: N/A"
       ::= {acKpiGatewayCallStatsIntervalGlobalEntry 37}



     acKpiGatewayCallStatsIntervalGlobalActiveCallsMax OBJECT-TYPE
       SYNTAX Gauge32
       MAX-ACCESS read-only
       STATUS current
       DESCRIPTION
           "Maximum number of active calls.
AC INI-Param: N/A"
       ::= {acKpiGatewayCallStatsIntervalGlobalEntry 38}



     acKpiGatewayCallStatsIntervalGlobalActiveCallsAvg OBJECT-TYPE
       SYNTAX Gauge32
       MAX-ACCESS read-only
       STATUS current
       DESCRIPTION
           "Average number of active calls.
AC INI-Param: N/A"
       ::= {acKpiGatewayCallStatsIntervalGlobalEntry 39}



     acKpiGatewayCallStatsIntervalTables OBJECT IDENTIFIER ::= {acKpiGatewayCallStatsInterval 2}


     -- ****************************************
     -- acKpiGatewayCallStatsIntervalIpGroup table declaration
     -- ****************************************
     acKpiGatewayCallStatsIntervalIpGroupTable OBJECT-TYPE
       SYNTAX SEQUENCE OF AcKpiGatewayCallStatsIntervalIpGroupEntry
       MAX-ACCESS not-accessible
       STATUS current
       DESCRIPTION
           ""
       ::= {acKpiGatewayCallStatsIntervalTables 1}



     -- ****************************************
     -- acKpiGatewayCallStatsIntervalIpGroup table entry
     -- ****************************************
     acKpiGatewayCallStatsIntervalIpGroupEntry OBJECT-TYPE
       SYNTAX AcKpiGatewayCallStatsIntervalIpGroupEntry
       MAX-ACCESS not-accessible
       STATUS current
       DESCRIPTION
           ""
       INDEX {acKpiGatewayCallStatsIntervalIpGroupIndex,acKpiGatewayCallStatsIntervalIpGroupInterval}
       ::= {acKpiGatewayCallStatsIntervalIpGroupTable 1}



     -- ****************************************
     -- acKpiGatewayCallStatsIntervalIpGroup TABLE
     -- ****************************************
     AcKpiGatewayCallStatsIntervalIpGroupEntry ::= SEQUENCE {
       acKpiGatewayCallStatsIntervalIpGroupIndex       Unsigned32,
       acKpiGatewayCallStatsIntervalIpGroupInterval    Unsigned32,
       acKpiGatewayCallStatsIntervalIpGroupAnswerSeizureRatioAvg 
                                                       Gauge32,
       acKpiGatewayCallStatsIntervalIpGroupForwardedCallsTel2Ip 
                                                       Counter64,
       acKpiGatewayCallStatsIntervalIpGroupForwardedCallsIp2Tel 
                                                       Counter64,
       acKpiGatewayCallStatsIntervalIpGroupFailedCallsOtherTel2Ip 
                                                       Counter64,
       acKpiGatewayCallStatsIntervalIpGroupFailedCallsOtherIp2Tel 
                                                       Counter64,
       acKpiGatewayCallStatsIntervalIpGroupFailedCallsNoRouteTel2Ip 
                                                       Counter64,
       acKpiGatewayCallStatsIntervalIpGroupFailedCallsNoRouteIp2Tel 
                                                       Counter64,
       acKpiGatewayCallStatsIntervalIpGroupFailedCallsNoRscTel2Ip 
                                                       Counter64,
       acKpiGatewayCallStatsIntervalIpGroupFailedCallsNoRscIp2Tel 
                                                       Counter64,
       acKpiGatewayCallStatsIntervalIpGroupFailedCallsNoCapMatchTel2Ip 
                                                       Counter64,
       acKpiGatewayCallStatsIntervalIpGroupFailedCallsNoCapMatchIp2Tel 
                                                       Counter64,
       acKpiGatewayCallStatsIntervalIpGroupFailedCallsNoAnswerTel2Ip 
                                                       Counter64,
       acKpiGatewayCallStatsIntervalIpGroupFailedCallsNoAnswerIp2Tel 
                                                       Counter64,
       acKpiGatewayCallStatsIntervalIpGroupFailedCallsBusyTel2Ip 
                                                       Counter64,
       acKpiGatewayCallStatsIntervalIpGroupFailedCallsBusyIp2Tel 
                                                       Counter64,
       acKpiGatewayCallStatsIntervalIpGroupAverageCallDurationAvg 
                                                       Gauge32,
       acKpiGatewayCallStatsIntervalIpGroupEstablishedCallsRateTel2IpMax 
                                                       Gauge32,
       acKpiGatewayCallStatsIntervalIpGroupEstablishedCallsRateTel2IpAvg 
                                                       Gauge32,
       acKpiGatewayCallStatsIntervalIpGroupEstablishedCallsRateIp2TelMax 
                                                       Gauge32,
       acKpiGatewayCallStatsIntervalIpGroupEstablishedCallsRateIp2TelAvg 
                                                       Gauge32,
       acKpiGatewayCallStatsIntervalIpGroupEstablishedFaxTel2Ip 
                                                       Counter64,
       acKpiGatewayCallStatsIntervalIpGroupEstablishedFaxIp2Tel 
                                                       Counter64,
       acKpiGatewayCallStatsIntervalIpGroupEstablishedCallsTel2Ip 
                                                       Counter64,
       acKpiGatewayCallStatsIntervalIpGroupEstablishedCallsIp2Tel 
                                                       Counter64,
       acKpiGatewayCallStatsIntervalIpGroupAttemptedFaxTel2Ip 
                                                       Counter64,
       acKpiGatewayCallStatsIntervalIpGroupAttemptedFaxIp2Tel 
                                                       Counter64,
       acKpiGatewayCallStatsIntervalIpGroupAttemptedCallsRateTel2IpMax 
                                                       Gauge32,
       acKpiGatewayCallStatsIntervalIpGroupAttemptedCallsRateTel2IpAvg 
                                                       Gauge32,
       acKpiGatewayCallStatsIntervalIpGroupAttemptedCallsTel2Ip 
                                                       Counter64,
       acKpiGatewayCallStatsIntervalIpGroupAttemptedCallsRateIp2TelMax 
                                                       Gauge32,
       acKpiGatewayCallStatsIntervalIpGroupAttemptedCallsRateIp2TelAvg 
                                                       Gauge32,
       acKpiGatewayCallStatsIntervalIpGroupAttemptedCallsIp2Tel 
                                                       Counter64,
       acKpiGatewayCallStatsIntervalIpGroupActiveCallsTel2IpMax 
                                                       Gauge32,
       acKpiGatewayCallStatsIntervalIpGroupActiveCallsTel2IpAvg 
                                                       Gauge32,
       acKpiGatewayCallStatsIntervalIpGroupActiveCallsIp2TelMax 
                                                       Gauge32,
       acKpiGatewayCallStatsIntervalIpGroupActiveCallsIp2TelAvg 
                                                       Gauge32,
       acKpiGatewayCallStatsIntervalIpGroupActiveCallsMax 
                                                       Gauge32,
       acKpiGatewayCallStatsIntervalIpGroupActiveCallsAvg 
                                                       Gauge32
     }



     acKpiGatewayCallStatsIntervalIpGroupIndex OBJECT-TYPE
       SYNTAX Unsigned32 (0..32767)
       MAX-ACCESS not-accessible
       STATUS current
       DESCRIPTION
           "
AC INI-Param: N/A"
       ::= {acKpiGatewayCallStatsIntervalIpGroupEntry 1}



     acKpiGatewayCallStatsIntervalIpGroupInterval OBJECT-TYPE
       SYNTAX Unsigned32 (1..200)
       MAX-ACCESS not-accessible
       STATUS current
       DESCRIPTION
           "
AC INI-Param: N/A"
       ::= {acKpiGatewayCallStatsIntervalIpGroupEntry 2}



     acKpiGatewayCallStatsIntervalIpGroupAnswerSeizureRatioAvg OBJECT-TYPE
       SYNTAX Gauge32
       MAX-ACCESS read-only
       STATUS current
       DESCRIPTION
           "Average answer/seizure ratio (ASR, %).
AC INI-Param: N/A"
       ::= {acKpiGatewayCallStatsIntervalIpGroupEntry 3}



     acKpiGatewayCallStatsIntervalIpGroupForwardedCallsTel2Ip OBJECT-TYPE
       SYNTAX Counter64
       MAX-ACCESS read-only
       STATUS current
       DESCRIPTION
           "Number of forwarded Tel->IP calls.
AC INI-Param: N/A"
       ::= {acKpiGatewayCallStatsIntervalIpGroupEntry 4}



     acKpiGatewayCallStatsIntervalIpGroupForwardedCallsIp2Tel OBJECT-TYPE
       SYNTAX Counter64
       MAX-ACCESS read-only
       STATUS current
       DESCRIPTION
           "Number of forwarded IP->Tel calls.
AC INI-Param: N/A"
       ::= {acKpiGatewayCallStatsIntervalIpGroupEntry 5}



     acKpiGatewayCallStatsIntervalIpGroupFailedCallsOtherTel2Ip OBJECT-TYPE
       SYNTAX Counter64
       MAX-ACCESS read-only
       STATUS current
       DESCRIPTION
           "Number of failed Tel->IP calls due to other reasons.
AC INI-Param: N/A"
       ::= {acKpiGatewayCallStatsIntervalIpGroupEntry 6}



     acKpiGatewayCallStatsIntervalIpGroupFailedCallsOtherIp2Tel OBJECT-TYPE
       SYNTAX Counter64
       MAX-ACCESS read-only
       STATUS current
       DESCRIPTION
           "Number of failed IP->Tel calls due to other reasons.
AC INI-Param: N/A"
       ::= {acKpiGatewayCallStatsIntervalIpGroupEntry 7}



     acKpiGatewayCallStatsIntervalIpGroupFailedCallsNoRouteTel2Ip OBJECT-TYPE
       SYNTAX Counter64
       MAX-ACCESS read-only
       STATUS current
       DESCRIPTION
           "Number of failed Tel->IP calls due to routing failure.
AC INI-Param: N/A"
       ::= {acKpiGatewayCallStatsIntervalIpGroupEntry 8}



     acKpiGatewayCallStatsIntervalIpGroupFailedCallsNoRouteIp2Tel OBJECT-TYPE
       SYNTAX Counter64
       MAX-ACCESS read-only
       STATUS current
       DESCRIPTION
           "Number of failed IP->Tel calls due to routing failure.
AC INI-Param: N/A"
       ::= {acKpiGatewayCallStatsIntervalIpGroupEntry 9}



     acKpiGatewayCallStatsIntervalIpGroupFailedCallsNoRscTel2Ip OBJECT-TYPE
       SYNTAX Counter64
       MAX-ACCESS read-only
       STATUS current
       DESCRIPTION
           "Number of failed Tel->IP calls due to lack of internal resources.
AC INI-Param: N/A"
       ::= {acKpiGatewayCallStatsIntervalIpGroupEntry 10}



     acKpiGatewayCallStatsIntervalIpGroupFailedCallsNoRscIp2Tel OBJECT-TYPE
       SYNTAX Counter64
       MAX-ACCESS read-only
       STATUS current
       DESCRIPTION
           "Number of failed IP->Tel calls due to lack of internal resources.
AC INI-Param: N/A"
       ::= {acKpiGatewayCallStatsIntervalIpGroupEntry 11}



     acKpiGatewayCallStatsIntervalIpGroupFailedCallsNoCapMatchTel2Ip OBJECT-TYPE
       SYNTAX Counter64
       MAX-ACCESS read-only
       STATUS current
       DESCRIPTION
           "Number of failed Tel->IP calls due to media mismatch.
AC INI-Param: N/A"
       ::= {acKpiGatewayCallStatsIntervalIpGroupEntry 12}



     acKpiGatewayCallStatsIntervalIpGroupFailedCallsNoCapMatchIp2Tel OBJECT-TYPE
       SYNTAX Counter64
       MAX-ACCESS read-only
       STATUS current
       DESCRIPTION
           "Number of failed IP->Tel calls due to media mismatch.
AC INI-Param: N/A"
       ::= {acKpiGatewayCallStatsIntervalIpGroupEntry 13}



     acKpiGatewayCallStatsIntervalIpGroupFailedCallsNoAnswerTel2Ip OBJECT-TYPE
       SYNTAX Counter64
       MAX-ACCESS read-only
       STATUS current
       DESCRIPTION
           "Number of failed Tel->IP calls due to no answer from the callee.
AC INI-Param: N/A"
       ::= {acKpiGatewayCallStatsIntervalIpGroupEntry 14}



     acKpiGatewayCallStatsIntervalIpGroupFailedCallsNoAnswerIp2Tel OBJECT-TYPE
       SYNTAX Counter64
       MAX-ACCESS read-only
       STATUS current
       DESCRIPTION
           "Number of failed IP->Tel calls due to no answer from the callee.
AC INI-Param: N/A"
       ::= {acKpiGatewayCallStatsIntervalIpGroupEntry 15}



     acKpiGatewayCallStatsIntervalIpGroupFailedCallsBusyTel2Ip OBJECT-TYPE
       SYNTAX Counter64
       MAX-ACCESS read-only
       STATUS current
       DESCRIPTION
           "Number of failed Tel->IP Calls due to callee being busy.
AC INI-Param: N/A"
       ::= {acKpiGatewayCallStatsIntervalIpGroupEntry 16}



     acKpiGatewayCallStatsIntervalIpGroupFailedCallsBusyIp2Tel OBJECT-TYPE
       SYNTAX Counter64
       MAX-ACCESS read-only
       STATUS current
       DESCRIPTION
           "Number of failed IP->Tel calls due to callee being busy.
AC INI-Param: N/A"
       ::= {acKpiGatewayCallStatsIntervalIpGroupEntry 17}



     acKpiGatewayCallStatsIntervalIpGroupAverageCallDurationAvg OBJECT-TYPE
       SYNTAX Gauge32
       MAX-ACCESS read-only
       STATUS current
       DESCRIPTION
           "Average call duration (ACD, seconds).
AC INI-Param: N/A"
       ::= {acKpiGatewayCallStatsIntervalIpGroupEntry 18}



     acKpiGatewayCallStatsIntervalIpGroupEstablishedCallsRateTel2IpMax OBJECT-TYPE
       SYNTAX Gauge32
       MAX-ACCESS read-only
       STATUS current
       DESCRIPTION
           "Maximum rate of established Tel->IP calls (call establish per
second).
AC INI-Param: N/A"
       ::= {acKpiGatewayCallStatsIntervalIpGroupEntry 19}



     acKpiGatewayCallStatsIntervalIpGroupEstablishedCallsRateTel2IpAvg OBJECT-TYPE
       SYNTAX Gauge32
       MAX-ACCESS read-only
       STATUS current
       DESCRIPTION
           "Average rate of established Tel->IP calls (call establish per
second).
AC INI-Param: N/A"
       ::= {acKpiGatewayCallStatsIntervalIpGroupEntry 20}



     acKpiGatewayCallStatsIntervalIpGroupEstablishedCallsRateIp2TelMax OBJECT-TYPE
       SYNTAX Gauge32
       MAX-ACCESS read-only
       STATUS current
       DESCRIPTION
           "Maximum rate of established IP->Tel calls (call establish per
second).
AC INI-Param: N/A"
       ::= {acKpiGatewayCallStatsIntervalIpGroupEntry 21}



     acKpiGatewayCallStatsIntervalIpGroupEstablishedCallsRateIp2TelAvg OBJECT-TYPE
       SYNTAX Gauge32
       MAX-ACCESS read-only
       STATUS current
       DESCRIPTION
           "Average rate of established IP->Tel calls (call establish per
second).
AC INI-Param: N/A"
       ::= {acKpiGatewayCallStatsIntervalIpGroupEntry 22}



     acKpiGatewayCallStatsIntervalIpGroupEstablishedFaxTel2Ip OBJECT-TYPE
       SYNTAX Counter64
       MAX-ACCESS read-only
       STATUS current
       DESCRIPTION
           "Number of established Tel->IP fax calls.
AC INI-Param: N/A"
       ::= {acKpiGatewayCallStatsIntervalIpGroupEntry 23}



     acKpiGatewayCallStatsIntervalIpGroupEstablishedFaxIp2Tel OBJECT-TYPE
       SYNTAX Counter64
       MAX-ACCESS read-only
       STATUS current
       DESCRIPTION
           "Number of established IP->Tel fax calls.
AC INI-Param: N/A"
       ::= {acKpiGatewayCallStatsIntervalIpGroupEntry 24}



     acKpiGatewayCallStatsIntervalIpGroupEstablishedCallsTel2Ip OBJECT-TYPE
       SYNTAX Counter64
       MAX-ACCESS read-only
       STATUS current
       DESCRIPTION
           "Number of established Tel->IP calls.
AC INI-Param: N/A"
       ::= {acKpiGatewayCallStatsIntervalIpGroupEntry 25}



     acKpiGatewayCallStatsIntervalIpGroupEstablishedCallsIp2Tel OBJECT-TYPE
       SYNTAX Counter64
       MAX-ACCESS read-only
       STATUS current
       DESCRIPTION
           "Number of established IP->Tel calls.
AC INI-Param: N/A"
       ::= {acKpiGatewayCallStatsIntervalIpGroupEntry 26}



     acKpiGatewayCallStatsIntervalIpGroupAttemptedFaxTel2Ip OBJECT-TYPE
       SYNTAX Counter64
       MAX-ACCESS read-only
       STATUS current
       DESCRIPTION
           "Number of attempted Tel->IP fax calls.
AC INI-Param: N/A"
       ::= {acKpiGatewayCallStatsIntervalIpGroupEntry 27}



     acKpiGatewayCallStatsIntervalIpGroupAttemptedFaxIp2Tel OBJECT-TYPE
       SYNTAX Counter64
       MAX-ACCESS read-only
       STATUS current
       DESCRIPTION
           "Number of attempted IP->Tel fax calls.
AC INI-Param: N/A"
       ::= {acKpiGatewayCallStatsIntervalIpGroupEntry 28}



     acKpiGatewayCallStatsIntervalIpGroupAttemptedCallsRateTel2IpMax OBJECT-TYPE
       SYNTAX Gauge32
       MAX-ACCESS read-only
       STATUS current
       DESCRIPTION
           "Maximum rate of attempted Tel->IP calls (call attempts per second).
AC INI-Param: N/A"
       ::= {acKpiGatewayCallStatsIntervalIpGroupEntry 29}



     acKpiGatewayCallStatsIntervalIpGroupAttemptedCallsRateTel2IpAvg OBJECT-TYPE
       SYNTAX Gauge32
       MAX-ACCESS read-only
       STATUS current
       DESCRIPTION
           "Average rate of attempted Tel->IP calls (call attempts per second).
AC INI-Param: N/A"
       ::= {acKpiGatewayCallStatsIntervalIpGroupEntry 30}



     acKpiGatewayCallStatsIntervalIpGroupAttemptedCallsTel2Ip OBJECT-TYPE
       SYNTAX Counter64
       MAX-ACCESS read-only
       STATUS current
       DESCRIPTION
           "Number of attempted Tel->IP calls.
AC INI-Param: N/A"
       ::= {acKpiGatewayCallStatsIntervalIpGroupEntry 31}



     acKpiGatewayCallStatsIntervalIpGroupAttemptedCallsRateIp2TelMax OBJECT-TYPE
       SYNTAX Gauge32
       MAX-ACCESS read-only
       STATUS current
       DESCRIPTION
           "Maximum rate of attempted IP->Tel calls (call attempts per second).
AC INI-Param: N/A"
       ::= {acKpiGatewayCallStatsIntervalIpGroupEntry 32}



     acKpiGatewayCallStatsIntervalIpGroupAttemptedCallsRateIp2TelAvg OBJECT-TYPE
       SYNTAX Gauge32
       MAX-ACCESS read-only
       STATUS current
       DESCRIPTION
           "Average rate of attempted IP->Tel calls (call attempts per second).
AC INI-Param: N/A"
       ::= {acKpiGatewayCallStatsIntervalIpGroupEntry 33}



     acKpiGatewayCallStatsIntervalIpGroupAttemptedCallsIp2Tel OBJECT-TYPE
       SYNTAX Counter64
       MAX-ACCESS read-only
       STATUS current
       DESCRIPTION
           "Number of attempted IP->Tel calls.
AC INI-Param: N/A"
       ::= {acKpiGatewayCallStatsIntervalIpGroupEntry 34}



     acKpiGatewayCallStatsIntervalIpGroupActiveCallsTel2IpMax OBJECT-TYPE
       SYNTAX Gauge32
       MAX-ACCESS read-only
       STATUS current
       DESCRIPTION
           "Maximum number of active Tel->IP calls.
AC INI-Param: N/A"
       ::= {acKpiGatewayCallStatsIntervalIpGroupEntry 35}



     acKpiGatewayCallStatsIntervalIpGroupActiveCallsTel2IpAvg OBJECT-TYPE
       SYNTAX Gauge32
       MAX-ACCESS read-only
       STATUS current
       DESCRIPTION
           "Average number of active Tel->IP calls.
AC INI-Param: N/A"
       ::= {acKpiGatewayCallStatsIntervalIpGroupEntry 36}



     acKpiGatewayCallStatsIntervalIpGroupActiveCallsIp2TelMax OBJECT-TYPE
       SYNTAX Gauge32
       MAX-ACCESS read-only
       STATUS current
       DESCRIPTION
           "Maximum number of active IP->Tel calls.
AC INI-Param: N/A"
       ::= {acKpiGatewayCallStatsIntervalIpGroupEntry 37}



     acKpiGatewayCallStatsIntervalIpGroupActiveCallsIp2TelAvg OBJECT-TYPE
       SYNTAX Gauge32
       MAX-ACCESS read-only
       STATUS current
       DESCRIPTION
           "Average number of active IP->Tel calls.
AC INI-Param: N/A"
       ::= {acKpiGatewayCallStatsIntervalIpGroupEntry 38}



     acKpiGatewayCallStatsIntervalIpGroupActiveCallsMax OBJECT-TYPE
       SYNTAX Gauge32
       MAX-ACCESS read-only
       STATUS current
       DESCRIPTION
           "Maximum number of active calls.
AC INI-Param: N/A"
       ::= {acKpiGatewayCallStatsIntervalIpGroupEntry 39}



     acKpiGatewayCallStatsIntervalIpGroupActiveCallsAvg OBJECT-TYPE
       SYNTAX Gauge32
       MAX-ACCESS read-only
       STATUS current
       DESCRIPTION
           "Average number of active calls.
AC INI-Param: N/A"
       ::= {acKpiGatewayCallStatsIntervalIpGroupEntry 40}



     -- ****************************************
     -- acKpiGatewayCallStatsIntervalTrunkGroup table declaration
     -- ****************************************
     acKpiGatewayCallStatsIntervalTrunkGroupTable OBJECT-TYPE
       SYNTAX SEQUENCE OF AcKpiGatewayCallStatsIntervalTrunkGroupEntry
       MAX-ACCESS not-accessible
       STATUS current
       DESCRIPTION
           ""
       ::= {acKpiGatewayCallStatsIntervalTables 2}



     -- ****************************************
     -- acKpiGatewayCallStatsIntervalTrunkGroup table entry
     -- ****************************************
     acKpiGatewayCallStatsIntervalTrunkGroupEntry OBJECT-TYPE
       SYNTAX AcKpiGatewayCallStatsIntervalTrunkGroupEntry
       MAX-ACCESS not-accessible
       STATUS current
       DESCRIPTION
           ""
       INDEX {acKpiGatewayCallStatsIntervalTrunkGroupIndex,acKpiGatewayCallStatsIntervalTrunkGroupInterval}
       ::= {acKpiGatewayCallStatsIntervalTrunkGroupTable 1}



     -- ****************************************
     -- acKpiGatewayCallStatsIntervalTrunkGroup TABLE
     -- ****************************************
     AcKpiGatewayCallStatsIntervalTrunkGroupEntry ::= SEQUENCE {
       acKpiGatewayCallStatsIntervalTrunkGroupIndex    Unsigned32,
       acKpiGatewayCallStatsIntervalTrunkGroupInterval Unsigned32,
       acKpiGatewayCallStatsIntervalTrunkGroupAnswerSeizureRatioAvg 
                                                       Gauge32,
       acKpiGatewayCallStatsIntervalTrunkGroupForwardedCallsTel2Ip 
                                                       Counter64,
       acKpiGatewayCallStatsIntervalTrunkGroupForwardedCallsIp2Tel 
                                                       Counter64,
       acKpiGatewayCallStatsIntervalTrunkGroupFailedCallsOtherTel2Ip 
                                                       Counter64,
       acKpiGatewayCallStatsIntervalTrunkGroupFailedCallsOtherIp2Tel 
                                                       Counter64,
       acKpiGatewayCallStatsIntervalTrunkGroupFailedCallsNoRouteTel2Ip 
                                                       Counter64,
       acKpiGatewayCallStatsIntervalTrunkGroupFailedCallsNoRouteIp2Tel 
                                                       Counter64,
       acKpiGatewayCallStatsIntervalTrunkGroupFailedCallsNoRscTel2Ip 
                                                       Counter64,
       acKpiGatewayCallStatsIntervalTrunkGroupFailedCallsNoRscIp2Tel 
                                                       Counter64,
       acKpiGatewayCallStatsIntervalTrunkGroupFailedCallsNoCapMatchTel2Ip 
                                                       Counter64,
       acKpiGatewayCallStatsIntervalTrunkGroupFailedCallsNoCapMatchIp2Tel 
                                                       Counter64,
       acKpiGatewayCallStatsIntervalTrunkGroupFailedCallsNoAnswerTel2Ip 
                                                       Counter64,
       acKpiGatewayCallStatsIntervalTrunkGroupFailedCallsNoAnswerIp2Tel 
                                                       Counter64,
       acKpiGatewayCallStatsIntervalTrunkGroupFailedCallsBusyTel2Ip 
                                                       Counter64,
       acKpiGatewayCallStatsIntervalTrunkGroupFailedCallsBusyIp2Tel 
                                                       Counter64,
       acKpiGatewayCallStatsIntervalTrunkGroupAverageCallDurationAvg 
                                                       Gauge32,
       acKpiGatewayCallStatsIntervalTrunkGroupEstablishedCallsRateTel2IpMax 
                                                       Gauge32,
       acKpiGatewayCallStatsIntervalTrunkGroupEstablishedCallsRateTel2IpAvg 
                                                       Gauge32,
       acKpiGatewayCallStatsIntervalTrunkGroupEstablishedCallsRateIp2TelMax 
                                                       Gauge32,
       acKpiGatewayCallStatsIntervalTrunkGroupEstablishedCallsRateIp2TelAvg 
                                                       Gauge32,
       acKpiGatewayCallStatsIntervalTrunkGroupEstablishedFaxTel2Ip 
                                                       Counter64,
       acKpiGatewayCallStatsIntervalTrunkGroupEstablishedFaxIp2Tel 
                                                       Counter64,
       acKpiGatewayCallStatsIntervalTrunkGroupEstablishedCallsTel2Ip 
                                                       Counter64,
       acKpiGatewayCallStatsIntervalTrunkGroupEstablishedCallsIp2Tel 
                                                       Counter64,
       acKpiGatewayCallStatsIntervalTrunkGroupAttemptedFaxTel2Ip 
                                                       Counter64,
       acKpiGatewayCallStatsIntervalTrunkGroupAttemptedFaxIp2Tel 
                                                       Counter64,
       acKpiGatewayCallStatsIntervalTrunkGroupAttemptedCallsRateTel2IpMax 
                                                       Gauge32,
       acKpiGatewayCallStatsIntervalTrunkGroupAttemptedCallsRateTel2IpAvg 
                                                       Gauge32,
       acKpiGatewayCallStatsIntervalTrunkGroupAttemptedCallsTel2Ip 
                                                       Counter64,
       acKpiGatewayCallStatsIntervalTrunkGroupAttemptedCallsRateIp2TelMax 
                                                       Gauge32,
       acKpiGatewayCallStatsIntervalTrunkGroupAttemptedCallsRateIp2TelAvg 
                                                       Gauge32,
       acKpiGatewayCallStatsIntervalTrunkGroupAttemptedCallsIp2Tel 
                                                       Counter64,
       acKpiGatewayCallStatsIntervalTrunkGroupActiveCallsTel2IpMax 
                                                       Gauge32,
       acKpiGatewayCallStatsIntervalTrunkGroupActiveCallsTel2Ip2Avg 
                                                       Gauge32,
       acKpiGatewayCallStatsIntervalTrunkGroupActiveCallsIp2TelMax 
                                                       Gauge32,
       acKpiGatewayCallStatsIntervalTrunkGroupActiveCallsIp2TelAvg 
                                                       Gauge32,
       acKpiGatewayCallStatsIntervalTrunkGroupActiveCallsMax 
                                                       Gauge32,
       acKpiGatewayCallStatsIntervalTrunkGroupActiveCallsAvg 
                                                       Gauge32
     }



     acKpiGatewayCallStatsIntervalTrunkGroupIndex OBJECT-TYPE
       SYNTAX Unsigned32 (0..32767)
       MAX-ACCESS not-accessible
       STATUS current
       DESCRIPTION
           "
AC INI-Param: N/A"
       ::= {acKpiGatewayCallStatsIntervalTrunkGroupEntry 1}



     acKpiGatewayCallStatsIntervalTrunkGroupInterval OBJECT-TYPE
       SYNTAX Unsigned32 (1..200)
       MAX-ACCESS not-accessible
       STATUS current
       DESCRIPTION
           "
AC INI-Param: N/A"
       ::= {acKpiGatewayCallStatsIntervalTrunkGroupEntry 2}



     acKpiGatewayCallStatsIntervalTrunkGroupAnswerSeizureRatioAvg OBJECT-TYPE
       SYNTAX Gauge32
       MAX-ACCESS read-only
       STATUS current
       DESCRIPTION
           "Average answer/seizure ratio (ASR, %).
AC INI-Param: N/A"
       ::= {acKpiGatewayCallStatsIntervalTrunkGroupEntry 3}



     acKpiGatewayCallStatsIntervalTrunkGroupForwardedCallsTel2Ip OBJECT-TYPE
       SYNTAX Counter64
       MAX-ACCESS read-only
       STATUS current
       DESCRIPTION
           "Number of forwarded Tel->IP calls.
AC INI-Param: N/A"
       ::= {acKpiGatewayCallStatsIntervalTrunkGroupEntry 4}



     acKpiGatewayCallStatsIntervalTrunkGroupForwardedCallsIp2Tel OBJECT-TYPE
       SYNTAX Counter64
       MAX-ACCESS read-only
       STATUS current
       DESCRIPTION
           "Number of forwarded IP->Tel calls.
AC INI-Param: N/A"
       ::= {acKpiGatewayCallStatsIntervalTrunkGroupEntry 5}



     acKpiGatewayCallStatsIntervalTrunkGroupFailedCallsOtherTel2Ip OBJECT-TYPE
       SYNTAX Counter64
       MAX-ACCESS read-only
       STATUS current
       DESCRIPTION
           "Number of failed Tel->IP calls due to other reasons.
AC INI-Param: N/A"
       ::= {acKpiGatewayCallStatsIntervalTrunkGroupEntry 6}



     acKpiGatewayCallStatsIntervalTrunkGroupFailedCallsOtherIp2Tel OBJECT-TYPE
       SYNTAX Counter64
       MAX-ACCESS read-only
       STATUS current
       DESCRIPTION
           "Number of failed IP->Tel calls due to other reasons.
AC INI-Param: N/A"
       ::= {acKpiGatewayCallStatsIntervalTrunkGroupEntry 7}



     acKpiGatewayCallStatsIntervalTrunkGroupFailedCallsNoRouteTel2Ip OBJECT-TYPE
       SYNTAX Counter64
       MAX-ACCESS read-only
       STATUS current
       DESCRIPTION
           "Number of failed Tel->IP calls due to routing failure.
AC INI-Param: N/A"
       ::= {acKpiGatewayCallStatsIntervalTrunkGroupEntry 8}



     acKpiGatewayCallStatsIntervalTrunkGroupFailedCallsNoRouteIp2Tel OBJECT-TYPE
       SYNTAX Counter64
       MAX-ACCESS read-only
       STATUS current
       DESCRIPTION
           "Number of failed IP->Tel calls due to routing failure.
AC INI-Param: N/A"
       ::= {acKpiGatewayCallStatsIntervalTrunkGroupEntry 9}



     acKpiGatewayCallStatsIntervalTrunkGroupFailedCallsNoRscTel2Ip OBJECT-TYPE
       SYNTAX Counter64
       MAX-ACCESS read-only
       STATUS current
       DESCRIPTION
           "Number of failed Tel->IP calls due to lack of internal resources.
AC INI-Param: N/A"
       ::= {acKpiGatewayCallStatsIntervalTrunkGroupEntry 10}



     acKpiGatewayCallStatsIntervalTrunkGroupFailedCallsNoRscIp2Tel OBJECT-TYPE
       SYNTAX Counter64
       MAX-ACCESS read-only
       STATUS current
       DESCRIPTION
           "Number of failed IP->Tel calls due to lack of internal resources.
AC INI-Param: N/A"
       ::= {acKpiGatewayCallStatsIntervalTrunkGroupEntry 11}



     acKpiGatewayCallStatsIntervalTrunkGroupFailedCallsNoCapMatchTel2Ip OBJECT-TYPE
       SYNTAX Counter64
       MAX-ACCESS read-only
       STATUS current
       DESCRIPTION
           "Number of failed Tel->IP calls due to media mismatch.
AC INI-Param: N/A"
       ::= {acKpiGatewayCallStatsIntervalTrunkGroupEntry 12}



     acKpiGatewayCallStatsIntervalTrunkGroupFailedCallsNoCapMatchIp2Tel OBJECT-TYPE
       SYNTAX Counter64
       MAX-ACCESS read-only
       STATUS current
       DESCRIPTION
           "Number of failed IP->Tel calls due to media mismatch.
AC INI-Param: N/A"
       ::= {acKpiGatewayCallStatsIntervalTrunkGroupEntry 13}



     acKpiGatewayCallStatsIntervalTrunkGroupFailedCallsNoAnswerTel2Ip OBJECT-TYPE
       SYNTAX Counter64
       MAX-ACCESS read-only
       STATUS current
       DESCRIPTION
           "Number of failed Tel->IP calls due to no answer from the callee.
AC INI-Param: N/A"
       ::= {acKpiGatewayCallStatsIntervalTrunkGroupEntry 14}



     acKpiGatewayCallStatsIntervalTrunkGroupFailedCallsNoAnswerIp2Tel OBJECT-TYPE
       SYNTAX Counter64
       MAX-ACCESS read-only
       STATUS current
       DESCRIPTION
           "Number of failed IP->Tel calls due to no answer from the callee.
AC INI-Param: N/A"
       ::= {acKpiGatewayCallStatsIntervalTrunkGroupEntry 15}



     acKpiGatewayCallStatsIntervalTrunkGroupFailedCallsBusyTel2Ip OBJECT-TYPE
       SYNTAX Counter64
       MAX-ACCESS read-only
       STATUS current
       DESCRIPTION
           "Number of failed Tel->IP Calls due to callee being busy.
AC INI-Param: N/A"
       ::= {acKpiGatewayCallStatsIntervalTrunkGroupEntry 16}



     acKpiGatewayCallStatsIntervalTrunkGroupFailedCallsBusyIp2Tel OBJECT-TYPE
       SYNTAX Counter64
       MAX-ACCESS read-only
       STATUS current
       DESCRIPTION
           "Number of failed IP->Tel calls due to callee being busy.
AC INI-Param: N/A"
       ::= {acKpiGatewayCallStatsIntervalTrunkGroupEntry 17}



     acKpiGatewayCallStatsIntervalTrunkGroupAverageCallDurationAvg OBJECT-TYPE
       SYNTAX Gauge32
       MAX-ACCESS read-only
       STATUS current
       DESCRIPTION
           "Average call duration (ACD, seconds).
AC INI-Param: N/A"
       ::= {acKpiGatewayCallStatsIntervalTrunkGroupEntry 18}



     acKpiGatewayCallStatsIntervalTrunkGroupEstablishedCallsRateTel2IpMax OBJECT-TYPE
       SYNTAX Gauge32
       MAX-ACCESS read-only
       STATUS current
       DESCRIPTION
           "Maximum rate of established Tel->IP calls (call establish per
second).
AC INI-Param: N/A"
       ::= {acKpiGatewayCallStatsIntervalTrunkGroupEntry 19}



     acKpiGatewayCallStatsIntervalTrunkGroupEstablishedCallsRateTel2IpAvg OBJECT-TYPE
       SYNTAX Gauge32
       MAX-ACCESS read-only
       STATUS current
       DESCRIPTION
           "Average rate of established Tel->IP calls (call establish per
second).
AC INI-Param: N/A"
       ::= {acKpiGatewayCallStatsIntervalTrunkGroupEntry 20}



     acKpiGatewayCallStatsIntervalTrunkGroupEstablishedCallsRateIp2TelMax OBJECT-TYPE
       SYNTAX Gauge32
       MAX-ACCESS read-only
       STATUS current
       DESCRIPTION
           "Maximum rate of established IP->Tel calls (call establish per
second).
AC INI-Param: N/A"
       ::= {acKpiGatewayCallStatsIntervalTrunkGroupEntry 21}



     acKpiGatewayCallStatsIntervalTrunkGroupEstablishedCallsRateIp2TelAvg OBJECT-TYPE
       SYNTAX Gauge32
       MAX-ACCESS read-only
       STATUS current
       DESCRIPTION
           "Average rate of established IP->Tel calls (call establish per
second).
AC INI-Param: N/A"
       ::= {acKpiGatewayCallStatsIntervalTrunkGroupEntry 22}



     acKpiGatewayCallStatsIntervalTrunkGroupEstablishedFaxTel2Ip OBJECT-TYPE
       SYNTAX Counter64
       MAX-ACCESS read-only
       STATUS current
       DESCRIPTION
           "Number of established Tel->IP fax calls.
AC INI-Param: N/A"
       ::= {acKpiGatewayCallStatsIntervalTrunkGroupEntry 23}



     acKpiGatewayCallStatsIntervalTrunkGroupEstablishedFaxIp2Tel OBJECT-TYPE
       SYNTAX Counter64
       MAX-ACCESS read-only
       STATUS current
       DESCRIPTION
           "Number of established IP->Tel fax calls.
AC INI-Param: N/A"
       ::= {acKpiGatewayCallStatsIntervalTrunkGroupEntry 24}



     acKpiGatewayCallStatsIntervalTrunkGroupEstablishedCallsTel2Ip OBJECT-TYPE
       SYNTAX Counter64
       MAX-ACCESS read-only
       STATUS current
       DESCRIPTION
           "Number of established Tel->IP calls.
AC INI-Param: N/A"
       ::= {acKpiGatewayCallStatsIntervalTrunkGroupEntry 25}



     acKpiGatewayCallStatsIntervalTrunkGroupEstablishedCallsIp2Tel OBJECT-TYPE
       SYNTAX Counter64
       MAX-ACCESS read-only
       STATUS current
       DESCRIPTION
           "Number of established IP->Tel calls.
AC INI-Param: N/A"
       ::= {acKpiGatewayCallStatsIntervalTrunkGroupEntry 26}



     acKpiGatewayCallStatsIntervalTrunkGroupAttemptedFaxTel2Ip OBJECT-TYPE
       SYNTAX Counter64
       MAX-ACCESS read-only
       STATUS current
       DESCRIPTION
           "Number of attempted Tel->IP fax calls.
AC INI-Param: N/A"
       ::= {acKpiGatewayCallStatsIntervalTrunkGroupEntry 27}



     acKpiGatewayCallStatsIntervalTrunkGroupAttemptedFaxIp2Tel OBJECT-TYPE
       SYNTAX Counter64
       MAX-ACCESS read-only
       STATUS current
       DESCRIPTION
           "Number of attempted IP->Tel fax calls.
AC INI-Param: N/A"
       ::= {acKpiGatewayCallStatsIntervalTrunkGroupEntry 28}



     acKpiGatewayCallStatsIntervalTrunkGroupAttemptedCallsRateTel2IpMax OBJECT-TYPE
       SYNTAX Gauge32
       MAX-ACCESS read-only
       STATUS current
       DESCRIPTION
           "Maximum rate of attempted Tel->IP calls (call attempts per second).
AC INI-Param: N/A"
       ::= {acKpiGatewayCallStatsIntervalTrunkGroupEntry 29}



     acKpiGatewayCallStatsIntervalTrunkGroupAttemptedCallsRateTel2IpAvg OBJECT-TYPE
       SYNTAX Gauge32
       MAX-ACCESS read-only
       STATUS current
       DESCRIPTION
           "Average rate of attempted Tel->IP calls (call attempts per second).
AC INI-Param: N/A"
       ::= {acKpiGatewayCallStatsIntervalTrunkGroupEntry 30}



     acKpiGatewayCallStatsIntervalTrunkGroupAttemptedCallsTel2Ip OBJECT-TYPE
       SYNTAX Counter64
       MAX-ACCESS read-only
       STATUS current
       DESCRIPTION
           "Number of attempted Tel->IP calls.
AC INI-Param: N/A"
       ::= {acKpiGatewayCallStatsIntervalTrunkGroupEntry 31}



     acKpiGatewayCallStatsIntervalTrunkGroupAttemptedCallsRateIp2TelMax OBJECT-TYPE
       SYNTAX Gauge32
       MAX-ACCESS read-only
       STATUS current
       DESCRIPTION
           "Maximum rate of attempted IP->Tel calls (call attempts per second).
AC INI-Param: N/A"
       ::= {acKpiGatewayCallStatsIntervalTrunkGroupEntry 32}



     acKpiGatewayCallStatsIntervalTrunkGroupAttemptedCallsRateIp2TelAvg OBJECT-TYPE
       SYNTAX Gauge32
       MAX-ACCESS read-only
       STATUS current
       DESCRIPTION
           "Average rate of attempted IP->Tel calls (call attempts per second).
AC INI-Param: N/A"
       ::= {acKpiGatewayCallStatsIntervalTrunkGroupEntry 33}



     acKpiGatewayCallStatsIntervalTrunkGroupAttemptedCallsIp2Tel OBJECT-TYPE
       SYNTAX Counter64
       MAX-ACCESS read-only
       STATUS current
       DESCRIPTION
           "Number of attempted IP->Tel calls.
AC INI-Param: N/A"
       ::= {acKpiGatewayCallStatsIntervalTrunkGroupEntry 34}



     acKpiGatewayCallStatsIntervalTrunkGroupActiveCallsTel2IpMax OBJECT-TYPE
       SYNTAX Gauge32
       MAX-ACCESS read-only
       STATUS current
       DESCRIPTION
           "Maximum number of active Tel->IP calls.
AC INI-Param: N/A"
       ::= {acKpiGatewayCallStatsIntervalTrunkGroupEntry 35}



     acKpiGatewayCallStatsIntervalTrunkGroupActiveCallsTel2Ip2Avg OBJECT-TYPE
       SYNTAX Gauge32
       MAX-ACCESS read-only
       STATUS current
       DESCRIPTION
           "Average Number of Tel->IP Active calls.
AC INI-Param: N/A"
       ::= {acKpiGatewayCallStatsIntervalTrunkGroupEntry 36}



     acKpiGatewayCallStatsIntervalTrunkGroupActiveCallsIp2TelMax OBJECT-TYPE
       SYNTAX Gauge32
       MAX-ACCESS read-only
       STATUS current
       DESCRIPTION
           "Maximum number of active IP->Tel calls.
AC INI-Param: N/A"
       ::= {acKpiGatewayCallStatsIntervalTrunkGroupEntry 37}



     acKpiGatewayCallStatsIntervalTrunkGroupActiveCallsIp2TelAvg OBJECT-TYPE
       SYNTAX Gauge32
       MAX-ACCESS read-only
       STATUS current
       DESCRIPTION
           "Average number of active IP->Tel calls.
AC INI-Param: N/A"
       ::= {acKpiGatewayCallStatsIntervalTrunkGroupEntry 38}



     acKpiGatewayCallStatsIntervalTrunkGroupActiveCallsMax OBJECT-TYPE
       SYNTAX Gauge32
       MAX-ACCESS read-only
       STATUS current
       DESCRIPTION
           "Maximum number of active calls.
AC INI-Param: N/A"
       ::= {acKpiGatewayCallStatsIntervalTrunkGroupEntry 39}



     acKpiGatewayCallStatsIntervalTrunkGroupActiveCallsAvg OBJECT-TYPE
       SYNTAX Gauge32
       MAX-ACCESS read-only
       STATUS current
       DESCRIPTION
           "Average number of active calls.
AC INI-Param: N/A"
       ::= {acKpiGatewayCallStatsIntervalTrunkGroupEntry 40}



     acKpiTrunkStats OBJECT IDENTIFIER ::= {acKpiGateway 2}


     acKpiTrunkStatsCurrent OBJECT IDENTIFIER ::= {acKpiTrunkStats 1}


     acKpiTrunkStatsCurrentGlobal OBJECT IDENTIFIER ::= {acKpiTrunkStatsCurrent 1}


     acKpiTrunkStatsCurrentTables OBJECT IDENTIFIER ::= {acKpiTrunkStatsCurrent 2}


     -- ****************************************
     -- acKpiTrunkStatsCurrentTrunk table declaration
     -- ****************************************
     acKpiTrunkStatsCurrentTrunkTable OBJECT-TYPE
       SYNTAX SEQUENCE OF AcKpiTrunkStatsCurrentTrunkEntry
       MAX-ACCESS not-accessible
       STATUS current
       DESCRIPTION
           ""
       ::= {acKpiTrunkStatsCurrentTables 1}



     -- ****************************************
     -- acKpiTrunkStatsCurrentTrunk table entry
     -- ****************************************
     acKpiTrunkStatsCurrentTrunkEntry OBJECT-TYPE
       SYNTAX AcKpiTrunkStatsCurrentTrunkEntry
       MAX-ACCESS not-accessible
       STATUS current
       DESCRIPTION
           ""
       INDEX {acKpiTrunkStatsCurrentTrunkIndex}
       ::= {acKpiTrunkStatsCurrentTrunkTable 1}



     -- ****************************************
     -- acKpiTrunkStatsCurrentTrunk TABLE
     -- ****************************************
     AcKpiTrunkStatsCurrentTrunkEntry ::= SEQUENCE {
       acKpiTrunkStatsCurrentTrunkIndex                Unsigned32,
       acKpiTrunkStatsCurrentTrunkChannelsNotEquipped  Gauge32,
       acKpiTrunkStatsCurrentTrunkChannelsInMaintenance 
                                                       Gauge32,
       acKpiTrunkStatsCurrentTrunkChannelsOutOfService Gauge32,
       acKpiTrunkStatsCurrentTrunkChannelsInService    Gauge32,
       acKpiTrunkStatsCurrentTrunkUtilization          Gauge32,
       acKpiTrunkStatsCurrentTrunkActiveChannels       Gauge32
     }



     acKpiTrunkStatsCurrentTrunkIndex OBJECT-TYPE
       SYNTAX Unsigned32 (0..32767)
       MAX-ACCESS not-accessible
       STATUS current
       DESCRIPTION
           "
AC INI-Param: N/A"
       ::= {acKpiTrunkStatsCurrentTrunkEntry 1}



     acKpiTrunkStatsCurrentTrunkChannelsNotEquipped OBJECT-TYPE
       SYNTAX Gauge32
       MAX-ACCESS read-only
       STATUS current
       DESCRIPTION
           "Number of channels not equipped (alarm on trunk).
AC INI-Param: N/A"
       ::= {acKpiTrunkStatsCurrentTrunkEntry 2}



     acKpiTrunkStatsCurrentTrunkChannelsInMaintenance OBJECT-TYPE
       SYNTAX Gauge32
       MAX-ACCESS read-only
       STATUS current
       DESCRIPTION
           "Number of channels in maintenance.
AC INI-Param: N/A"
       ::= {acKpiTrunkStatsCurrentTrunkEntry 3}



     acKpiTrunkStatsCurrentTrunkChannelsOutOfService OBJECT-TYPE
       SYNTAX Gauge32
       MAX-ACCESS read-only
       STATUS current
       DESCRIPTION
           "Number of channels in service.
AC INI-Param: N/A"
       ::= {acKpiTrunkStatsCurrentTrunkEntry 4}



     acKpiTrunkStatsCurrentTrunkChannelsInService OBJECT-TYPE
       SYNTAX Gauge32
       MAX-ACCESS read-only
       STATUS current
       DESCRIPTION
           "Number of channels in service.
AC INI-Param: N/A"
       ::= {acKpiTrunkStatsCurrentTrunkEntry 5}



     acKpiTrunkStatsCurrentTrunkUtilization OBJECT-TYPE
       SYNTAX Gauge32
       MAX-ACCESS read-only
       STATUS current
       DESCRIPTION
           "Percentage of active channels from total capacity (%).
AC INI-Param: N/A"
       ::= {acKpiTrunkStatsCurrentTrunkEntry 6}



     acKpiTrunkStatsCurrentTrunkActiveChannels OBJECT-TYPE
       SYNTAX Gauge32
       MAX-ACCESS read-only
       STATUS current
       DESCRIPTION
           "Number of active channels.
AC INI-Param: N/A"
       ::= {acKpiTrunkStatsCurrentTrunkEntry 7}



     -- ****************************************
     -- acKpiTrunkStatsCurrentTrunkGroup table declaration
     -- ****************************************
     acKpiTrunkStatsCurrentTrunkGroupTable OBJECT-TYPE
       SYNTAX SEQUENCE OF AcKpiTrunkStatsCurrentTrunkGroupEntry
       MAX-ACCESS not-accessible
       STATUS current
       DESCRIPTION
           ""
       ::= {acKpiTrunkStatsCurrentTables 2}



     -- ****************************************
     -- acKpiTrunkStatsCurrentTrunkGroup table entry
     -- ****************************************
     acKpiTrunkStatsCurrentTrunkGroupEntry OBJECT-TYPE
       SYNTAX AcKpiTrunkStatsCurrentTrunkGroupEntry
       MAX-ACCESS not-accessible
       STATUS current
       DESCRIPTION
           ""
       INDEX {acKpiTrunkStatsCurrentTrunkGroupIndex}
       ::= {acKpiTrunkStatsCurrentTrunkGroupTable 1}



     -- ****************************************
     -- acKpiTrunkStatsCurrentTrunkGroup TABLE
     -- ****************************************
     AcKpiTrunkStatsCurrentTrunkGroupEntry ::= SEQUENCE {
       acKpiTrunkStatsCurrentTrunkGroupIndex           Unsigned32,
       acKpiTrunkStatsCurrentTrunkGroupUtilization     Gauge32,
       acKpiTrunkStatsCurrentTrunkGroupActiveChannels  Gauge32
     }



     acKpiTrunkStatsCurrentTrunkGroupIndex OBJECT-TYPE
       SYNTAX Unsigned32 (0..32767)
       MAX-ACCESS not-accessible
       STATUS current
       DESCRIPTION
           "
AC INI-Param: N/A"
       ::= {acKpiTrunkStatsCurrentTrunkGroupEntry 1}



     acKpiTrunkStatsCurrentTrunkGroupUtilization OBJECT-TYPE
       SYNTAX Gauge32
       MAX-ACCESS read-only
       STATUS current
       DESCRIPTION
           "Percentage of active channels from total capacity (%).
AC INI-Param: N/A"
       ::= {acKpiTrunkStatsCurrentTrunkGroupEntry 2}



     acKpiTrunkStatsCurrentTrunkGroupActiveChannels OBJECT-TYPE
       SYNTAX Gauge32
       MAX-ACCESS read-only
       STATUS current
       DESCRIPTION
           "Number of active channels.
AC INI-Param: N/A"
       ::= {acKpiTrunkStatsCurrentTrunkGroupEntry 3}



     acKpiTrunkStatsInterval OBJECT IDENTIFIER ::= {acKpiTrunkStats 2}


     acKpiTrunkStatsIntervalGlobal OBJECT IDENTIFIER ::= {acKpiTrunkStatsInterval 1}


     acKpiTrunkStatsIntervalTables OBJECT IDENTIFIER ::= {acKpiTrunkStatsInterval 2}


     -- ****************************************
     -- acKpiTrunkStatsIntervalTrunk table declaration
     -- ****************************************
     acKpiTrunkStatsIntervalTrunkTable OBJECT-TYPE
       SYNTAX SEQUENCE OF AcKpiTrunkStatsIntervalTrunkEntry
       MAX-ACCESS not-accessible
       STATUS current
       DESCRIPTION
           ""
       ::= {acKpiTrunkStatsIntervalTables 1}



     -- ****************************************
     -- acKpiTrunkStatsIntervalTrunk table entry
     -- ****************************************
     acKpiTrunkStatsIntervalTrunkEntry OBJECT-TYPE
       SYNTAX AcKpiTrunkStatsIntervalTrunkEntry
       MAX-ACCESS not-accessible
       STATUS current
       DESCRIPTION
           ""
       INDEX {acKpiTrunkStatsIntervalTrunkIndex,acKpiTrunkStatsIntervalTrunkInterval}
       ::= {acKpiTrunkStatsIntervalTrunkTable 1}



     -- ****************************************
     -- acKpiTrunkStatsIntervalTrunk TABLE
     -- ****************************************
     AcKpiTrunkStatsIntervalTrunkEntry ::= SEQUENCE {
       acKpiTrunkStatsIntervalTrunkIndex               Unsigned32,
       acKpiTrunkStatsIntervalTrunkInterval            Unsigned32,
       acKpiTrunkStatsIntervalTrunkChannelsNotEquippedMax 
                                                       Gauge32,
       acKpiTrunkStatsIntervalTrunkChannelsInMaintenanceMax 
                                                       Gauge32,
       acKpiTrunkStatsIntervalTrunkChannelsOutOfServiceMax 
                                                       Gauge32,
       acKpiTrunkStatsIntervalTrunkChannelsInServiceMax 
                                                       Gauge32,
       acKpiTrunkStatsIntervalTrunkUtilizationMax      Gauge32,
       acKpiTrunkStatsIntervalTrunkUtilizationAvg      Gauge32,
       acKpiTrunkStatsIntervalTrunkActiveChannelsMax   Gauge32,
       acKpiTrunkStatsIntervalTrunkActiveChannelsAvg   Gauge32,
       acKpiTrunkStatsIntervalTrunkChannelsInServiceAvg 
                                                       Gauge32,
       acKpiTrunkStatsIntervalTrunkChannelsOutOfServiceAvg 
                                                       Gauge32,
       acKpiTrunkStatsIntervalTrunkChannelsInMaintenanceAvg 
                                                       Gauge32,
       acKpiTrunkStatsIntervalTrunkChannelsNotEquippedAvg 
                                                       Gauge32
     }



     acKpiTrunkStatsIntervalTrunkIndex OBJECT-TYPE
       SYNTAX Unsigned32 (0..32767)
       MAX-ACCESS not-accessible
       STATUS current
       DESCRIPTION
           "
AC INI-Param: N/A"
       ::= {acKpiTrunkStatsIntervalTrunkEntry 1}



     acKpiTrunkStatsIntervalTrunkInterval OBJECT-TYPE
       SYNTAX Unsigned32 (1..200)
       MAX-ACCESS not-accessible
       STATUS current
       DESCRIPTION
           "
AC INI-Param: N/A"
       ::= {acKpiTrunkStatsIntervalTrunkEntry 2}



     acKpiTrunkStatsIntervalTrunkChannelsNotEquippedMax OBJECT-TYPE
       SYNTAX Gauge32
       MAX-ACCESS read-only
       STATUS current
       DESCRIPTION
           "Maximum Number of channels not equipped (alarm on trunk).
AC INI-Param: N/A"
       ::= {acKpiTrunkStatsIntervalTrunkEntry 3}



     acKpiTrunkStatsIntervalTrunkChannelsInMaintenanceMax OBJECT-TYPE
       SYNTAX Gauge32
       MAX-ACCESS read-only
       STATUS current
       DESCRIPTION
           "Maximum Number of channels in maintenance.
AC INI-Param: N/A"
       ::= {acKpiTrunkStatsIntervalTrunkEntry 4}



     acKpiTrunkStatsIntervalTrunkChannelsOutOfServiceMax OBJECT-TYPE
       SYNTAX Gauge32
       MAX-ACCESS read-only
       STATUS current
       DESCRIPTION
           "Maximum Number of active channels in trunk.
AC INI-Param: N/A"
       ::= {acKpiTrunkStatsIntervalTrunkEntry 5}



     acKpiTrunkStatsIntervalTrunkChannelsInServiceMax OBJECT-TYPE
       SYNTAX Gauge32
       MAX-ACCESS read-only
       STATUS current
       DESCRIPTION
           "Maximum Number of active channels in trunk.
AC INI-Param: N/A"
       ::= {acKpiTrunkStatsIntervalTrunkEntry 6}



     acKpiTrunkStatsIntervalTrunkUtilizationMax OBJECT-TYPE
       SYNTAX Gauge32
       MAX-ACCESS read-only
       STATUS current
       DESCRIPTION
           "Maximum percentage of active channels from total capacity (%).
AC INI-Param: N/A"
       ::= {acKpiTrunkStatsIntervalTrunkEntry 7}



     acKpiTrunkStatsIntervalTrunkUtilizationAvg OBJECT-TYPE
       SYNTAX Gauge32
       MAX-ACCESS read-only
       STATUS current
       DESCRIPTION
           "Average percentage of active channels from total capacity (%).
AC INI-Param: N/A"
       ::= {acKpiTrunkStatsIntervalTrunkEntry 8}



     acKpiTrunkStatsIntervalTrunkActiveChannelsMax OBJECT-TYPE
       SYNTAX Gauge32
       MAX-ACCESS read-only
       STATUS current
       DESCRIPTION
           "Maximum number of active channels.
AC INI-Param: N/A"
       ::= {acKpiTrunkStatsIntervalTrunkEntry 9}



     acKpiTrunkStatsIntervalTrunkActiveChannelsAvg OBJECT-TYPE
       SYNTAX Gauge32
       MAX-ACCESS read-only
       STATUS current
       DESCRIPTION
           "Average number of active channels.
AC INI-Param: N/A"
       ::= {acKpiTrunkStatsIntervalTrunkEntry 10}



     acKpiTrunkStatsIntervalTrunkChannelsInServiceAvg OBJECT-TYPE
       SYNTAX Gauge32
       MAX-ACCESS read-only
       STATUS current
       DESCRIPTION
           "Average Number of channels in service.
AC INI-Param: N/A"
       ::= {acKpiTrunkStatsIntervalTrunkEntry 11}



     acKpiTrunkStatsIntervalTrunkChannelsOutOfServiceAvg OBJECT-TYPE
       SYNTAX Gauge32
       MAX-ACCESS read-only
       STATUS current
       DESCRIPTION
           "Average Number of channels in service.
AC INI-Param: N/A"
       ::= {acKpiTrunkStatsIntervalTrunkEntry 12}



     acKpiTrunkStatsIntervalTrunkChannelsInMaintenanceAvg OBJECT-TYPE
       SYNTAX Gauge32
       MAX-ACCESS read-only
       STATUS current
       DESCRIPTION
           "Average Number of channels in maintenance.
AC INI-Param: N/A"
       ::= {acKpiTrunkStatsIntervalTrunkEntry 13}



     acKpiTrunkStatsIntervalTrunkChannelsNotEquippedAvg OBJECT-TYPE
       SYNTAX Gauge32
       MAX-ACCESS read-only
       STATUS current
       DESCRIPTION
           "Average Number of channels not equipped (alarm on trunk).
AC INI-Param: N/A"
       ::= {acKpiTrunkStatsIntervalTrunkEntry 14}



     -- ****************************************
     -- acKpiTrunkStatsIntervalTrunkGroup table declaration
     -- ****************************************
     acKpiTrunkStatsIntervalTrunkGroupTable OBJECT-TYPE
       SYNTAX SEQUENCE OF AcKpiTrunkStatsIntervalTrunkGroupEntry
       MAX-ACCESS not-accessible
       STATUS current
       DESCRIPTION
           ""
       ::= {acKpiTrunkStatsIntervalTables 2}



     -- ****************************************
     -- acKpiTrunkStatsIntervalTrunkGroup table entry
     -- ****************************************
     acKpiTrunkStatsIntervalTrunkGroupEntry OBJECT-TYPE
       SYNTAX AcKpiTrunkStatsIntervalTrunkGroupEntry
       MAX-ACCESS not-accessible
       STATUS current
       DESCRIPTION
           ""
       INDEX {acKpiTrunkStatsIntervalTrunkGroupIndex,acKpiTrunkStatsIntervalTrunkGroupInterval}
       ::= {acKpiTrunkStatsIntervalTrunkGroupTable 1}



     -- ****************************************
     -- acKpiTrunkStatsIntervalTrunkGroup TABLE
     -- ****************************************
     AcKpiTrunkStatsIntervalTrunkGroupEntry ::= SEQUENCE {
       acKpiTrunkStatsIntervalTrunkGroupIndex          Unsigned32,
       acKpiTrunkStatsIntervalTrunkGroupInterval       Unsigned32,
       acKpiTrunkStatsIntervalTrunkGroupUtilizationMax Gauge32,
       acKpiTrunkStatsIntervalTrunkGroupUtilizationAvg Gauge32,
       acKpiTrunkStatsIntervalTrunkGroupActiveChannelsMax 
                                                       Gauge32,
       acKpiTrunkStatsIntervalTrunkGroupActiveChannelsAvg 
                                                       Gauge32,
       acKpiTrunkStatsIntervalTrunkGroupAllChannelsBusy 
                                                       Gauge32
     }



     acKpiTrunkStatsIntervalTrunkGroupIndex OBJECT-TYPE
       SYNTAX Unsigned32 (0..32767)
       MAX-ACCESS not-accessible
       STATUS current
       DESCRIPTION
           "
AC INI-Param: N/A"
       ::= {acKpiTrunkStatsIntervalTrunkGroupEntry 1}



     acKpiTrunkStatsIntervalTrunkGroupInterval OBJECT-TYPE
       SYNTAX Unsigned32 (1..200)
       MAX-ACCESS not-accessible
       STATUS current
       DESCRIPTION
           "
AC INI-Param: N/A"
       ::= {acKpiTrunkStatsIntervalTrunkGroupEntry 2}



     acKpiTrunkStatsIntervalTrunkGroupUtilizationMax OBJECT-TYPE
       SYNTAX Gauge32
       MAX-ACCESS read-only
       STATUS current
       DESCRIPTION
           "Maximum percentage of active channels from total capacity (%).
AC INI-Param: N/A"
       ::= {acKpiTrunkStatsIntervalTrunkGroupEntry 3}



     acKpiTrunkStatsIntervalTrunkGroupUtilizationAvg OBJECT-TYPE
       SYNTAX Gauge32
       MAX-ACCESS read-only
       STATUS current
       DESCRIPTION
           "Average percentage of active channels from total capacity (%).
AC INI-Param: N/A"
       ::= {acKpiTrunkStatsIntervalTrunkGroupEntry 4}



     acKpiTrunkStatsIntervalTrunkGroupActiveChannelsMax OBJECT-TYPE
       SYNTAX Gauge32
       MAX-ACCESS read-only
       STATUS current
       DESCRIPTION
           "Maximum number of active channels.
AC INI-Param: N/A"
       ::= {acKpiTrunkStatsIntervalTrunkGroupEntry 5}



     acKpiTrunkStatsIntervalTrunkGroupActiveChannelsAvg OBJECT-TYPE
       SYNTAX Gauge32
       MAX-ACCESS read-only
       STATUS current
       DESCRIPTION
           "Average number of active channels.
AC INI-Param: N/A"
       ::= {acKpiTrunkStatsIntervalTrunkGroupEntry 6}



     acKpiTrunkStatsIntervalTrunkGroupAllChannelsBusy OBJECT-TYPE
       SYNTAX Gauge32
       MAX-ACCESS read-only
       STATUS current
       DESCRIPTION
           "percentage of time within 15 min that all channels were busy.
AC INI-Param: N/A"
       ::= {acKpiTrunkStatsIntervalTrunkGroupEntry 7}



     acKpiAnalogStats OBJECT IDENTIFIER ::= {acKpiGateway 3}


     acKpiAnalogStatsCurrent OBJECT IDENTIFIER ::= {acKpiAnalogStats 1}


     acKpiAnalogStatsCurrentGlobal OBJECT IDENTIFIER ::= {acKpiAnalogStatsCurrent 1}


     acKpiAnalogStatsCurrentGlobalAnalogActiveLines OBJECT-TYPE
       SYNTAX Gauge32
       MAX-ACCESS read-only
       STATUS current
       DESCRIPTION
           "Number of active (off-hook) analog lines.
AC INI-Param: N/A"
       ::= {acKpiAnalogStatsCurrentGlobal 1}



     acKpiAnalogStatsInterval OBJECT IDENTIFIER ::= {acKpiAnalogStats 2}


     acKpiAnalogStatsIntervalGlobal OBJECT IDENTIFIER ::= {acKpiAnalogStatsInterval 1}


     -- ****************************************
     -- acKpiAnalogStatsIntervalGlobal table declaration
     -- ****************************************
     acKpiAnalogStatsIntervalGlobalTable OBJECT-TYPE
       SYNTAX SEQUENCE OF AcKpiAnalogStatsIntervalGlobalEntry
       MAX-ACCESS not-accessible
       STATUS current
       DESCRIPTION
           ""
       ::= {acKpiAnalogStatsIntervalGlobal 1}



     -- ****************************************
     -- acKpiAnalogStatsIntervalGlobal table entry
     -- ****************************************
     acKpiAnalogStatsIntervalGlobalEntry OBJECT-TYPE
       SYNTAX AcKpiAnalogStatsIntervalGlobalEntry
       MAX-ACCESS not-accessible
       STATUS current
       DESCRIPTION
           ""
       INDEX {acKpiAnalogStatsIntervalGlobalInterval}
       ::= {acKpiAnalogStatsIntervalGlobalTable 1}



     -- ****************************************
     -- acKpiAnalogStatsIntervalGlobal TABLE
     -- ****************************************
     AcKpiAnalogStatsIntervalGlobalEntry ::= SEQUENCE {
       acKpiAnalogStatsIntervalGlobalInterval          Unsigned32,
       acKpiAnalogStatsIntervalGlobalAnalogActiveLinesMax 
                                                       Gauge32,
       acKpiAnalogStatsIntervalGlobalAnalogActiveLinesAvg 
                                                       Gauge32
     }



     acKpiAnalogStatsIntervalGlobalInterval OBJECT-TYPE
       SYNTAX Unsigned32 (1..200)
       MAX-ACCESS not-accessible
       STATUS current
       DESCRIPTION
           "
AC INI-Param: N/A"
       ::= {acKpiAnalogStatsIntervalGlobalEntry 1}



     acKpiAnalogStatsIntervalGlobalAnalogActiveLinesMax OBJECT-TYPE
       SYNTAX Gauge32
       MAX-ACCESS read-only
       STATUS current
       DESCRIPTION
           "Maximum number of active (off-hook) analog lines.
AC INI-Param: N/A"
       ::= {acKpiAnalogStatsIntervalGlobalEntry 2}



     acKpiAnalogStatsIntervalGlobalAnalogActiveLinesAvg OBJECT-TYPE
       SYNTAX Gauge32
       MAX-ACCESS read-only
       STATUS current
       DESCRIPTION
           "Average number of active (off-hook) analog lines.
AC INI-Param: N/A"
       ::= {acKpiAnalogStatsIntervalGlobalEntry 3}



     acKpiDs1Stats OBJECT IDENTIFIER ::= {acKpiGateway 4}


     acKpiDs1StatsCurrent OBJECT IDENTIFIER ::= {acKpiDs1Stats 1}


     acKpiDs1StatsCurrentGlobal OBJECT IDENTIFIER ::= {acKpiDs1StatsCurrent 1}


     acKpiDs1StatsCurrentTables OBJECT IDENTIFIER ::= {acKpiDs1StatsCurrent 2}


     -- ****************************************
     -- acKpiDs1StatsCurrentTrunk table declaration
     -- ****************************************
     acKpiDs1StatsCurrentTrunkTable OBJECT-TYPE
       SYNTAX SEQUENCE OF AcKpiDs1StatsCurrentTrunkEntry
       MAX-ACCESS not-accessible
       STATUS current
       DESCRIPTION
           ""
       ::= {acKpiDs1StatsCurrentTables 1}



     -- ****************************************
     -- acKpiDs1StatsCurrentTrunk table entry
     -- ****************************************
     acKpiDs1StatsCurrentTrunkEntry OBJECT-TYPE
       SYNTAX AcKpiDs1StatsCurrentTrunkEntry
       MAX-ACCESS not-accessible
       STATUS current
       DESCRIPTION
           ""
       INDEX {acKpiDs1StatsCurrentTrunkIndex}
       ::= {acKpiDs1StatsCurrentTrunkTable 1}



     -- ****************************************
     -- acKpiDs1StatsCurrentTrunk TABLE
     -- ****************************************
     AcKpiDs1StatsCurrentTrunkEntry ::= SEQUENCE {
       acKpiDs1StatsCurrentTrunkIndex                  Unsigned32,
       acKpiDs1StatsCurrentTrunkDegradedMinutesCurrent Counter64,
       acKpiDs1StatsCurrentTrunkLineErroredSecondsCurrent 
                                                       Counter64,
       acKpiDs1StatsCurrentTrunkPathCodingViolationsCurrent 
                                                       Counter64,
       acKpiDs1StatsCurrentTrunkUnavailableSecondsCurrent 
                                                       Counter64,
       acKpiDs1StatsCurrentTrunkBurstyErroredSecondsCurrent 
                                                       Counter64,
       acKpiDs1StatsCurrentTrunkSeverelyErroredSecondsCurrent 
                                                       Counter64,
       acKpiDs1StatsCurrentTrunkSeverelyErroredFramingSecondsCurrent 
                                                       Counter64,
       acKpiDs1StatsCurrentTrunkControlledSlipSecondsCurrent 
                                                       Counter64,
       acKpiDs1StatsCurrentTrunkErroredSecondsCurrent  Counter64,
       acKpiDs1StatsCurrentTrunkControlledSlipsCurrent Counter64,
       acKpiDs1StatsCurrentTrunkLineCodingViolationsCurrent 
                                                       Counter64,
       acKpiDs1StatsCurrentTrunkBitErrorsCurrent       Counter64,
       acKpiDs1StatsCurrentTrunkEbitErrorsCurrent      Counter64,
       acKpiDs1StatsCurrentTrunkCrcErrorsCurrent       Counter64,
       acKpiDs1StatsCurrentTrunkCrc4MultiframeErrorsCurrent 
                                                       Counter64,
       acKpiDs1StatsCurrentTrunkRemoteAlarmsReceivedCurrent 
                                                       Counter64,
       acKpiDs1StatsCurrentTrunkFramingErrorsCurrent   Counter64,
       acKpiDs1StatsCurrentTrunkLofAlarmsCurrent       Counter64,
       acKpiDs1StatsCurrentTrunkLosAlarmsCurrent       Counter64,
       acKpiDs1StatsCurrentTrunkAisAlarmsCurrent       Counter64
     }



     acKpiDs1StatsCurrentTrunkIndex OBJECT-TYPE
       SYNTAX Unsigned32 (0..32767)
       MAX-ACCESS not-accessible
       STATUS current
       DESCRIPTION
           "
AC INI-Param: N/A"
       ::= {acKpiDs1StatsCurrentTrunkEntry 1}



     acKpiDs1StatsCurrentTrunkDegradedMinutesCurrent OBJECT-TYPE
       SYNTAX Counter64
       MAX-ACCESS read-only
       STATUS current
       DESCRIPTION
           "Current number of degraded minutes.
AC INI-Param: N/A"
       ::= {acKpiDs1StatsCurrentTrunkEntry 2}



     acKpiDs1StatsCurrentTrunkLineErroredSecondsCurrent OBJECT-TYPE
       SYNTAX Counter64
       MAX-ACCESS read-only
       STATUS current
       DESCRIPTION
           "Current number of line errored seconds.
AC INI-Param: N/A"
       ::= {acKpiDs1StatsCurrentTrunkEntry 3}



     acKpiDs1StatsCurrentTrunkPathCodingViolationsCurrent OBJECT-TYPE
       SYNTAX Counter64
       MAX-ACCESS read-only
       STATUS current
       DESCRIPTION
           "Current number of path coding violations.
AC INI-Param: N/A"
       ::= {acKpiDs1StatsCurrentTrunkEntry 4}



     acKpiDs1StatsCurrentTrunkUnavailableSecondsCurrent OBJECT-TYPE
       SYNTAX Counter64
       MAX-ACCESS read-only
       STATUS current
       DESCRIPTION
           "Current number of unavailable seconds.
AC INI-Param: N/A"
       ::= {acKpiDs1StatsCurrentTrunkEntry 5}



     acKpiDs1StatsCurrentTrunkBurstyErroredSecondsCurrent OBJECT-TYPE
       SYNTAX Counter64
       MAX-ACCESS read-only
       STATUS current
       DESCRIPTION
           "Current number of bursty errored seconds.
AC INI-Param: N/A"
       ::= {acKpiDs1StatsCurrentTrunkEntry 6}



     acKpiDs1StatsCurrentTrunkSeverelyErroredSecondsCurrent OBJECT-TYPE
       SYNTAX Counter64
       MAX-ACCESS read-only
       STATUS current
       DESCRIPTION
           "Current number of severely errored seconds.
AC INI-Param: N/A"
       ::= {acKpiDs1StatsCurrentTrunkEntry 7}



     acKpiDs1StatsCurrentTrunkSeverelyErroredFramingSecondsCurrent OBJECT-TYPE
       SYNTAX Counter64
       MAX-ACCESS read-only
       STATUS current
       DESCRIPTION
           "Current number of severely errored framing seconds.
AC INI-Param: N/A"
       ::= {acKpiDs1StatsCurrentTrunkEntry 8}



     acKpiDs1StatsCurrentTrunkControlledSlipSecondsCurrent OBJECT-TYPE
       SYNTAX Counter64
       MAX-ACCESS read-only
       STATUS current
       DESCRIPTION
           "Current number of controlled slip seconds.
AC INI-Param: N/A"
       ::= {acKpiDs1StatsCurrentTrunkEntry 9}



     acKpiDs1StatsCurrentTrunkErroredSecondsCurrent OBJECT-TYPE
       SYNTAX Counter64
       MAX-ACCESS read-only
       STATUS current
       DESCRIPTION
           "Current number of errored seconds.
AC INI-Param: N/A"
       ::= {acKpiDs1StatsCurrentTrunkEntry 10}



     acKpiDs1StatsCurrentTrunkControlledSlipsCurrent OBJECT-TYPE
       SYNTAX Counter64
       MAX-ACCESS read-only
       STATUS current
       DESCRIPTION
           "Current number of controlled slip events.
AC INI-Param: N/A"
       ::= {acKpiDs1StatsCurrentTrunkEntry 11}



     acKpiDs1StatsCurrentTrunkLineCodingViolationsCurrent OBJECT-TYPE
       SYNTAX Counter64
       MAX-ACCESS read-only
       STATUS current
       DESCRIPTION
           "Current number of line coding violations.
AC INI-Param: N/A"
       ::= {acKpiDs1StatsCurrentTrunkEntry 12}



     acKpiDs1StatsCurrentTrunkBitErrorsCurrent OBJECT-TYPE
       SYNTAX Counter64
       MAX-ACCESS read-only
       STATUS current
       DESCRIPTION
           "Current number of bit errors.
AC INI-Param: N/A"
       ::= {acKpiDs1StatsCurrentTrunkEntry 13}



     acKpiDs1StatsCurrentTrunkEbitErrorsCurrent OBJECT-TYPE
       SYNTAX Counter64
       MAX-ACCESS read-only
       STATUS current
       DESCRIPTION
           "Current number of E-bit errors.
AC INI-Param: N/A"
       ::= {acKpiDs1StatsCurrentTrunkEntry 14}



     acKpiDs1StatsCurrentTrunkCrcErrorsCurrent OBJECT-TYPE
       SYNTAX Counter64
       MAX-ACCESS read-only
       STATUS current
       DESCRIPTION
           "Current number of CRC errors.
AC INI-Param: N/A"
       ::= {acKpiDs1StatsCurrentTrunkEntry 15}



     acKpiDs1StatsCurrentTrunkCrc4MultiframeErrorsCurrent OBJECT-TYPE
       SYNTAX Counter64
       MAX-ACCESS read-only
       STATUS current
       DESCRIPTION
           "Current number of multi-frame alignment errors or FEC errors.
AC INI-Param: N/A"
       ::= {acKpiDs1StatsCurrentTrunkEntry 16}



     acKpiDs1StatsCurrentTrunkRemoteAlarmsReceivedCurrent OBJECT-TYPE
       SYNTAX Counter64
       MAX-ACCESS read-only
       STATUS current
       DESCRIPTION
           "Current number of remote alarm indication (RAI) alarms.
AC INI-Param: N/A"
       ::= {acKpiDs1StatsCurrentTrunkEntry 17}



     acKpiDs1StatsCurrentTrunkFramingErrorsCurrent OBJECT-TYPE
       SYNTAX Counter64
       MAX-ACCESS read-only
       STATUS current
       DESCRIPTION
           "Current number of received framing errors.
AC INI-Param: N/A"
       ::= {acKpiDs1StatsCurrentTrunkEntry 18}



     acKpiDs1StatsCurrentTrunkLofAlarmsCurrent OBJECT-TYPE
       SYNTAX Counter64
       MAX-ACCESS read-only
       STATUS current
       DESCRIPTION
           "Current number of loss of frame (LOF) alarms.
AC INI-Param: N/A"
       ::= {acKpiDs1StatsCurrentTrunkEntry 19}



     acKpiDs1StatsCurrentTrunkLosAlarmsCurrent OBJECT-TYPE
       SYNTAX Counter64
       MAX-ACCESS read-only
       STATUS current
       DESCRIPTION
           "Current number of loss of signal (LOS) alarms.
AC INI-Param: N/A"
       ::= {acKpiDs1StatsCurrentTrunkEntry 20}



     acKpiDs1StatsCurrentTrunkAisAlarmsCurrent OBJECT-TYPE
       SYNTAX Counter64
       MAX-ACCESS read-only
       STATUS current
       DESCRIPTION
           "Current number of alarm indication signal (AIS) alarms.
AC INI-Param: N/A"
       ::= {acKpiDs1StatsCurrentTrunkEntry 21}



     acKpiDs1StatsInterval OBJECT IDENTIFIER ::= {acKpiDs1Stats 2}


     acKpiDs1StatsIntervalGlobal OBJECT IDENTIFIER ::= {acKpiDs1StatsInterval 1}


     acKpiDs1StatsIntervalTables OBJECT IDENTIFIER ::= {acKpiDs1StatsInterval 2}


     -- ****************************************
     -- acKpiDs1StatsIntervalTrunk table declaration
     -- ****************************************
     acKpiDs1StatsIntervalTrunkTable OBJECT-TYPE
       SYNTAX SEQUENCE OF AcKpiDs1StatsIntervalTrunkEntry
       MAX-ACCESS not-accessible
       STATUS current
       DESCRIPTION
           ""
       ::= {acKpiDs1StatsIntervalTables 1}



     -- ****************************************
     -- acKpiDs1StatsIntervalTrunk table entry
     -- ****************************************
     acKpiDs1StatsIntervalTrunkEntry OBJECT-TYPE
       SYNTAX AcKpiDs1StatsIntervalTrunkEntry
       MAX-ACCESS not-accessible
       STATUS current
       DESCRIPTION
           ""
       INDEX {acKpiDs1StatsIntervalTrunkIndex,acKpiDs1StatsIntervalTrunkInterval}
       ::= {acKpiDs1StatsIntervalTrunkTable 1}



     -- ****************************************
     -- acKpiDs1StatsIntervalTrunk TABLE
     -- ****************************************
     AcKpiDs1StatsIntervalTrunkEntry ::= SEQUENCE {
       acKpiDs1StatsIntervalTrunkIndex                 Unsigned32,
       acKpiDs1StatsIntervalTrunkInterval              Unsigned32,
       acKpiDs1StatsIntervalTrunkAisAlarms             Counter64,
       acKpiDs1StatsIntervalTrunkLosAlarms             Counter64,
       acKpiDs1StatsIntervalTrunkLofAlarms             Counter64,
       acKpiDs1StatsIntervalTrunkFramingErrors         Counter64,
       acKpiDs1StatsIntervalTrunkRemoteAlarmsReceived  Counter64,
       acKpiDs1StatsIntervalTrunkCrc4MultiframeErrors  Counter64,
       acKpiDs1StatsIntervalTrunkCrcErrors             Counter64,
       acKpiDs1StatsIntervalTrunkEbitErrors            Counter64,
       acKpiDs1StatsIntervalTrunkBitErrors             Counter64,
       acKpiDs1StatsIntervalTrunkLineCodingViolations  Counter64,
       acKpiDs1StatsIntervalTrunkControlledSlips       Counter64,
       acKpiDs1StatsIntervalTrunkErroredSeconds        Counter64,
       acKpiDs1StatsIntervalTrunkControlledSlipSeconds Counter64,
       acKpiDs1StatsIntervalTrunkSeverelyErroredFramingSeconds 
                                                       Counter64,
       acKpiDs1StatsIntervalTrunkSeverelyErroredSeconds 
                                                       Counter64,
       acKpiDs1StatsIntervalTrunkBurstyErroredSeconds  Counter64,
       acKpiDs1StatsIntervalTrunkUnavailableSeconds    Counter64,
       acKpiDs1StatsIntervalTrunkPathCodingViolations  Counter64,
       acKpiDs1StatsIntervalTrunkLineErroredSeconds    Counter64,
       acKpiDs1StatsIntervalTrunkDegradedMinutes       Counter64
     }



     acKpiDs1StatsIntervalTrunkIndex OBJECT-TYPE
       SYNTAX Unsigned32 (0..32767)
       MAX-ACCESS not-accessible
       STATUS current
       DESCRIPTION
           "
AC INI-Param: N/A"
       ::= {acKpiDs1StatsIntervalTrunkEntry 1}



     acKpiDs1StatsIntervalTrunkInterval OBJECT-TYPE
       SYNTAX Unsigned32 (1..200)
       MAX-ACCESS not-accessible
       STATUS current
       DESCRIPTION
           "
AC INI-Param: N/A"
       ::= {acKpiDs1StatsIntervalTrunkEntry 2}



     acKpiDs1StatsIntervalTrunkAisAlarms OBJECT-TYPE
       SYNTAX Counter64
       MAX-ACCESS read-only
       STATUS current
       DESCRIPTION
           "Number of alarm indication signal (AIS) alarms.
AC INI-Param: N/A"
       ::= {acKpiDs1StatsIntervalTrunkEntry 3}



     acKpiDs1StatsIntervalTrunkLosAlarms OBJECT-TYPE
       SYNTAX Counter64
       MAX-ACCESS read-only
       STATUS current
       DESCRIPTION
           "Number of loss of signal (LOS) alarms.
AC INI-Param: N/A"
       ::= {acKpiDs1StatsIntervalTrunkEntry 4}



     acKpiDs1StatsIntervalTrunkLofAlarms OBJECT-TYPE
       SYNTAX Counter64
       MAX-ACCESS read-only
       STATUS current
       DESCRIPTION
           "Number of loss of frame (LOF) alarms.
AC INI-Param: N/A"
       ::= {acKpiDs1StatsIntervalTrunkEntry 5}



     acKpiDs1StatsIntervalTrunkFramingErrors OBJECT-TYPE
       SYNTAX Counter64
       MAX-ACCESS read-only
       STATUS current
       DESCRIPTION
           "Number of received framing errors.
AC INI-Param: N/A"
       ::= {acKpiDs1StatsIntervalTrunkEntry 6}



     acKpiDs1StatsIntervalTrunkRemoteAlarmsReceived OBJECT-TYPE
       SYNTAX Counter64
       MAX-ACCESS read-only
       STATUS current
       DESCRIPTION
           "Number of remote alarm indication (RAI) alarms.
AC INI-Param: N/A"
       ::= {acKpiDs1StatsIntervalTrunkEntry 7}



     acKpiDs1StatsIntervalTrunkCrc4MultiframeErrors OBJECT-TYPE
       SYNTAX Counter64
       MAX-ACCESS read-only
       STATUS current
       DESCRIPTION
           "Number of multi-frame alignment errors or FEC errors.
AC INI-Param: N/A"
       ::= {acKpiDs1StatsIntervalTrunkEntry 8}



     acKpiDs1StatsIntervalTrunkCrcErrors OBJECT-TYPE
       SYNTAX Counter64
       MAX-ACCESS read-only
       STATUS current
       DESCRIPTION
           "Number of CRC errors.
AC INI-Param: N/A"
       ::= {acKpiDs1StatsIntervalTrunkEntry 9}



     acKpiDs1StatsIntervalTrunkEbitErrors OBJECT-TYPE
       SYNTAX Counter64
       MAX-ACCESS read-only
       STATUS current
       DESCRIPTION
           "Number of E-bit errors.
AC INI-Param: N/A"
       ::= {acKpiDs1StatsIntervalTrunkEntry 10}



     acKpiDs1StatsIntervalTrunkBitErrors OBJECT-TYPE
       SYNTAX Counter64
       MAX-ACCESS read-only
       STATUS current
       DESCRIPTION
           "Number of bit errors.
AC INI-Param: N/A"
       ::= {acKpiDs1StatsIntervalTrunkEntry 11}



     acKpiDs1StatsIntervalTrunkLineCodingViolations OBJECT-TYPE
       SYNTAX Counter64
       MAX-ACCESS read-only
       STATUS current
       DESCRIPTION
           "Number of line coding violations.
AC INI-Param: N/A"
       ::= {acKpiDs1StatsIntervalTrunkEntry 12}



     acKpiDs1StatsIntervalTrunkControlledSlips OBJECT-TYPE
       SYNTAX Counter64
       MAX-ACCESS read-only
       STATUS current
       DESCRIPTION
           "Number of controlled slip events.
AC INI-Param: N/A"
       ::= {acKpiDs1StatsIntervalTrunkEntry 13}



     acKpiDs1StatsIntervalTrunkErroredSeconds OBJECT-TYPE
       SYNTAX Counter64
       MAX-ACCESS read-only
       STATUS current
       DESCRIPTION
           "Number of errored seconds.
AC INI-Param: N/A"
       ::= {acKpiDs1StatsIntervalTrunkEntry 14}



     acKpiDs1StatsIntervalTrunkControlledSlipSeconds OBJECT-TYPE
       SYNTAX Counter64
       MAX-ACCESS read-only
       STATUS current
       DESCRIPTION
           "Number of controlled slip seconds.
AC INI-Param: N/A"
       ::= {acKpiDs1StatsIntervalTrunkEntry 15}



     acKpiDs1StatsIntervalTrunkSeverelyErroredFramingSeconds OBJECT-TYPE
       SYNTAX Counter64
       MAX-ACCESS read-only
       STATUS current
       DESCRIPTION
           "Number of severely errored framing seconds.
AC INI-Param: N/A"
       ::= {acKpiDs1StatsIntervalTrunkEntry 16}



     acKpiDs1StatsIntervalTrunkSeverelyErroredSeconds OBJECT-TYPE
       SYNTAX Counter64
       MAX-ACCESS read-only
       STATUS current
       DESCRIPTION
           "Number of severely errored seconds.
AC INI-Param: N/A"
       ::= {acKpiDs1StatsIntervalTrunkEntry 17}



     acKpiDs1StatsIntervalTrunkBurstyErroredSeconds OBJECT-TYPE
       SYNTAX Counter64
       MAX-ACCESS read-only
       STATUS current
       DESCRIPTION
           "Number of bursty errored seconds.
AC INI-Param: N/A"
       ::= {acKpiDs1StatsIntervalTrunkEntry 18}



     acKpiDs1StatsIntervalTrunkUnavailableSeconds OBJECT-TYPE
       SYNTAX Counter64
       MAX-ACCESS read-only
       STATUS current
       DESCRIPTION
           "Number of unavailable seconds.
AC INI-Param: N/A"
       ::= {acKpiDs1StatsIntervalTrunkEntry 19}



     acKpiDs1StatsIntervalTrunkPathCodingViolations OBJECT-TYPE
       SYNTAX Counter64
       MAX-ACCESS read-only
       STATUS current
       DESCRIPTION
           "Number of path coding violations.
AC INI-Param: N/A"
       ::= {acKpiDs1StatsIntervalTrunkEntry 20}



     acKpiDs1StatsIntervalTrunkLineErroredSeconds OBJECT-TYPE
       SYNTAX Counter64
       MAX-ACCESS read-only
       STATUS current
       DESCRIPTION
           "Number of line errored seconds.
AC INI-Param: N/A"
       ::= {acKpiDs1StatsIntervalTrunkEntry 21}



     acKpiDs1StatsIntervalTrunkDegradedMinutes OBJECT-TYPE
       SYNTAX Counter64
       MAX-ACCESS read-only
       STATUS current
       DESCRIPTION
           "Number of degraded minutes.
AC INI-Param: N/A"
       ::= {acKpiDs1StatsIntervalTrunkEntry 22}



     acKpiBriStats OBJECT IDENTIFIER ::= {acKpiGateway 5}


     acKpiBriStatsCurrent OBJECT IDENTIFIER ::= {acKpiBriStats 1}


     acKpiBriStatsCurrentGlobal OBJECT IDENTIFIER ::= {acKpiBriStatsCurrent 1}


     acKpiBriStatsCurrentTables OBJECT IDENTIFIER ::= {acKpiBriStatsCurrent 2}


     -- ****************************************
     -- acKpiBriStatsCurrentTrunk table declaration
     -- ****************************************
     acKpiBriStatsCurrentTrunkTable OBJECT-TYPE
       SYNTAX SEQUENCE OF AcKpiBriStatsCurrentTrunkEntry
       MAX-ACCESS not-accessible
       STATUS current
       DESCRIPTION
           ""
       ::= {acKpiBriStatsCurrentTables 1}



     -- ****************************************
     -- acKpiBriStatsCurrentTrunk table entry
     -- ****************************************
     acKpiBriStatsCurrentTrunkEntry OBJECT-TYPE
       SYNTAX AcKpiBriStatsCurrentTrunkEntry
       MAX-ACCESS not-accessible
       STATUS current
       DESCRIPTION
           ""
       INDEX {acKpiBriStatsCurrentTrunkIndex}
       ::= {acKpiBriStatsCurrentTrunkTable 1}



     -- ****************************************
     -- acKpiBriStatsCurrentTrunk TABLE
     -- ****************************************
     AcKpiBriStatsCurrentTrunkEntry ::= SEQUENCE {
       acKpiBriStatsCurrentTrunkIndex                  Unsigned32,
       acKpiBriStatsCurrentTrunkLofSecondsCurrent      Counter64,
       acKpiBriStatsCurrentTrunkHdlcCrcErrorsCurrent   Counter64,
       acKpiBriStatsCurrentTrunkCodeViolationSecondsCurrent 
                                                       Counter64,
       acKpiBriStatsCurrentTrunkCodeViolationsCurrent  Counter64,
       acKpiBriStatsCurrentTrunkSlipSecondsCurrent     Counter64,
       acKpiBriStatsCurrentTrunkSlipsCurrent           Counter64,
       acKpiBriStatsCurrentTrunkLofEventsCurrent       Counter64
     }



     acKpiBriStatsCurrentTrunkIndex OBJECT-TYPE
       SYNTAX Unsigned32 (0..32767)
       MAX-ACCESS not-accessible
       STATUS current
       DESCRIPTION
           "
AC INI-Param: N/A"
       ::= {acKpiBriStatsCurrentTrunkEntry 1}



     acKpiBriStatsCurrentTrunkLofSecondsCurrent OBJECT-TYPE
       SYNTAX Counter64
       MAX-ACCESS read-only
       STATUS obsolete
       DESCRIPTION
           "Current number of loss of frame (LOF) seconds.
AC INI-Param: N/A"
       ::= {acKpiBriStatsCurrentTrunkEntry 2}



     acKpiBriStatsCurrentTrunkHdlcCrcErrorsCurrent OBJECT-TYPE
       SYNTAX Counter64
       MAX-ACCESS read-only
       STATUS current
       DESCRIPTION
           "Current number of HDLC CRC errors.
AC INI-Param: N/A"
       ::= {acKpiBriStatsCurrentTrunkEntry 3}



     acKpiBriStatsCurrentTrunkCodeViolationSecondsCurrent OBJECT-TYPE
       SYNTAX Counter64
       MAX-ACCESS read-only
       STATUS current
       DESCRIPTION
           "Current number of code violation seconds.
AC INI-Param: N/A"
       ::= {acKpiBriStatsCurrentTrunkEntry 4}



     acKpiBriStatsCurrentTrunkCodeViolationsCurrent OBJECT-TYPE
       SYNTAX Counter64
       MAX-ACCESS read-only
       STATUS current
       DESCRIPTION
           "Current number of code violations.
AC INI-Param: N/A"
       ::= {acKpiBriStatsCurrentTrunkEntry 5}



     acKpiBriStatsCurrentTrunkSlipSecondsCurrent OBJECT-TYPE
       SYNTAX Counter64
       MAX-ACCESS read-only
       STATUS current
       DESCRIPTION
           "Current number of slip seconds.
AC INI-Param: N/A"
       ::= {acKpiBriStatsCurrentTrunkEntry 6}



     acKpiBriStatsCurrentTrunkSlipsCurrent OBJECT-TYPE
       SYNTAX Counter64
       MAX-ACCESS read-only
       STATUS current
       DESCRIPTION
           "Current number of slip events.
AC INI-Param: N/A"
       ::= {acKpiBriStatsCurrentTrunkEntry 7}



     acKpiBriStatsCurrentTrunkLofEventsCurrent OBJECT-TYPE
       SYNTAX Counter64
       MAX-ACCESS read-only
       STATUS current
       DESCRIPTION
           "Current number of loss of frame (LOF) events.
AC INI-Param: N/A"
       ::= {acKpiBriStatsCurrentTrunkEntry 8}



     acKpiBriStatsInterval OBJECT IDENTIFIER ::= {acKpiBriStats 2}


     acKpiBriStatsIntervalGlobal OBJECT IDENTIFIER ::= {acKpiBriStatsInterval 1}


     acKpiBriStatsIntervalTables OBJECT IDENTIFIER ::= {acKpiBriStatsInterval 2}


     -- ****************************************
     -- acKpiBriStatsIntervalTrunk table declaration
     -- ****************************************
     acKpiBriStatsIntervalTrunkTable OBJECT-TYPE
       SYNTAX SEQUENCE OF AcKpiBriStatsIntervalTrunkEntry
       MAX-ACCESS not-accessible
       STATUS current
       DESCRIPTION
           ""
       ::= {acKpiBriStatsIntervalTables 1}



     -- ****************************************
     -- acKpiBriStatsIntervalTrunk table entry
     -- ****************************************
     acKpiBriStatsIntervalTrunkEntry OBJECT-TYPE
       SYNTAX AcKpiBriStatsIntervalTrunkEntry
       MAX-ACCESS not-accessible
       STATUS current
       DESCRIPTION
           ""
       INDEX {acKpiBriStatsIntervalTrunkIndex,acKpiBriStatsIntervalTrunkInterval}
       ::= {acKpiBriStatsIntervalTrunkTable 1}



     -- ****************************************
     -- acKpiBriStatsIntervalTrunk TABLE
     -- ****************************************
     AcKpiBriStatsIntervalTrunkEntry ::= SEQUENCE {
       acKpiBriStatsIntervalTrunkIndex                 Unsigned32,
       acKpiBriStatsIntervalTrunkInterval              Unsigned32,
       acKpiBriStatsIntervalTrunkSlips                 Counter64,
       acKpiBriStatsIntervalTrunkSlipSeconds           Counter64,
       acKpiBriStatsIntervalTrunkCodeViolations        Counter64,
       acKpiBriStatsIntervalTrunkCodeViolationSeconds  Counter64,
       acKpiBriStatsIntervalTrunkHdlcCrcErrors         Counter64,
       acKpiBriStatsIntervalTrunkLofSeconds            Counter64,
       acKpiBriStatsIntervalTrunkLofEvents             Counter64
     }



     acKpiBriStatsIntervalTrunkIndex OBJECT-TYPE
       SYNTAX Unsigned32 (0..32767)
       MAX-ACCESS not-accessible
       STATUS current
       DESCRIPTION
           "
AC INI-Param: N/A"
       ::= {acKpiBriStatsIntervalTrunkEntry 1}



     acKpiBriStatsIntervalTrunkInterval OBJECT-TYPE
       SYNTAX Unsigned32 (1..200)
       MAX-ACCESS not-accessible
       STATUS current
       DESCRIPTION
           "
AC INI-Param: N/A"
       ::= {acKpiBriStatsIntervalTrunkEntry 2}



     acKpiBriStatsIntervalTrunkSlips OBJECT-TYPE
       SYNTAX Counter64
       MAX-ACCESS read-only
       STATUS current
       DESCRIPTION
           "Number of slip events.
AC INI-Param: N/A"
       ::= {acKpiBriStatsIntervalTrunkEntry 3}



     acKpiBriStatsIntervalTrunkSlipSeconds OBJECT-TYPE
       SYNTAX Counter64
       MAX-ACCESS read-only
       STATUS current
       DESCRIPTION
           "Number of slip seconds.
AC INI-Param: N/A"
       ::= {acKpiBriStatsIntervalTrunkEntry 4}



     acKpiBriStatsIntervalTrunkCodeViolations OBJECT-TYPE
       SYNTAX Counter64
       MAX-ACCESS read-only
       STATUS current
       DESCRIPTION
           "Number of code violations.
AC INI-Param: N/A"
       ::= {acKpiBriStatsIntervalTrunkEntry 5}



     acKpiBriStatsIntervalTrunkCodeViolationSeconds OBJECT-TYPE
       SYNTAX Counter64
       MAX-ACCESS read-only
       STATUS current
       DESCRIPTION
           "Number of code violation seconds.
AC INI-Param: N/A"
       ::= {acKpiBriStatsIntervalTrunkEntry 6}



     acKpiBriStatsIntervalTrunkHdlcCrcErrors OBJECT-TYPE
       SYNTAX Counter64
       MAX-ACCESS read-only
       STATUS current
       DESCRIPTION
           "Number of HDLC CRC errors.
AC INI-Param: N/A"
       ::= {acKpiBriStatsIntervalTrunkEntry 7}



     acKpiBriStatsIntervalTrunkLofSeconds OBJECT-TYPE
       SYNTAX Counter64
       MAX-ACCESS read-only
       STATUS obsolete
       DESCRIPTION
           "Number of loss of frame (LOF) seconds.
AC INI-Param: N/A"
       ::= {acKpiBriStatsIntervalTrunkEntry 8}



     acKpiBriStatsIntervalTrunkLofEvents OBJECT-TYPE
       SYNTAX Counter64
       MAX-ACCESS read-only
       STATUS current
       DESCRIPTION
           "Number of loss of frame (LOF) events.
AC INI-Param: N/A"
       ::= {acKpiBriStatsIntervalTrunkEntry 9}



     acKpiGatewayOtherStats OBJECT IDENTIFIER ::= {acKpiGateway 6}


     acKpiGatewayOtherStatsCurrent OBJECT IDENTIFIER ::= {acKpiGatewayOtherStats 1}


     acKpiGatewayOtherStatsCurrentGlobal OBJECT IDENTIFIER ::= {acKpiGatewayOtherStatsCurrent 1}


     acKpiGatewayOtherStatsCurrentGlobalTransactionRate OBJECT-TYPE
       SYNTAX Gauge32
       MAX-ACCESS read-only
       STATUS current
       DESCRIPTION
           "SIP transactions rate (transactions per second).
AC INI-Param: N/A"
       ::= {acKpiGatewayOtherStatsCurrentGlobal 1}



     acKpiGatewayOtherStatsInterval OBJECT IDENTIFIER ::= {acKpiGatewayOtherStats 2}


     acKpiGatewayOtherStatsIntervalGlobal OBJECT IDENTIFIER ::= {acKpiGatewayOtherStatsInterval 1}


     -- ****************************************
     -- acKpiGatewayOtherStatsIntervalGlobal table declaration
     -- ****************************************
     acKpiGatewayOtherStatsIntervalGlobalTable OBJECT-TYPE
       SYNTAX SEQUENCE OF AcKpiGatewayOtherStatsIntervalGlobalEntry
       MAX-ACCESS not-accessible
       STATUS current
       DESCRIPTION
           ""
       ::= {acKpiGatewayOtherStatsIntervalGlobal 1}



     -- ****************************************
     -- acKpiGatewayOtherStatsIntervalGlobal table entry
     -- ****************************************
     acKpiGatewayOtherStatsIntervalGlobalEntry OBJECT-TYPE
       SYNTAX AcKpiGatewayOtherStatsIntervalGlobalEntry
       MAX-ACCESS not-accessible
       STATUS current
       DESCRIPTION
           ""
       INDEX {acKpiGatewayOtherStatsIntervalGlobalInterval}
       ::= {acKpiGatewayOtherStatsIntervalGlobalTable 1}



     -- ****************************************
     -- acKpiGatewayOtherStatsIntervalGlobal TABLE
     -- ****************************************
     AcKpiGatewayOtherStatsIntervalGlobalEntry ::= SEQUENCE {
       acKpiGatewayOtherStatsIntervalGlobalInterval    Unsigned32,
       acKpiGatewayOtherStatsIntervalGlobalTransactionRateMax 
                                                       Gauge32,
       acKpiGatewayOtherStatsIntervalGlobalTransactionRateAvg 
                                                       Gauge32
     }



     acKpiGatewayOtherStatsIntervalGlobalInterval OBJECT-TYPE
       SYNTAX Unsigned32 (1..200)
       MAX-ACCESS not-accessible
       STATUS current
       DESCRIPTION
           "
AC INI-Param: N/A"
       ::= {acKpiGatewayOtherStatsIntervalGlobalEntry 1}



     acKpiGatewayOtherStatsIntervalGlobalTransactionRateMax OBJECT-TYPE
       SYNTAX Gauge32
       MAX-ACCESS read-only
       STATUS current
       DESCRIPTION
           "Maximum SIP transactions rate (transactions per second).
AC INI-Param: N/A"
       ::= {acKpiGatewayOtherStatsIntervalGlobalEntry 2}



     acKpiGatewayOtherStatsIntervalGlobalTransactionRateAvg OBJECT-TYPE
       SYNTAX Gauge32
       MAX-ACCESS read-only
       STATUS current
       DESCRIPTION
           "Average SIP transactions rate (transactions per second).
AC INI-Param: N/A"
       ::= {acKpiGatewayOtherStatsIntervalGlobalEntry 3}



     acKpiMedia OBJECT IDENTIFIER ::= {acKpi 5}


     acKpiDspStats OBJECT IDENTIFIER ::= {acKpiMedia 3}


     acKpiDspStatsCurrent OBJECT IDENTIFIER ::= {acKpiDspStats 1}


     acKpiDspStatsCurrentGlobal OBJECT IDENTIFIER ::= {acKpiDspStatsCurrent 1}


     acKpiDspStatsCurrentGlobalDspResourceCurrentPercent OBJECT-TYPE
       SYNTAX Gauge32
       MAX-ACCESS read-only
       STATUS current
       DESCRIPTION
           "Percentage of DSP resources currently used.
AC INI-Param: N/A"
       ::= {acKpiDspStatsCurrentGlobal 1}



     acKpiDspStatsCurrentGlobalSbcSessionsCoderTranscoding OBJECT-TYPE
       SYNTAX Gauge32
       MAX-ACCESS read-only
       STATUS current
       DESCRIPTION
           "Number of SBC transcoding sessions.
AC INI-Param: N/A"
       ::= {acKpiDspStatsCurrentGlobal 2}



     acKpiDspStatsCurrentGlobalSbcTranscodingFailedAllocationTotal OBJECT-TYPE
       SYNTAX Counter64
       MAX-ACCESS read-only
       STATUS current
       DESCRIPTION
           "Total number of failed transcoding resource allocations.
AC INI-Param: N/A"
       ::= {acKpiDspStatsCurrentGlobal 3}



     acKpiDspStatsCurrentGlobalSbcSessionsCoderTranscodingPercent OBJECT-TYPE
       SYNTAX Gauge32
       MAX-ACCESS read-only
       STATUS current
       DESCRIPTION
           "Percentage of SBC transcoding sessions (from all sessions).
AC INI-Param: N/A"
       ::= {acKpiDspStatsCurrentGlobal 4}



     acKpiDspStatsInterval OBJECT IDENTIFIER ::= {acKpiDspStats 2}


     acKpiDspStatsIntervalGlobal OBJECT IDENTIFIER ::= {acKpiDspStatsInterval 1}


     -- ****************************************
     -- acKpiDspStatsIntervalGlobal table declaration
     -- ****************************************
     acKpiDspStatsIntervalGlobalTable OBJECT-TYPE
       SYNTAX SEQUENCE OF AcKpiDspStatsIntervalGlobalEntry
       MAX-ACCESS not-accessible
       STATUS current
       DESCRIPTION
           ""
       ::= {acKpiDspStatsIntervalGlobal 1}



     -- ****************************************
     -- acKpiDspStatsIntervalGlobal table entry
     -- ****************************************
     acKpiDspStatsIntervalGlobalEntry OBJECT-TYPE
       SYNTAX AcKpiDspStatsIntervalGlobalEntry
       MAX-ACCESS not-accessible
       STATUS current
       DESCRIPTION
           ""
       INDEX {acKpiDspStatsIntervalGlobalInterval}
       ::= {acKpiDspStatsIntervalGlobalTable 1}



     -- ****************************************
     -- acKpiDspStatsIntervalGlobal TABLE
     -- ****************************************
     AcKpiDspStatsIntervalGlobalEntry ::= SEQUENCE {
       acKpiDspStatsIntervalGlobalInterval             Unsigned32,
       acKpiDspStatsIntervalGlobalDspResourceCurrentPercentAvg 
                                                       Gauge32,
       acKpiDspStatsIntervalGlobalDspResourceCurrentPercentMax 
                                                       Gauge32,
       acKpiDspStatsIntervalGlobalSbcSessionsCoderTranscodingAvg 
                                                       Gauge32,
       acKpiDspStatsIntervalGlobalSbcSessionsCoderTranscodingMax 
                                                       Gauge32,
       acKpiDspStatsIntervalGlobalSbcTranscodingFailedAllocation 
                                                       Counter64,
       acKpiDspStatsIntervalGlobalSbcSessionsCoderTranscodingPercentMax 
                                                       Gauge32,
       acKpiDspStatsIntervalGlobalSbcSessionsCoderTranscodingPercentAvg 
                                                       Gauge32
     }



     acKpiDspStatsIntervalGlobalInterval OBJECT-TYPE
       SYNTAX Unsigned32 (1..200)
       MAX-ACCESS not-accessible
       STATUS current
       DESCRIPTION
           "
AC INI-Param: N/A"
       ::= {acKpiDspStatsIntervalGlobalEntry 1}



     acKpiDspStatsIntervalGlobalDspResourceCurrentPercentAvg OBJECT-TYPE
       SYNTAX Gauge32
       MAX-ACCESS read-only
       STATUS current
       DESCRIPTION
           "Average percentage of DSP resources currently used.
AC INI-Param: N/A"
       ::= {acKpiDspStatsIntervalGlobalEntry 2}



     acKpiDspStatsIntervalGlobalDspResourceCurrentPercentMax OBJECT-TYPE
       SYNTAX Gauge32
       MAX-ACCESS read-only
       STATUS current
       DESCRIPTION
           "Maximum percentage of DSP resources currently used.
AC INI-Param: N/A"
       ::= {acKpiDspStatsIntervalGlobalEntry 3}



     acKpiDspStatsIntervalGlobalSbcSessionsCoderTranscodingAvg OBJECT-TYPE
       SYNTAX Gauge32
       MAX-ACCESS read-only
       STATUS current
       DESCRIPTION
           "Average number of SBC transcoding sessions.
AC INI-Param: N/A"
       ::= {acKpiDspStatsIntervalGlobalEntry 4}



     acKpiDspStatsIntervalGlobalSbcSessionsCoderTranscodingMax OBJECT-TYPE
       SYNTAX Gauge32
       MAX-ACCESS read-only
       STATUS current
       DESCRIPTION
           "Maximum number of SBC transcoding sessions.
AC INI-Param: N/A"
       ::= {acKpiDspStatsIntervalGlobalEntry 5}



     acKpiDspStatsIntervalGlobalSbcTranscodingFailedAllocation OBJECT-TYPE
       SYNTAX Counter64
       MAX-ACCESS read-only
       STATUS current
       DESCRIPTION
           "Number of failed transcoding resource allocations.
AC INI-Param: N/A"
       ::= {acKpiDspStatsIntervalGlobalEntry 6}



     acKpiDspStatsIntervalGlobalSbcSessionsCoderTranscodingPercentMax OBJECT-TYPE
       SYNTAX Gauge32
       MAX-ACCESS read-only
       STATUS current
       DESCRIPTION
           "Maximum percentage of SBC transcoding sessions (from all sessions).
AC INI-Param: N/A"
       ::= {acKpiDspStatsIntervalGlobalEntry 7}



     acKpiDspStatsIntervalGlobalSbcSessionsCoderTranscodingPercentAvg OBJECT-TYPE
       SYNTAX Gauge32
       MAX-ACCESS read-only
       STATUS current
       DESCRIPTION
           "Average percentage of SBC transcoding sessions (from all sessions).
AC INI-Param: N/A"
       ::= {acKpiDspStatsIntervalGlobalEntry 8}



     acKpiClusterStats OBJECT IDENTIFIER ::= {acKpiMedia 4}


     acKpiClusterStatsCurrent OBJECT IDENTIFIER ::= {acKpiClusterStats 1}


     acKpiClusterStatsCurrentGlobal OBJECT IDENTIFIER ::= {acKpiClusterStatsCurrent 1}


     acKpiClusterStatsCurrentGlobalMediaClusterUtilization OBJECT-TYPE
       SYNTAX Gauge32
       MAX-ACCESS read-only
       STATUS current
       DESCRIPTION
           "Utilization of media resources in decomposed SBC architecture.
AC INI-Param: N/A"
       ::= {acKpiClusterStatsCurrentGlobal 1}



     acKpiClusterStatsCurrentGlobalDspClusterUtilization OBJECT-TYPE
       SYNTAX Gauge32
       MAX-ACCESS read-only
       STATUS current
       DESCRIPTION
           "Utilization of DSP resources in decomposed SBC architecture.
AC INI-Param: N/A"
       ::= {acKpiClusterStatsCurrentGlobal 2}



     acKpiClusterStatsInterval OBJECT IDENTIFIER ::= {acKpiClusterStats 2}


     acKpiClusterStatsIntervalGlobal OBJECT IDENTIFIER ::= {acKpiClusterStatsInterval 1}


     -- ****************************************
     -- acKpiClusterStatsIntervalGlobal table declaration
     -- ****************************************
     acKpiClusterStatsIntervalGlobalTable OBJECT-TYPE
       SYNTAX SEQUENCE OF AcKpiClusterStatsIntervalGlobalEntry
       MAX-ACCESS not-accessible
       STATUS current
       DESCRIPTION
           ""
       ::= {acKpiClusterStatsIntervalGlobal 1}



     -- ****************************************
     -- acKpiClusterStatsIntervalGlobal table entry
     -- ****************************************
     acKpiClusterStatsIntervalGlobalEntry OBJECT-TYPE
       SYNTAX AcKpiClusterStatsIntervalGlobalEntry
       MAX-ACCESS not-accessible
       STATUS current
       DESCRIPTION
           ""
       INDEX {acKpiClusterStatsIntervalGlobalInterval}
       ::= {acKpiClusterStatsIntervalGlobalTable 1}



     -- ****************************************
     -- acKpiClusterStatsIntervalGlobal TABLE
     -- ****************************************
     AcKpiClusterStatsIntervalGlobalEntry ::= SEQUENCE {
       acKpiClusterStatsIntervalGlobalInterval         Unsigned32,
       acKpiClusterStatsIntervalGlobalMediaClusterUtilizationAvg 
                                                       Gauge32,
       acKpiClusterStatsIntervalGlobalMediaClusterUtilizationMax 
                                                       Gauge32,
       acKpiClusterStatsIntervalGlobalDspClusterUtilizationAvg 
                                                       Gauge32,
       acKpiClusterStatsIntervalGlobalDspClusterUtilizationMax 
                                                       Gauge32
     }



     acKpiClusterStatsIntervalGlobalInterval OBJECT-TYPE
       SYNTAX Unsigned32 (1..200)
       MAX-ACCESS not-accessible
       STATUS current
       DESCRIPTION
           "
AC INI-Param: N/A"
       ::= {acKpiClusterStatsIntervalGlobalEntry 1}



     acKpiClusterStatsIntervalGlobalMediaClusterUtilizationAvg OBJECT-TYPE
       SYNTAX Gauge32
       MAX-ACCESS read-only
       STATUS current
       DESCRIPTION
           "Average utilization of media resources in decomposed SBC architecture.
AC INI-Param: N/A"
       ::= {acKpiClusterStatsIntervalGlobalEntry 2}



     acKpiClusterStatsIntervalGlobalMediaClusterUtilizationMax OBJECT-TYPE
       SYNTAX Gauge32
       MAX-ACCESS read-only
       STATUS current
       DESCRIPTION
           "Maximum utilization of media resources in decomposed SBC architecture.
AC INI-Param: N/A"
       ::= {acKpiClusterStatsIntervalGlobalEntry 3}



     acKpiClusterStatsIntervalGlobalDspClusterUtilizationAvg OBJECT-TYPE
       SYNTAX Gauge32
       MAX-ACCESS read-only
       STATUS current
       DESCRIPTION
           "Average utilization of DSP resources in decomposed SBC architecture.
AC INI-Param: N/A"
       ::= {acKpiClusterStatsIntervalGlobalEntry 4}



     acKpiClusterStatsIntervalGlobalDspClusterUtilizationMax OBJECT-TYPE
       SYNTAX Gauge32
       MAX-ACCESS read-only
       STATUS current
       DESCRIPTION
           "Maximum utilization of DSP resources in decomposed SBC architecture.
AC INI-Param: N/A"
       ::= {acKpiClusterStatsIntervalGlobalEntry 5}



     acKpiMediaStats OBJECT IDENTIFIER ::= {acKpiMedia 1}


     acKpiMediaStatsCurrent OBJECT IDENTIFIER ::= {acKpiMediaStats 1}


     acKpiMediaStatsCurrentGlobal OBJECT IDENTIFIER ::= {acKpiMediaStatsCurrent 1}


     acKpiMediaStatsCurrentGlobalMediaPacketsInTotal OBJECT-TYPE
       SYNTAX Counter64
       MAX-ACCESS read-only
       STATUS current
       DESCRIPTION
           "Total number of received media packets.
AC INI-Param: N/A"
       ::= {acKpiMediaStatsCurrentGlobal 1}



     acKpiMediaStatsCurrentGlobalMediaPacketsOutTotal OBJECT-TYPE
       SYNTAX Counter64
       MAX-ACCESS read-only
       STATUS current
       DESCRIPTION
           "Total number of transmitted media packets.
AC INI-Param: N/A"
       ::= {acKpiMediaStatsCurrentGlobal 2}



     acKpiMediaStatsCurrentGlobalMediaKBytesInTotal OBJECT-TYPE
       SYNTAX Counter64
       MAX-ACCESS read-only
       STATUS current
       DESCRIPTION
           "Total amount of inbound media traffic (KBytes).
AC INI-Param: N/A"
       ::= {acKpiMediaStatsCurrentGlobal 3}



     acKpiMediaStatsCurrentGlobalMediaKBytesOutTotal OBJECT-TYPE
       SYNTAX Counter64
       MAX-ACCESS read-only
       STATUS current
       DESCRIPTION
           "Total amount of outbound media traffic (KBytes).
AC INI-Param: N/A"
       ::= {acKpiMediaStatsCurrentGlobal 4}



     acKpiMediaStatsCurrentGlobalMediaBandwidthIn OBJECT-TYPE
       SYNTAX Gauge32
       MAX-ACCESS read-only
       STATUS current
       DESCRIPTION
           "Inbound media bandwidth (Kbits per sec).
AC INI-Param: N/A"
       ::= {acKpiMediaStatsCurrentGlobal 5}



     acKpiMediaStatsCurrentGlobalMediaBandwidthOut OBJECT-TYPE
       SYNTAX Gauge32
       MAX-ACCESS read-only
       STATUS current
       DESCRIPTION
           "Outbound media bandwidth (Kbits per sec).
AC INI-Param: N/A"
       ::= {acKpiMediaStatsCurrentGlobal 6}



     acKpiMediaStatsCurrentGlobalMediaPacketLossIn OBJECT-TYPE
       SYNTAX Gauge32
       MAX-ACCESS read-only
       STATUS current
       DESCRIPTION
           "Inbound media packet loss [%].
AC INI-Param: N/A"
       ::= {acKpiMediaStatsCurrentGlobal 7}



     acKpiMediaStatsCurrentGlobalMediaPacketLossOut OBJECT-TYPE
       SYNTAX Gauge32
       MAX-ACCESS read-only
       STATUS current
       DESCRIPTION
           "Outbound media packet loss [%].
AC INI-Param: N/A"
       ::= {acKpiMediaStatsCurrentGlobal 8}



     acKpiMediaStatsCurrentGlobalMediaJitterIn OBJECT-TYPE
       SYNTAX Gauge32
       MAX-ACCESS read-only
       STATUS current
       DESCRIPTION
           "Inbound media jitter (msec).
AC INI-Param: N/A"
       ::= {acKpiMediaStatsCurrentGlobal 9}



     acKpiMediaStatsCurrentGlobalMediaJitterOut OBJECT-TYPE
       SYNTAX Gauge32
       MAX-ACCESS read-only
       STATUS current
       DESCRIPTION
           "Outbound media jitter (msec).
AC INI-Param: N/A"
       ::= {acKpiMediaStatsCurrentGlobal 10}



     acKpiMediaStatsCurrentGlobalMediaDelayIn OBJECT-TYPE
       SYNTAX Gauge32
       MAX-ACCESS read-only
       STATUS current
       DESCRIPTION
           "Inbound media delay (msec).
AC INI-Param: N/A"
       ::= {acKpiMediaStatsCurrentGlobal 11}



     acKpiMediaStatsCurrentGlobalMediaDelayOut OBJECT-TYPE
       SYNTAX Gauge32
       MAX-ACCESS read-only
       STATUS current
       DESCRIPTION
           "Outbound media delay (msec).
AC INI-Param: N/A"
       ::= {acKpiMediaStatsCurrentGlobal 12}



     acKpiMediaStatsCurrentGlobalMediaMOSIn OBJECT-TYPE
       SYNTAX Gauge32
       MAX-ACCESS read-only
       STATUS current
       DESCRIPTION
           "Inbound media Mean Opinion Score (MOS, 0.1 units) on a scale
of 10-50.
AC INI-Param: N/A"
       ::= {acKpiMediaStatsCurrentGlobal 13}



     acKpiMediaStatsCurrentGlobalMediaMOSOut OBJECT-TYPE
       SYNTAX Gauge32
       MAX-ACCESS read-only
       STATUS current
       DESCRIPTION
           "Outbound media Mean Opinion Score (MOS, 0.1 units) on a scale
of 10-50.
AC INI-Param: N/A"
       ::= {acKpiMediaStatsCurrentGlobal 14}



     acKpiMediaStatsCurrentGlobalMediaQualityIn OBJECT-TYPE
       SYNTAX Gauge32
       MAX-ACCESS read-only
       STATUS current
       DESCRIPTION
           "Inbound media quality (0: Red, 1: Yellow, 2: Green).
AC INI-Param: N/A"
       ::= {acKpiMediaStatsCurrentGlobal 15}



     acKpiMediaStatsCurrentGlobalMediaQualityOut OBJECT-TYPE
       SYNTAX Gauge32
       MAX-ACCESS read-only
       STATUS current
       DESCRIPTION
           "Outbound media quality (0: Red, 1: Yellow, 2: Green).
AC INI-Param: N/A"
       ::= {acKpiMediaStatsCurrentGlobal 16}



     acKpiMediaStatsCurrentGlobalMediaStreams OBJECT-TYPE
       SYNTAX Gauge32
       MAX-ACCESS read-only
       STATUS current
       DESCRIPTION
           "Number of media streams (legs).
AC INI-Param: N/A"
       ::= {acKpiMediaStatsCurrentGlobal 17}



     acKpiMediaStatsCurrentGlobalMediaRtpStreams OBJECT-TYPE
       SYNTAX Gauge32
       MAX-ACCESS read-only
       STATUS current
       DESCRIPTION
           "Number of media RTP streams (legs).
AC INI-Param: N/A"
       ::= {acKpiMediaStatsCurrentGlobal 18}



     acKpiMediaStatsCurrentGlobalMediaSrtpStreams OBJECT-TYPE
       SYNTAX Gauge32
       MAX-ACCESS read-only
       STATUS current
       DESCRIPTION
           "Number of media SRTP streams (legs).
AC INI-Param: N/A"
       ::= {acKpiMediaStatsCurrentGlobal 19}



     acKpiMediaStatsCurrentGlobalMediaSipRecStreams OBJECT-TYPE
       SYNTAX Gauge32
       MAX-ACCESS read-only
       STATUS current
       DESCRIPTION
           "Number of media SIP-REC streams (legs).
AC INI-Param: N/A"
       ::= {acKpiMediaStatsCurrentGlobal 20}



     acKpiMediaStatsCurrentGlobalMediaWebRTCStreams OBJECT-TYPE
       SYNTAX Gauge32
       MAX-ACCESS read-only
       STATUS current
       DESCRIPTION
           "Number of media WebRTC streams (legs).
AC INI-Param: N/A"
       ::= {acKpiMediaStatsCurrentGlobal 21}



     acKpiMediaStatsCurrentTables OBJECT IDENTIFIER ::= {acKpiMediaStatsCurrent 2}


     -- ****************************************
     -- acKpiMediaStatsCurrentIpGroup table declaration
     -- ****************************************
     acKpiMediaStatsCurrentIpGroupTable OBJECT-TYPE
       SYNTAX SEQUENCE OF AcKpiMediaStatsCurrentIpGroupEntry
       MAX-ACCESS not-accessible
       STATUS current
       DESCRIPTION
           ""
       ::= {acKpiMediaStatsCurrentTables 1}



     -- ****************************************
     -- acKpiMediaStatsCurrentIpGroup table entry
     -- ****************************************
     acKpiMediaStatsCurrentIpGroupEntry OBJECT-TYPE
       SYNTAX AcKpiMediaStatsCurrentIpGroupEntry
       MAX-ACCESS not-accessible
       STATUS current
       DESCRIPTION
           ""
       INDEX {acKpiMediaStatsCurrentIpGroupIndex}
       ::= {acKpiMediaStatsCurrentIpGroupTable 1}



     -- ****************************************
     -- acKpiMediaStatsCurrentIpGroup TABLE
     -- ****************************************
     AcKpiMediaStatsCurrentIpGroupEntry ::= SEQUENCE {
       acKpiMediaStatsCurrentIpGroupIndex              Unsigned32,
       acKpiMediaStatsCurrentIpGroupMediaPacketsInTotal 
                                                       Counter64,
       acKpiMediaStatsCurrentIpGroupMediaPacketsOutTotal 
                                                       Counter64,
       acKpiMediaStatsCurrentIpGroupMediaKBytesInTotal Counter64,
       acKpiMediaStatsCurrentIpGroupMediaKBytesOutTotal 
                                                       Counter64,
       acKpiMediaStatsCurrentIpGroupMediaBandwidthIn   Gauge32,
       acKpiMediaStatsCurrentIpGroupMediaBandwidthOut  Gauge32,
       acKpiMediaStatsCurrentIpGroupMediaPacketLossIn  Gauge32,
       acKpiMediaStatsCurrentIpGroupMediaPacketLossOut Gauge32,
       acKpiMediaStatsCurrentIpGroupMediaJitterIn      Gauge32,
       acKpiMediaStatsCurrentIpGroupMediaJitterOut     Gauge32,
       acKpiMediaStatsCurrentIpGroupMediaDelayIn       Gauge32,
       acKpiMediaStatsCurrentIpGroupMediaDelayOut      Gauge32,
       acKpiMediaStatsCurrentIpGroupMediaMOSIn         Gauge32,
       acKpiMediaStatsCurrentIpGroupMediaMOSOut        Gauge32,
       acKpiMediaStatsCurrentIpGroupMediaQualityIn     Gauge32,
       acKpiMediaStatsCurrentIpGroupMediaQualityOut    Gauge32,
       acKpiMediaStatsCurrentIpGroupMediaStreams       Gauge32,
       acKpiMediaStatsCurrentIpGroupMediaRtpStreams    Gauge32,
       acKpiMediaStatsCurrentIpGroupMediaSrtpStreams   Gauge32,
       acKpiMediaStatsCurrentIpGroupMediaSipRecStreams Gauge32,
       acKpiMediaStatsCurrentIpGroupMediaWebRTCStreams Gauge32
     }



     acKpiMediaStatsCurrentIpGroupIndex OBJECT-TYPE
       SYNTAX Unsigned32 (0..32767)
       MAX-ACCESS not-accessible
       STATUS current
       DESCRIPTION
           "
AC INI-Param: N/A"
       ::= {acKpiMediaStatsCurrentIpGroupEntry 1}



     acKpiMediaStatsCurrentIpGroupMediaPacketsInTotal OBJECT-TYPE
       SYNTAX Counter64
       MAX-ACCESS read-only
       STATUS current
       DESCRIPTION
           "Total number of received media packets.
AC INI-Param: N/A"
       ::= {acKpiMediaStatsCurrentIpGroupEntry 2}



     acKpiMediaStatsCurrentIpGroupMediaPacketsOutTotal OBJECT-TYPE
       SYNTAX Counter64
       MAX-ACCESS read-only
       STATUS current
       DESCRIPTION
           "Total number of transmitted media packets.
AC INI-Param: N/A"
       ::= {acKpiMediaStatsCurrentIpGroupEntry 3}



     acKpiMediaStatsCurrentIpGroupMediaKBytesInTotal OBJECT-TYPE
       SYNTAX Counter64
       MAX-ACCESS read-only
       STATUS current
       DESCRIPTION
           "Total amount of inbound media traffic (KBytes).
AC INI-Param: N/A"
       ::= {acKpiMediaStatsCurrentIpGroupEntry 4}



     acKpiMediaStatsCurrentIpGroupMediaKBytesOutTotal OBJECT-TYPE
       SYNTAX Counter64
       MAX-ACCESS read-only
       STATUS current
       DESCRIPTION
           "Total amount of outbound media traffic (KBytes).
AC INI-Param: N/A"
       ::= {acKpiMediaStatsCurrentIpGroupEntry 5}



     acKpiMediaStatsCurrentIpGroupMediaBandwidthIn OBJECT-TYPE
       SYNTAX Gauge32
       MAX-ACCESS read-only
       STATUS current
       DESCRIPTION
           "Inbound media bandwidth (Kbits per sec).
AC INI-Param: N/A"
       ::= {acKpiMediaStatsCurrentIpGroupEntry 6}



     acKpiMediaStatsCurrentIpGroupMediaBandwidthOut OBJECT-TYPE
       SYNTAX Gauge32
       MAX-ACCESS read-only
       STATUS current
       DESCRIPTION
           "Outbound media bandwidth (Kbits per sec).
AC INI-Param: N/A"
       ::= {acKpiMediaStatsCurrentIpGroupEntry 7}



     acKpiMediaStatsCurrentIpGroupMediaPacketLossIn OBJECT-TYPE
       SYNTAX Gauge32
       MAX-ACCESS read-only
       STATUS current
       DESCRIPTION
           "Inbound media packet loss [%].
AC INI-Param: N/A"
       ::= {acKpiMediaStatsCurrentIpGroupEntry 8}



     acKpiMediaStatsCurrentIpGroupMediaPacketLossOut OBJECT-TYPE
       SYNTAX Gauge32
       MAX-ACCESS read-only
       STATUS current
       DESCRIPTION
           "Outbound media packet loss [%].
AC INI-Param: N/A"
       ::= {acKpiMediaStatsCurrentIpGroupEntry 9}



     acKpiMediaStatsCurrentIpGroupMediaJitterIn OBJECT-TYPE
       SYNTAX Gauge32
       MAX-ACCESS read-only
       STATUS current
       DESCRIPTION
           "Inbound media jitter (msec).
AC INI-Param: N/A"
       ::= {acKpiMediaStatsCurrentIpGroupEntry 10}



     acKpiMediaStatsCurrentIpGroupMediaJitterOut OBJECT-TYPE
       SYNTAX Gauge32
       MAX-ACCESS read-only
       STATUS current
       DESCRIPTION
           "Outbound media jitter (msec).
AC INI-Param: N/A"
       ::= {acKpiMediaStatsCurrentIpGroupEntry 11}



     acKpiMediaStatsCurrentIpGroupMediaDelayIn OBJECT-TYPE
       SYNTAX Gauge32
       MAX-ACCESS read-only
       STATUS current
       DESCRIPTION
           "Inbound media delay (msec).
AC INI-Param: N/A"
       ::= {acKpiMediaStatsCurrentIpGroupEntry 12}



     acKpiMediaStatsCurrentIpGroupMediaDelayOut OBJECT-TYPE
       SYNTAX Gauge32
       MAX-ACCESS read-only
       STATUS current
       DESCRIPTION
           "Outbound media delay (msec).
AC INI-Param: N/A"
       ::= {acKpiMediaStatsCurrentIpGroupEntry 13}



     acKpiMediaStatsCurrentIpGroupMediaMOSIn OBJECT-TYPE
       SYNTAX Gauge32
       MAX-ACCESS read-only
       STATUS current
       DESCRIPTION
           "Inbound media Mean Opinion Score (MOS, 0.1 units) on a scale
of 10-50.
AC INI-Param: N/A"
       ::= {acKpiMediaStatsCurrentIpGroupEntry 14}



     acKpiMediaStatsCurrentIpGroupMediaMOSOut OBJECT-TYPE
       SYNTAX Gauge32
       MAX-ACCESS read-only
       STATUS current
       DESCRIPTION
           "Outbound media Mean Opinion Score (MOS, 0.1 units) on a scale
of 10-50.
AC INI-Param: N/A"
       ::= {acKpiMediaStatsCurrentIpGroupEntry 15}



     acKpiMediaStatsCurrentIpGroupMediaQualityIn OBJECT-TYPE
       SYNTAX Gauge32
       MAX-ACCESS read-only
       STATUS current
       DESCRIPTION
           "Inbound media quality (0: Red, 1: Yellow, 2: Green).
AC INI-Param: N/A"
       ::= {acKpiMediaStatsCurrentIpGroupEntry 16}



     acKpiMediaStatsCurrentIpGroupMediaQualityOut OBJECT-TYPE
       SYNTAX Gauge32
       MAX-ACCESS read-only
       STATUS current
       DESCRIPTION
           "Outbound media quality (0: Red, 1: Yellow, 2: Green).
AC INI-Param: N/A"
       ::= {acKpiMediaStatsCurrentIpGroupEntry 17}



     acKpiMediaStatsCurrentIpGroupMediaStreams OBJECT-TYPE
       SYNTAX Gauge32
       MAX-ACCESS read-only
       STATUS current
       DESCRIPTION
           "Number of media streams (legs).
AC INI-Param: N/A"
       ::= {acKpiMediaStatsCurrentIpGroupEntry 18}



     acKpiMediaStatsCurrentIpGroupMediaRtpStreams OBJECT-TYPE
       SYNTAX Gauge32
       MAX-ACCESS read-only
       STATUS current
       DESCRIPTION
           "Number of media RTP streams (legs).
AC INI-Param: N/A"
       ::= {acKpiMediaStatsCurrentIpGroupEntry 19}



     acKpiMediaStatsCurrentIpGroupMediaSrtpStreams OBJECT-TYPE
       SYNTAX Gauge32
       MAX-ACCESS read-only
       STATUS current
       DESCRIPTION
           "Number of media SRTP streams (legs).
AC INI-Param: N/A"
       ::= {acKpiMediaStatsCurrentIpGroupEntry 20}



     acKpiMediaStatsCurrentIpGroupMediaSipRecStreams OBJECT-TYPE
       SYNTAX Gauge32
       MAX-ACCESS read-only
       STATUS current
       DESCRIPTION
           "Number of media SIP-REC streams (legs).
AC INI-Param: N/A"
       ::= {acKpiMediaStatsCurrentIpGroupEntry 21}



     acKpiMediaStatsCurrentIpGroupMediaWebRTCStreams OBJECT-TYPE
       SYNTAX Gauge32
       MAX-ACCESS read-only
       STATUS current
       DESCRIPTION
           "Number of media WebRTC streams (legs).
AC INI-Param: N/A"
       ::= {acKpiMediaStatsCurrentIpGroupEntry 22}



     -- ****************************************
     -- acKpiMediaStatsCurrentCpMediaRealm table declaration
     -- ****************************************
     acKpiMediaStatsCurrentCpMediaRealmTable OBJECT-TYPE
       SYNTAX SEQUENCE OF AcKpiMediaStatsCurrentCpMediaRealmEntry
       MAX-ACCESS not-accessible
       STATUS obsolete
       DESCRIPTION
           ""
       ::= {acKpiMediaStatsCurrentTables 2}



     -- ****************************************
     -- acKpiMediaStatsCurrentCpMediaRealm table entry
     -- ****************************************
     acKpiMediaStatsCurrentCpMediaRealmEntry OBJECT-TYPE
       SYNTAX AcKpiMediaStatsCurrentCpMediaRealmEntry
       MAX-ACCESS not-accessible
       STATUS obsolete
       DESCRIPTION
           ""
       INDEX {acKpiMediaStatsCurrentCpMediaRealmIndex}
       ::= {acKpiMediaStatsCurrentCpMediaRealmTable 1}



     -- ****************************************
     -- acKpiMediaStatsCurrentCpMediaRealm TABLE
     -- ****************************************
     AcKpiMediaStatsCurrentCpMediaRealmEntry ::= SEQUENCE {
       acKpiMediaStatsCurrentCpMediaRealmIndex         Unsigned32,
       acKpiMediaStatsCurrentCpMediaRealmMediaPacketsInTotal 
                                                       Counter64,
       acKpiMediaStatsCurrentCpMediaRealmMediaPacketsOutTotal 
                                                       Counter64,
       acKpiMediaStatsCurrentCpMediaRealmMediaKBytesInTotal 
                                                       Counter64,
       acKpiMediaStatsCurrentCpMediaRealmMediaKBytesOutTotal 
                                                       Counter64,
       acKpiMediaStatsCurrentCpMediaRealmMediaBandwidthIn 
                                                       Gauge32,
       acKpiMediaStatsCurrentCpMediaRealmMediaBandwidthOut 
                                                       Gauge32,
       acKpiMediaStatsCurrentCpMediaRealmMediaPacketLossIn 
                                                       Gauge32,
       acKpiMediaStatsCurrentCpMediaRealmMediaPacketLossOut 
                                                       Gauge32,
       acKpiMediaStatsCurrentCpMediaRealmMediaJitterIn Gauge32,
       acKpiMediaStatsCurrentCpMediaRealmMediaJitterOut 
                                                       Gauge32,
       acKpiMediaStatsCurrentCpMediaRealmMediaDelayIn  Gauge32,
       acKpiMediaStatsCurrentCpMediaRealmMediaDelayOut Gauge32,
       acKpiMediaStatsCurrentCpMediaRealmMediaMOSIn    Gauge32,
       acKpiMediaStatsCurrentCpMediaRealmMediaMOSOut   Gauge32,
       acKpiMediaStatsCurrentCpMediaRealmMediaQualityIn 
                                                       Gauge32,
       acKpiMediaStatsCurrentCpMediaRealmMediaQualityOut 
                                                       Gauge32
     }



     acKpiMediaStatsCurrentCpMediaRealmIndex OBJECT-TYPE
       SYNTAX Unsigned32 (0..32767)
       MAX-ACCESS not-accessible
       STATUS obsolete
       DESCRIPTION
           "
AC INI-Param: N/A"
       ::= {acKpiMediaStatsCurrentCpMediaRealmEntry 1}



     acKpiMediaStatsCurrentCpMediaRealmMediaPacketsInTotal OBJECT-TYPE
       SYNTAX Counter64
       MAX-ACCESS read-only
       STATUS obsolete
       DESCRIPTION
           "Total number of received media packets.
AC INI-Param: N/A"
       ::= {acKpiMediaStatsCurrentCpMediaRealmEntry 2}



     acKpiMediaStatsCurrentCpMediaRealmMediaPacketsOutTotal OBJECT-TYPE
       SYNTAX Counter64
       MAX-ACCESS read-only
       STATUS obsolete
       DESCRIPTION
           "Total number of transmitted media packets.
AC INI-Param: N/A"
       ::= {acKpiMediaStatsCurrentCpMediaRealmEntry 3}



     acKpiMediaStatsCurrentCpMediaRealmMediaKBytesInTotal OBJECT-TYPE
       SYNTAX Counter64
       MAX-ACCESS read-only
       STATUS obsolete
       DESCRIPTION
           "Total amount of inbound media traffic (KBytes).
AC INI-Param: N/A"
       ::= {acKpiMediaStatsCurrentCpMediaRealmEntry 4}



     acKpiMediaStatsCurrentCpMediaRealmMediaKBytesOutTotal OBJECT-TYPE
       SYNTAX Counter64
       MAX-ACCESS read-only
       STATUS obsolete
       DESCRIPTION
           "Total amount of outbound media traffic (KBytes).
AC INI-Param: N/A"
       ::= {acKpiMediaStatsCurrentCpMediaRealmEntry 5}



     acKpiMediaStatsCurrentCpMediaRealmMediaBandwidthIn OBJECT-TYPE
       SYNTAX Gauge32
       MAX-ACCESS read-only
       STATUS obsolete
       DESCRIPTION
           "Inbound media bandwidth (Kbits per sec).
AC INI-Param: N/A"
       ::= {acKpiMediaStatsCurrentCpMediaRealmEntry 6}



     acKpiMediaStatsCurrentCpMediaRealmMediaBandwidthOut OBJECT-TYPE
       SYNTAX Gauge32
       MAX-ACCESS read-only
       STATUS obsolete
       DESCRIPTION
           "Outbound media bandwidth (Kbits per sec).
AC INI-Param: N/A"
       ::= {acKpiMediaStatsCurrentCpMediaRealmEntry 7}



     acKpiMediaStatsCurrentCpMediaRealmMediaPacketLossIn OBJECT-TYPE
       SYNTAX Gauge32
       MAX-ACCESS read-only
       STATUS obsolete
       DESCRIPTION
           "Inbound media packet loss (in 0.01% units).
AC INI-Param: N/A"
       ::= {acKpiMediaStatsCurrentCpMediaRealmEntry 8}



     acKpiMediaStatsCurrentCpMediaRealmMediaPacketLossOut OBJECT-TYPE
       SYNTAX Gauge32
       MAX-ACCESS read-only
       STATUS obsolete
       DESCRIPTION
           "Outbound media packet loss (in 0.01% units).
AC INI-Param: N/A"
       ::= {acKpiMediaStatsCurrentCpMediaRealmEntry 9}



     acKpiMediaStatsCurrentCpMediaRealmMediaJitterIn OBJECT-TYPE
       SYNTAX Gauge32
       MAX-ACCESS read-only
       STATUS obsolete
       DESCRIPTION
           "Inbound media jitter (msec).
AC INI-Param: N/A"
       ::= {acKpiMediaStatsCurrentCpMediaRealmEntry 10}



     acKpiMediaStatsCurrentCpMediaRealmMediaJitterOut OBJECT-TYPE
       SYNTAX Gauge32
       MAX-ACCESS read-only
       STATUS obsolete
       DESCRIPTION
           "Outbound media jitter (msec).
AC INI-Param: N/A"
       ::= {acKpiMediaStatsCurrentCpMediaRealmEntry 11}



     acKpiMediaStatsCurrentCpMediaRealmMediaDelayIn OBJECT-TYPE
       SYNTAX Gauge32
       MAX-ACCESS read-only
       STATUS obsolete
       DESCRIPTION
           "Inbound media delay (msec).
AC INI-Param: N/A"
       ::= {acKpiMediaStatsCurrentCpMediaRealmEntry 12}



     acKpiMediaStatsCurrentCpMediaRealmMediaDelayOut OBJECT-TYPE
       SYNTAX Gauge32
       MAX-ACCESS read-only
       STATUS obsolete
       DESCRIPTION
           "Outbound media delay (msec).
AC INI-Param: N/A"
       ::= {acKpiMediaStatsCurrentCpMediaRealmEntry 13}



     acKpiMediaStatsCurrentCpMediaRealmMediaMOSIn OBJECT-TYPE
       SYNTAX Gauge32
       MAX-ACCESS read-only
       STATUS obsolete
       DESCRIPTION
           "Inbound media Mean Opinion Score (MOS) on a scale from 1 to
5.
AC INI-Param: N/A"
       ::= {acKpiMediaStatsCurrentCpMediaRealmEntry 14}



     acKpiMediaStatsCurrentCpMediaRealmMediaMOSOut OBJECT-TYPE
       SYNTAX Gauge32
       MAX-ACCESS read-only
       STATUS obsolete
       DESCRIPTION
           "Outbound media Mean Opinion Score (MOS) on a scale from 1 to
5.
AC INI-Param: N/A"
       ::= {acKpiMediaStatsCurrentCpMediaRealmEntry 15}



     acKpiMediaStatsCurrentCpMediaRealmMediaQualityIn OBJECT-TYPE
       SYNTAX Gauge32
       MAX-ACCESS read-only
       STATUS obsolete
       DESCRIPTION
           "Inbound media quality (0: Red, 1: Yellow, 2: Green).
AC INI-Param: N/A"
       ::= {acKpiMediaStatsCurrentCpMediaRealmEntry 16}



     acKpiMediaStatsCurrentCpMediaRealmMediaQualityOut OBJECT-TYPE
       SYNTAX Gauge32
       MAX-ACCESS read-only
       STATUS obsolete
       DESCRIPTION
           "Outbound media quality (0: Red, 1: Yellow, 2: Green).
AC INI-Param: N/A"
       ::= {acKpiMediaStatsCurrentCpMediaRealmEntry 17}



     acKpiMediaStatsInterval OBJECT IDENTIFIER ::= {acKpiMediaStats 2}


     acKpiMediaStatsIntervalGlobal OBJECT IDENTIFIER ::= {acKpiMediaStatsInterval 1}


     -- ****************************************
     -- acKpiMediaStatsIntervalGlobal table declaration
     -- ****************************************
     acKpiMediaStatsIntervalGlobalTable OBJECT-TYPE
       SYNTAX SEQUENCE OF AcKpiMediaStatsIntervalGlobalEntry
       MAX-ACCESS not-accessible
       STATUS current
       DESCRIPTION
           ""
       ::= {acKpiMediaStatsIntervalGlobal 1}



     -- ****************************************
     -- acKpiMediaStatsIntervalGlobal table entry
     -- ****************************************
     acKpiMediaStatsIntervalGlobalEntry OBJECT-TYPE
       SYNTAX AcKpiMediaStatsIntervalGlobalEntry
       MAX-ACCESS not-accessible
       STATUS current
       DESCRIPTION
           ""
       INDEX {acKpiMediaStatsIntervalGlobalInterval}
       ::= {acKpiMediaStatsIntervalGlobalTable 1}



     -- ****************************************
     -- acKpiMediaStatsIntervalGlobal TABLE
     -- ****************************************
     AcKpiMediaStatsIntervalGlobalEntry ::= SEQUENCE {
       acKpiMediaStatsIntervalGlobalInterval           Unsigned32,
       acKpiMediaStatsIntervalGlobalMediaPacketsIn     Counter64,
       acKpiMediaStatsIntervalGlobalMediaPacketsOut    Counter64,
       acKpiMediaStatsIntervalGlobalMediaKBytesIn      Counter64,
       acKpiMediaStatsIntervalGlobalMediaKBytesOut     Counter64,
       acKpiMediaStatsIntervalGlobalMediaBandwidthInAvg 
                                                       Gauge32,
       acKpiMediaStatsIntervalGlobalMediaBandwidthOutAvg 
                                                       Gauge32,
       acKpiMediaStatsIntervalGlobalMediaPacketLossInAvg 
                                                       Gauge32,
       acKpiMediaStatsIntervalGlobalMediaPacketLossInMin 
                                                       Gauge32,
       acKpiMediaStatsIntervalGlobalMediaPacketLossInMax 
                                                       Gauge32,
       acKpiMediaStatsIntervalGlobalMediaPacketLossOutAvg 
                                                       Gauge32,
       acKpiMediaStatsIntervalGlobalMediaPacketLossOutMin 
                                                       Gauge32,
       acKpiMediaStatsIntervalGlobalMediaPacketLossOutMax 
                                                       Gauge32,
       acKpiMediaStatsIntervalGlobalMediaJitterInAvg   Gauge32,
       acKpiMediaStatsIntervalGlobalMediaJitterInMin   Gauge32,
       acKpiMediaStatsIntervalGlobalMediaJitterInMax   Gauge32,
       acKpiMediaStatsIntervalGlobalMediaJitterOutAvg  Gauge32,
       acKpiMediaStatsIntervalGlobalMediaJitterOutMin  Gauge32,
       acKpiMediaStatsIntervalGlobalMediaJitterOutMax  Gauge32,
       acKpiMediaStatsIntervalGlobalMediaDelayInAvg    Gauge32,
       acKpiMediaStatsIntervalGlobalMediaDelayInMin    Gauge32,
       acKpiMediaStatsIntervalGlobalMediaDelayInMax    Gauge32,
       acKpiMediaStatsIntervalGlobalMediaDelayOutAvg   Gauge32,
       acKpiMediaStatsIntervalGlobalMediaDelayOutMin   Gauge32,
       acKpiMediaStatsIntervalGlobalMediaDelayOutMax   Gauge32,
       acKpiMediaStatsIntervalGlobalMediaMOSInAvg      Gauge32,
       acKpiMediaStatsIntervalGlobalMediaMOSInMin      Gauge32,
       acKpiMediaStatsIntervalGlobalMediaMOSInMax      Gauge32,
       acKpiMediaStatsIntervalGlobalMediaMOSOutAvg     Gauge32,
       acKpiMediaStatsIntervalGlobalMediaMOSOutMin     Gauge32,
       acKpiMediaStatsIntervalGlobalMediaMOSOutMax     Gauge32,
       acKpiMediaStatsIntervalGlobalMediaQualityInMin  Gauge32,
       acKpiMediaStatsIntervalGlobalMediaQualityInMax  Gauge32,
       acKpiMediaStatsIntervalGlobalMediaQualityOutMin Gauge32,
       acKpiMediaStatsIntervalGlobalMediaQualityOutMax Gauge32,
       acKpiMediaStatsIntervalGlobalMediaStreamsAvg    Gauge32,
       acKpiMediaStatsIntervalGlobalMediaStreamsMax    Gauge32,
       acKpiMediaStatsIntervalGlobalMediaRtpStreamsAvg Gauge32,
       acKpiMediaStatsIntervalGlobalMediaRtpStreamsMax Gauge32,
       acKpiMediaStatsIntervalGlobalMediaSrtpStreamsAvg 
                                                       Gauge32,
       acKpiMediaStatsIntervalGlobalMediaSrtpStreamsMax 
                                                       Gauge32,
       acKpiMediaStatsIntervalGlobalMediaSipRecStreamsAvg 
                                                       Gauge32,
       acKpiMediaStatsIntervalGlobalMediaSipRecStreamsMax 
                                                       Gauge32,
       acKpiMediaStatsIntervalGlobalMediaWebRTCStreamsMax 
                                                       Gauge32,
       acKpiMediaStatsIntervalGlobalMediaWebRTCStreamsAvg 
                                                       Gauge32
     }



     acKpiMediaStatsIntervalGlobalInterval OBJECT-TYPE
       SYNTAX Unsigned32 (1..200)
       MAX-ACCESS not-accessible
       STATUS current
       DESCRIPTION
           "
AC INI-Param: N/A"
       ::= {acKpiMediaStatsIntervalGlobalEntry 1}



     acKpiMediaStatsIntervalGlobalMediaPacketsIn OBJECT-TYPE
       SYNTAX Counter64
       MAX-ACCESS read-only
       STATUS current
       DESCRIPTION
           "Number of received media packets.
AC INI-Param: N/A"
       ::= {acKpiMediaStatsIntervalGlobalEntry 2}



     acKpiMediaStatsIntervalGlobalMediaPacketsOut OBJECT-TYPE
       SYNTAX Counter64
       MAX-ACCESS read-only
       STATUS current
       DESCRIPTION
           "Number of transmitted media packets.
AC INI-Param: N/A"
       ::= {acKpiMediaStatsIntervalGlobalEntry 3}



     acKpiMediaStatsIntervalGlobalMediaKBytesIn OBJECT-TYPE
       SYNTAX Counter64
       MAX-ACCESS read-only
       STATUS current
       DESCRIPTION
           "Amount of inbound media traffic (KBytes).
AC INI-Param: N/A"
       ::= {acKpiMediaStatsIntervalGlobalEntry 4}



     acKpiMediaStatsIntervalGlobalMediaKBytesOut OBJECT-TYPE
       SYNTAX Counter64
       MAX-ACCESS read-only
       STATUS current
       DESCRIPTION
           "Amount of outbound media traffic (KBytes).
AC INI-Param: N/A"
       ::= {acKpiMediaStatsIntervalGlobalEntry 5}



     acKpiMediaStatsIntervalGlobalMediaBandwidthInAvg OBJECT-TYPE
       SYNTAX Gauge32
       MAX-ACCESS read-only
       STATUS current
       DESCRIPTION
           "Average inbound media bandwidth (Kbits per sec).
AC INI-Param: N/A"
       ::= {acKpiMediaStatsIntervalGlobalEntry 6}



     acKpiMediaStatsIntervalGlobalMediaBandwidthOutAvg OBJECT-TYPE
       SYNTAX Gauge32
       MAX-ACCESS read-only
       STATUS current
       DESCRIPTION
           "Average outbound media bandwidth (Kbits per sec).
AC INI-Param: N/A"
       ::= {acKpiMediaStatsIntervalGlobalEntry 7}



     acKpiMediaStatsIntervalGlobalMediaPacketLossInAvg OBJECT-TYPE
       SYNTAX Gauge32
       MAX-ACCESS read-only
       STATUS current
       DESCRIPTION
           "Average inbound media packet loss [%].
AC INI-Param: N/A"
       ::= {acKpiMediaStatsIntervalGlobalEntry 8}



     acKpiMediaStatsIntervalGlobalMediaPacketLossInMin OBJECT-TYPE
       SYNTAX Gauge32
       MAX-ACCESS read-only
       STATUS current
       DESCRIPTION
           "Minimum inbound media packet loss [%].
AC INI-Param: N/A"
       ::= {acKpiMediaStatsIntervalGlobalEntry 9}



     acKpiMediaStatsIntervalGlobalMediaPacketLossInMax OBJECT-TYPE
       SYNTAX Gauge32
       MAX-ACCESS read-only
       STATUS current
       DESCRIPTION
           "Maximum inbound media packet loss [%].
AC INI-Param: N/A"
       ::= {acKpiMediaStatsIntervalGlobalEntry 10}



     acKpiMediaStatsIntervalGlobalMediaPacketLossOutAvg OBJECT-TYPE
       SYNTAX Gauge32
       MAX-ACCESS read-only
       STATUS current
       DESCRIPTION
           "Average outbound media packet loss [%].
AC INI-Param: N/A"
       ::= {acKpiMediaStatsIntervalGlobalEntry 11}



     acKpiMediaStatsIntervalGlobalMediaPacketLossOutMin OBJECT-TYPE
       SYNTAX Gauge32
       MAX-ACCESS read-only
       STATUS current
       DESCRIPTION
           "Minimum outbound media packet loss [%].
AC INI-Param: N/A"
       ::= {acKpiMediaStatsIntervalGlobalEntry 12}



     acKpiMediaStatsIntervalGlobalMediaPacketLossOutMax OBJECT-TYPE
       SYNTAX Gauge32
       MAX-ACCESS read-only
       STATUS current
       DESCRIPTION
           "Maximum outbound media packet loss [%].
AC INI-Param: N/A"
       ::= {acKpiMediaStatsIntervalGlobalEntry 13}



     acKpiMediaStatsIntervalGlobalMediaJitterInAvg OBJECT-TYPE
       SYNTAX Gauge32
       MAX-ACCESS read-only
       STATUS current
       DESCRIPTION
           "Average inbound media jitter (msec).
AC INI-Param: N/A"
       ::= {acKpiMediaStatsIntervalGlobalEntry 14}



     acKpiMediaStatsIntervalGlobalMediaJitterInMin OBJECT-TYPE
       SYNTAX Gauge32
       MAX-ACCESS read-only
       STATUS current
       DESCRIPTION
           "Minimum inbound media jitter (msec).
AC INI-Param: N/A"
       ::= {acKpiMediaStatsIntervalGlobalEntry 15}



     acKpiMediaStatsIntervalGlobalMediaJitterInMax OBJECT-TYPE
       SYNTAX Gauge32
       MAX-ACCESS read-only
       STATUS current
       DESCRIPTION
           "Maximum inbound media jitter (msec).
AC INI-Param: N/A"
       ::= {acKpiMediaStatsIntervalGlobalEntry 16}



     acKpiMediaStatsIntervalGlobalMediaJitterOutAvg OBJECT-TYPE
       SYNTAX Gauge32
       MAX-ACCESS read-only
       STATUS current
       DESCRIPTION
           "Average outbound media jitter (msec).
AC INI-Param: N/A"
       ::= {acKpiMediaStatsIntervalGlobalEntry 17}



     acKpiMediaStatsIntervalGlobalMediaJitterOutMin OBJECT-TYPE
       SYNTAX Gauge32
       MAX-ACCESS read-only
       STATUS current
       DESCRIPTION
           "Minimum outbound media jitter (msec).
AC INI-Param: N/A"
       ::= {acKpiMediaStatsIntervalGlobalEntry 18}



     acKpiMediaStatsIntervalGlobalMediaJitterOutMax OBJECT-TYPE
       SYNTAX Gauge32
       MAX-ACCESS read-only
       STATUS current
       DESCRIPTION
           "Maximum outbound media jitter (msec).
AC INI-Param: N/A"
       ::= {acKpiMediaStatsIntervalGlobalEntry 19}



     acKpiMediaStatsIntervalGlobalMediaDelayInAvg OBJECT-TYPE
       SYNTAX Gauge32
       MAX-ACCESS read-only
       STATUS current
       DESCRIPTION
           "Average inbound media delay (msec).
AC INI-Param: N/A"
       ::= {acKpiMediaStatsIntervalGlobalEntry 20}



     acKpiMediaStatsIntervalGlobalMediaDelayInMin OBJECT-TYPE
       SYNTAX Gauge32
       MAX-ACCESS read-only
       STATUS current
       DESCRIPTION
           "Minimum inbound media delay (msec).
AC INI-Param: N/A"
       ::= {acKpiMediaStatsIntervalGlobalEntry 21}



     acKpiMediaStatsIntervalGlobalMediaDelayInMax OBJECT-TYPE
       SYNTAX Gauge32
       MAX-ACCESS read-only
       STATUS current
       DESCRIPTION
           "Maximum inbound media delay (msec).
AC INI-Param: N/A"
       ::= {acKpiMediaStatsIntervalGlobalEntry 22}



     acKpiMediaStatsIntervalGlobalMediaDelayOutAvg OBJECT-TYPE
       SYNTAX Gauge32
       MAX-ACCESS read-only
       STATUS current
       DESCRIPTION
           "Average outbound media delay (msec).
AC INI-Param: N/A"
       ::= {acKpiMediaStatsIntervalGlobalEntry 23}



     acKpiMediaStatsIntervalGlobalMediaDelayOutMin OBJECT-TYPE
       SYNTAX Gauge32
       MAX-ACCESS read-only
       STATUS current
       DESCRIPTION
           "Minimum outbound media delay (msec).
AC INI-Param: N/A"
       ::= {acKpiMediaStatsIntervalGlobalEntry 24}



     acKpiMediaStatsIntervalGlobalMediaDelayOutMax OBJECT-TYPE
       SYNTAX Gauge32
       MAX-ACCESS read-only
       STATUS current
       DESCRIPTION
           "Maximum outbound media delay (msec).
AC INI-Param: N/A"
       ::= {acKpiMediaStatsIntervalGlobalEntry 25}



     acKpiMediaStatsIntervalGlobalMediaMOSInAvg OBJECT-TYPE
       SYNTAX Gauge32
       MAX-ACCESS read-only
       STATUS current
       DESCRIPTION
           "Average inbound media Mean Opinion Score (MOS, 0.1 units) on
a scale of 10-50.
AC INI-Param: N/A"
       ::= {acKpiMediaStatsIntervalGlobalEntry 26}



     acKpiMediaStatsIntervalGlobalMediaMOSInMin OBJECT-TYPE
       SYNTAX Gauge32
       MAX-ACCESS read-only
       STATUS current
       DESCRIPTION
           "Minimum inbound media Mean Opinion Score (MOS, 0.1 units) on
a scale of 10-50.
AC INI-Param: N/A"
       ::= {acKpiMediaStatsIntervalGlobalEntry 27}



     acKpiMediaStatsIntervalGlobalMediaMOSInMax OBJECT-TYPE
       SYNTAX Gauge32
       MAX-ACCESS read-only
       STATUS current
       DESCRIPTION
           "Maximum inbound media Mean Opinion Score (MOS, 0.1 units) on
a scale of 10-50.
AC INI-Param: N/A"
       ::= {acKpiMediaStatsIntervalGlobalEntry 28}



     acKpiMediaStatsIntervalGlobalMediaMOSOutAvg OBJECT-TYPE
       SYNTAX Gauge32
       MAX-ACCESS read-only
       STATUS current
       DESCRIPTION
           "Average outbound media Mean Opinion Score (MOS, 0.1 units) on
a scale of 10-50.
AC INI-Param: N/A"
       ::= {acKpiMediaStatsIntervalGlobalEntry 29}



     acKpiMediaStatsIntervalGlobalMediaMOSOutMin OBJECT-TYPE
       SYNTAX Gauge32
       MAX-ACCESS read-only
       STATUS current
       DESCRIPTION
           "Minimum outbound media Mean Opinion Score (MOS, 0.1 units) on
a scale of 10-50.
AC INI-Param: N/A"
       ::= {acKpiMediaStatsIntervalGlobalEntry 30}



     acKpiMediaStatsIntervalGlobalMediaMOSOutMax OBJECT-TYPE
       SYNTAX Gauge32
       MAX-ACCESS read-only
       STATUS current
       DESCRIPTION
           "Maximum outbound media Mean Opinion Score (MOS, 0.1 units) on
a scale of 10-50.
AC INI-Param: N/A"
       ::= {acKpiMediaStatsIntervalGlobalEntry 31}



     acKpiMediaStatsIntervalGlobalMediaQualityInMin OBJECT-TYPE
       SYNTAX Gauge32
       MAX-ACCESS read-only
       STATUS current
       DESCRIPTION
           "Minimum inbound media quality (0: Red, 1: Yellow, 2: Green).
AC INI-Param: N/A"
       ::= {acKpiMediaStatsIntervalGlobalEntry 32}



     acKpiMediaStatsIntervalGlobalMediaQualityInMax OBJECT-TYPE
       SYNTAX Gauge32
       MAX-ACCESS read-only
       STATUS current
       DESCRIPTION
           "Maximum inbound media quality (0: Red, 1: Yellow, 2: Green).
AC INI-Param: N/A"
       ::= {acKpiMediaStatsIntervalGlobalEntry 33}



     acKpiMediaStatsIntervalGlobalMediaQualityOutMin OBJECT-TYPE
       SYNTAX Gauge32
       MAX-ACCESS read-only
       STATUS current
       DESCRIPTION
           "Minimum outbound media quality (0: Red, 1: Yellow, 2: Green).
AC INI-Param: N/A"
       ::= {acKpiMediaStatsIntervalGlobalEntry 34}



     acKpiMediaStatsIntervalGlobalMediaQualityOutMax OBJECT-TYPE
       SYNTAX Gauge32
       MAX-ACCESS read-only
       STATUS current
       DESCRIPTION
           "Maximum outbound media quality (0: Red, 1: Yellow, 2: Green).
AC INI-Param: N/A"
       ::= {acKpiMediaStatsIntervalGlobalEntry 35}



     acKpiMediaStatsIntervalGlobalMediaStreamsAvg OBJECT-TYPE
       SYNTAX Gauge32
       MAX-ACCESS read-only
       STATUS current
       DESCRIPTION
           "Average number of media streams (legs).
AC INI-Param: N/A"
       ::= {acKpiMediaStatsIntervalGlobalEntry 36}



     acKpiMediaStatsIntervalGlobalMediaStreamsMax OBJECT-TYPE
       SYNTAX Gauge32
       MAX-ACCESS read-only
       STATUS current
       DESCRIPTION
           "Maximum number of media streams (legs).
AC INI-Param: N/A"
       ::= {acKpiMediaStatsIntervalGlobalEntry 37}



     acKpiMediaStatsIntervalGlobalMediaRtpStreamsAvg OBJECT-TYPE
       SYNTAX Gauge32
       MAX-ACCESS read-only
       STATUS current
       DESCRIPTION
           "Average number of media RTP streams (legs).
AC INI-Param: N/A"
       ::= {acKpiMediaStatsIntervalGlobalEntry 38}



     acKpiMediaStatsIntervalGlobalMediaRtpStreamsMax OBJECT-TYPE
       SYNTAX Gauge32
       MAX-ACCESS read-only
       STATUS current
       DESCRIPTION
           "Maximum number of media RTP streams (legs).
AC INI-Param: N/A"
       ::= {acKpiMediaStatsIntervalGlobalEntry 39}



     acKpiMediaStatsIntervalGlobalMediaSrtpStreamsAvg OBJECT-TYPE
       SYNTAX Gauge32
       MAX-ACCESS read-only
       STATUS current
       DESCRIPTION
           "Average number of media SRTP streams (legs).
AC INI-Param: N/A"
       ::= {acKpiMediaStatsIntervalGlobalEntry 40}



     acKpiMediaStatsIntervalGlobalMediaSrtpStreamsMax OBJECT-TYPE
       SYNTAX Gauge32
       MAX-ACCESS read-only
       STATUS current
       DESCRIPTION
           "Maximum number of media SRTP streams (legs).
AC INI-Param: N/A"
       ::= {acKpiMediaStatsIntervalGlobalEntry 41}



     acKpiMediaStatsIntervalGlobalMediaSipRecStreamsAvg OBJECT-TYPE
       SYNTAX Gauge32
       MAX-ACCESS read-only
       STATUS current
       DESCRIPTION
           "Average number of media SIP-REC streams (legs).
AC INI-Param: N/A"
       ::= {acKpiMediaStatsIntervalGlobalEntry 42}



     acKpiMediaStatsIntervalGlobalMediaSipRecStreamsMax OBJECT-TYPE
       SYNTAX Gauge32
       MAX-ACCESS read-only
       STATUS current
       DESCRIPTION
           "Maximum number of media SIP-REC streams (legs).
AC INI-Param: N/A"
       ::= {acKpiMediaStatsIntervalGlobalEntry 43}



     acKpiMediaStatsIntervalGlobalMediaWebRTCStreamsMax OBJECT-TYPE
       SYNTAX Gauge32
       MAX-ACCESS read-only
       STATUS current
       DESCRIPTION
           "Maximum number of media WebRTC streams (legs).
AC INI-Param: N/A"
       ::= {acKpiMediaStatsIntervalGlobalEntry 44}



     acKpiMediaStatsIntervalGlobalMediaWebRTCStreamsAvg OBJECT-TYPE
       SYNTAX Gauge32
       MAX-ACCESS read-only
       STATUS current
       DESCRIPTION
           "Average number of media WebRTC streams (legs).
AC INI-Param: N/A"
       ::= {acKpiMediaStatsIntervalGlobalEntry 45}



     acKpiMediaStatsIntervalTables OBJECT IDENTIFIER ::= {acKpiMediaStatsInterval 2}


     -- ****************************************
     -- acKpiMediaStatsIntervalIpGroup table declaration
     -- ****************************************
     acKpiMediaStatsIntervalIpGroupTable OBJECT-TYPE
       SYNTAX SEQUENCE OF AcKpiMediaStatsIntervalIpGroupEntry
       MAX-ACCESS not-accessible
       STATUS current
       DESCRIPTION
           ""
       ::= {acKpiMediaStatsIntervalTables 1}



     -- ****************************************
     -- acKpiMediaStatsIntervalIpGroup table entry
     -- ****************************************
     acKpiMediaStatsIntervalIpGroupEntry OBJECT-TYPE
       SYNTAX AcKpiMediaStatsIntervalIpGroupEntry
       MAX-ACCESS not-accessible
       STATUS current
       DESCRIPTION
           ""
       INDEX {acKpiMediaStatsIntervalIpGroupIndex,acKpiMediaStatsIntervalIpGroupInterval}
       ::= {acKpiMediaStatsIntervalIpGroupTable 1}



     -- ****************************************
     -- acKpiMediaStatsIntervalIpGroup TABLE
     -- ****************************************
     AcKpiMediaStatsIntervalIpGroupEntry ::= SEQUENCE {
       acKpiMediaStatsIntervalIpGroupIndex             Unsigned32,
       acKpiMediaStatsIntervalIpGroupInterval          Unsigned32,
       acKpiMediaStatsIntervalIpGroupMediaPacketsIn    Counter64,
       acKpiMediaStatsIntervalIpGroupMediaPacketsOut   Counter64,
       acKpiMediaStatsIntervalIpGroupMediaKBytesIn     Counter64,
       acKpiMediaStatsIntervalIpGroupMediaKBytesOut    Counter64,
       acKpiMediaStatsIntervalIpGroupMediaBandwidthInAvg 
                                                       Gauge32,
       acKpiMediaStatsIntervalIpGroupMediaBandwidthOutAvg 
                                                       Gauge32,
       acKpiMediaStatsIntervalIpGroupMediaPacketLossInAvg 
                                                       Gauge32,
       acKpiMediaStatsIntervalIpGroupMediaPacketLossInMin 
                                                       Gauge32,
       acKpiMediaStatsIntervalIpGroupMediaPacketLossInMax 
                                                       Gauge32,
       acKpiMediaStatsIntervalIpGroupMediaPacketLossOutAvg 
                                                       Gauge32,
       acKpiMediaStatsIntervalIpGroupMediaPacketLossOutMin 
                                                       Gauge32,
       acKpiMediaStatsIntervalIpGroupMediaPacketLossOutMax 
                                                       Gauge32,
       acKpiMediaStatsIntervalIpGroupMediaJitterInAvg  Gauge32,
       acKpiMediaStatsIntervalIpGroupMediaJitterInMin  Gauge32,
       acKpiMediaStatsIntervalIpGroupMediaJitterInMax  Gauge32,
       acKpiMediaStatsIntervalIpGroupMediaJitterOutAvg Gauge32,
       acKpiMediaStatsIntervalIpGroupMediaJitterOutMin Gauge32,
       acKpiMediaStatsIntervalIpGroupMediaJitterOutMax Gauge32,
       acKpiMediaStatsIntervalIpGroupMediaDelayInAvg   Gauge32,
       acKpiMediaStatsIntervalIpGroupMediaDelayInMin   Gauge32,
       acKpiMediaStatsIntervalIpGroupMediaDelayInMax   Gauge32,
       acKpiMediaStatsIntervalIpGroupMediaDelayOutAvg  Gauge32,
       acKpiMediaStatsIntervalIpGroupMediaDelayOutMin  Gauge32,
       acKpiMediaStatsIntervalIpGroupMediaDelayOutMax  Gauge32,
       acKpiMediaStatsIntervalIpGroupMediaMOSInAvg     Gauge32,
       acKpiMediaStatsIntervalIpGroupMediaMOSInMin     Gauge32,
       acKpiMediaStatsIntervalIpGroupMediaMOSInMax     Gauge32,
       acKpiMediaStatsIntervalIpGroupMediaMOSOutAvg    Gauge32,
       acKpiMediaStatsIntervalIpGroupMediaMOSOutMin    Gauge32,
       acKpiMediaStatsIntervalIpGroupMediaMOSOutMax    Gauge32,
       acKpiMediaStatsIntervalIpGroupMediaQualityInMin Gauge32,
       acKpiMediaStatsIntervalIpGroupMediaQualityInMax Gauge32,
       acKpiMediaStatsIntervalIpGroupMediaQualityOutMin 
                                                       Gauge32,
       acKpiMediaStatsIntervalIpGroupMediaQualityOutMax 
                                                       Gauge32,
       acKpiMediaStatsIntervalIpGroupMediaStreamsAvg   Gauge32,
       acKpiMediaStatsIntervalIpGroupMediaStreamsMax   Gauge32,
       acKpiMediaStatsIntervalIpGroupMediaRtpStreamsAvg 
                                                       Gauge32,
       acKpiMediaStatsIntervalIpGroupMediaRtpStreamsMax 
                                                       Gauge32,
       acKpiMediaStatsIntervalIpGroupMediaSrtpStreamsAvg 
                                                       Gauge32,
       acKpiMediaStatsIntervalIpGroupMediaSrtpStreamsMax 
                                                       Gauge32,
       acKpiMediaStatsIntervalIpGroupMediaSipRecStreamsAvg 
                                                       Gauge32,
       acKpiMediaStatsIntervalIpGroupMediaSipRecStreamsMax 
                                                       Gauge32,
       acKpiMediaStatsIntervalIpGroupMediaWebRTCStreamsAvg 
                                                       Gauge32,
       acKpiMediaStatsIntervalIpGroupMediaWebRTCStreamsMax 
                                                       Gauge32
     }



     acKpiMediaStatsIntervalIpGroupIndex OBJECT-TYPE
       SYNTAX Unsigned32 (0..32767)
       MAX-ACCESS not-accessible
       STATUS current
       DESCRIPTION
           "
AC INI-Param: N/A"
       ::= {acKpiMediaStatsIntervalIpGroupEntry 1}



     acKpiMediaStatsIntervalIpGroupInterval OBJECT-TYPE
       SYNTAX Unsigned32 (1..200)
       MAX-ACCESS not-accessible
       STATUS current
       DESCRIPTION
           "
AC INI-Param: N/A"
       ::= {acKpiMediaStatsIntervalIpGroupEntry 2}



     acKpiMediaStatsIntervalIpGroupMediaPacketsIn OBJECT-TYPE
       SYNTAX Counter64
       MAX-ACCESS read-only
       STATUS current
       DESCRIPTION
           "Number of received media packets.
AC INI-Param: N/A"
       ::= {acKpiMediaStatsIntervalIpGroupEntry 3}



     acKpiMediaStatsIntervalIpGroupMediaPacketsOut OBJECT-TYPE
       SYNTAX Counter64
       MAX-ACCESS read-only
       STATUS current
       DESCRIPTION
           "Number of transmitted media packets.
AC INI-Param: N/A"
       ::= {acKpiMediaStatsIntervalIpGroupEntry 4}



     acKpiMediaStatsIntervalIpGroupMediaKBytesIn OBJECT-TYPE
       SYNTAX Counter64
       MAX-ACCESS read-only
       STATUS current
       DESCRIPTION
           "Amount of inbound media traffic (KBytes).
AC INI-Param: N/A"
       ::= {acKpiMediaStatsIntervalIpGroupEntry 5}



     acKpiMediaStatsIntervalIpGroupMediaKBytesOut OBJECT-TYPE
       SYNTAX Counter64
       MAX-ACCESS read-only
       STATUS current
       DESCRIPTION
           "Amount of outbound media traffic (KBytes).
AC INI-Param: N/A"
       ::= {acKpiMediaStatsIntervalIpGroupEntry 6}



     acKpiMediaStatsIntervalIpGroupMediaBandwidthInAvg OBJECT-TYPE
       SYNTAX Gauge32
       MAX-ACCESS read-only
       STATUS current
       DESCRIPTION
           "Average inbound media bandwidth (Kbits per sec).
AC INI-Param: N/A"
       ::= {acKpiMediaStatsIntervalIpGroupEntry 7}



     acKpiMediaStatsIntervalIpGroupMediaBandwidthOutAvg OBJECT-TYPE
       SYNTAX Gauge32
       MAX-ACCESS read-only
       STATUS current
       DESCRIPTION
           "Average outbound media bandwidth (Kbits per sec).
AC INI-Param: N/A"
       ::= {acKpiMediaStatsIntervalIpGroupEntry 8}



     acKpiMediaStatsIntervalIpGroupMediaPacketLossInAvg OBJECT-TYPE
       SYNTAX Gauge32
       MAX-ACCESS read-only
       STATUS current
       DESCRIPTION
           "Average inbound media packet loss [%].
AC INI-Param: N/A"
       ::= {acKpiMediaStatsIntervalIpGroupEntry 9}



     acKpiMediaStatsIntervalIpGroupMediaPacketLossInMin OBJECT-TYPE
       SYNTAX Gauge32
       MAX-ACCESS read-only
       STATUS current
       DESCRIPTION
           "Minimum inbound media packet loss [%].
AC INI-Param: N/A"
       ::= {acKpiMediaStatsIntervalIpGroupEntry 10}



     acKpiMediaStatsIntervalIpGroupMediaPacketLossInMax OBJECT-TYPE
       SYNTAX Gauge32
       MAX-ACCESS read-only
       STATUS current
       DESCRIPTION
           "Maximum inbound media packet loss [%].
AC INI-Param: N/A"
       ::= {acKpiMediaStatsIntervalIpGroupEntry 11}



     acKpiMediaStatsIntervalIpGroupMediaPacketLossOutAvg OBJECT-TYPE
       SYNTAX Gauge32
       MAX-ACCESS read-only
       STATUS current
       DESCRIPTION
           "Average outbound media packet loss [%].
AC INI-Param: N/A"
       ::= {acKpiMediaStatsIntervalIpGroupEntry 12}



     acKpiMediaStatsIntervalIpGroupMediaPacketLossOutMin OBJECT-TYPE
       SYNTAX Gauge32
       MAX-ACCESS read-only
       STATUS current
       DESCRIPTION
           "Minimum outbound media packet loss [%].
AC INI-Param: N/A"
       ::= {acKpiMediaStatsIntervalIpGroupEntry 13}



     acKpiMediaStatsIntervalIpGroupMediaPacketLossOutMax OBJECT-TYPE
       SYNTAX Gauge32
       MAX-ACCESS read-only
       STATUS current
       DESCRIPTION
           "Maximum outbound media packet loss [%].
AC INI-Param: N/A"
       ::= {acKpiMediaStatsIntervalIpGroupEntry 14}



     acKpiMediaStatsIntervalIpGroupMediaJitterInAvg OBJECT-TYPE
       SYNTAX Gauge32
       MAX-ACCESS read-only
       STATUS current
       DESCRIPTION
           "Average inbound media jitter (msec).
AC INI-Param: N/A"
       ::= {acKpiMediaStatsIntervalIpGroupEntry 15}



     acKpiMediaStatsIntervalIpGroupMediaJitterInMin OBJECT-TYPE
       SYNTAX Gauge32
       MAX-ACCESS read-only
       STATUS current
       DESCRIPTION
           "Minimum inbound media jitter (msec).
AC INI-Param: N/A"
       ::= {acKpiMediaStatsIntervalIpGroupEntry 16}



     acKpiMediaStatsIntervalIpGroupMediaJitterInMax OBJECT-TYPE
       SYNTAX Gauge32
       MAX-ACCESS read-only
       STATUS current
       DESCRIPTION
           "Maximum inbound media jitter (msec).
AC INI-Param: N/A"
       ::= {acKpiMediaStatsIntervalIpGroupEntry 17}



     acKpiMediaStatsIntervalIpGroupMediaJitterOutAvg OBJECT-TYPE
       SYNTAX Gauge32
       MAX-ACCESS read-only
       STATUS current
       DESCRIPTION
           "Average outbound media jitter (msec).
AC INI-Param: N/A"
       ::= {acKpiMediaStatsIntervalIpGroupEntry 18}



     acKpiMediaStatsIntervalIpGroupMediaJitterOutMin OBJECT-TYPE
       SYNTAX Gauge32
       MAX-ACCESS read-only
       STATUS current
       DESCRIPTION
           "Minimum outbound media jitter (msec).
AC INI-Param: N/A"
       ::= {acKpiMediaStatsIntervalIpGroupEntry 19}



     acKpiMediaStatsIntervalIpGroupMediaJitterOutMax OBJECT-TYPE
       SYNTAX Gauge32
       MAX-ACCESS read-only
       STATUS current
       DESCRIPTION
           "Maximum outbound media jitter (msec).
AC INI-Param: N/A"
       ::= {acKpiMediaStatsIntervalIpGroupEntry 20}



     acKpiMediaStatsIntervalIpGroupMediaDelayInAvg OBJECT-TYPE
       SYNTAX Gauge32
       MAX-ACCESS read-only
       STATUS current
       DESCRIPTION
           "Average inbound media delay (msec).
AC INI-Param: N/A"
       ::= {acKpiMediaStatsIntervalIpGroupEntry 21}



     acKpiMediaStatsIntervalIpGroupMediaDelayInMin OBJECT-TYPE
       SYNTAX Gauge32
       MAX-ACCESS read-only
       STATUS current
       DESCRIPTION
           "Minimum inbound media delay (msec).
AC INI-Param: N/A"
       ::= {acKpiMediaStatsIntervalIpGroupEntry 22}



     acKpiMediaStatsIntervalIpGroupMediaDelayInMax OBJECT-TYPE
       SYNTAX Gauge32
       MAX-ACCESS read-only
       STATUS current
       DESCRIPTION
           "Maximum inbound media delay (msec).
AC INI-Param: N/A"
       ::= {acKpiMediaStatsIntervalIpGroupEntry 23}



     acKpiMediaStatsIntervalIpGroupMediaDelayOutAvg OBJECT-TYPE
       SYNTAX Gauge32
       MAX-ACCESS read-only
       STATUS current
       DESCRIPTION
           "Average outbound media delay (msec).
AC INI-Param: N/A"
       ::= {acKpiMediaStatsIntervalIpGroupEntry 24}



     acKpiMediaStatsIntervalIpGroupMediaDelayOutMin OBJECT-TYPE
       SYNTAX Gauge32
       MAX-ACCESS read-only
       STATUS current
       DESCRIPTION
           "Minimum outbound media delay (msec).
AC INI-Param: N/A"
       ::= {acKpiMediaStatsIntervalIpGroupEntry 25}



     acKpiMediaStatsIntervalIpGroupMediaDelayOutMax OBJECT-TYPE
       SYNTAX Gauge32
       MAX-ACCESS read-only
       STATUS current
       DESCRIPTION
           "Maximum outbound media delay (msec).
AC INI-Param: N/A"
       ::= {acKpiMediaStatsIntervalIpGroupEntry 26}



     acKpiMediaStatsIntervalIpGroupMediaMOSInAvg OBJECT-TYPE
       SYNTAX Gauge32
       MAX-ACCESS read-only
       STATUS current
       DESCRIPTION
           "Average inbound media Mean Opinion Score (MOS, 0.1 units) on
a scale of 10-50.
AC INI-Param: N/A"
       ::= {acKpiMediaStatsIntervalIpGroupEntry 27}



     acKpiMediaStatsIntervalIpGroupMediaMOSInMin OBJECT-TYPE
       SYNTAX Gauge32
       MAX-ACCESS read-only
       STATUS current
       DESCRIPTION
           "Minimum inbound media Mean Opinion Score (MOS, 0.1 units) on
a scale of 10-50.
AC INI-Param: N/A"
       ::= {acKpiMediaStatsIntervalIpGroupEntry 28}



     acKpiMediaStatsIntervalIpGroupMediaMOSInMax OBJECT-TYPE
       SYNTAX Gauge32
       MAX-ACCESS read-only
       STATUS current
       DESCRIPTION
           "Maximum inbound media Mean Opinion Score (MOS, 0.1 units) on
a scale of 10-50.
AC INI-Param: N/A"
       ::= {acKpiMediaStatsIntervalIpGroupEntry 29}



     acKpiMediaStatsIntervalIpGroupMediaMOSOutAvg OBJECT-TYPE
       SYNTAX Gauge32
       MAX-ACCESS read-only
       STATUS current
       DESCRIPTION
           "Average outbound media Mean Opinion Score (MOS, 0.1 units) on
a scale of 10-50.
AC INI-Param: N/A"
       ::= {acKpiMediaStatsIntervalIpGroupEntry 30}



     acKpiMediaStatsIntervalIpGroupMediaMOSOutMin OBJECT-TYPE
       SYNTAX Gauge32
       MAX-ACCESS read-only
       STATUS current
       DESCRIPTION
           "Minimum outbound media Mean Opinion Score (MOS, 0.1 units) on
a scale of 10-50.
AC INI-Param: N/A"
       ::= {acKpiMediaStatsIntervalIpGroupEntry 31}



     acKpiMediaStatsIntervalIpGroupMediaMOSOutMax OBJECT-TYPE
       SYNTAX Gauge32
       MAX-ACCESS read-only
       STATUS current
       DESCRIPTION
           "Maximum outbound media Mean Opinion Score (MOS, 0.1 units) on
a scale of 10-50.
AC INI-Param: N/A"
       ::= {acKpiMediaStatsIntervalIpGroupEntry 32}



     acKpiMediaStatsIntervalIpGroupMediaQualityInMin OBJECT-TYPE
       SYNTAX Gauge32
       MAX-ACCESS read-only
       STATUS current
       DESCRIPTION
           "Minimum inbound media quality (0: Red, 1: Yellow, 2: Green).
AC INI-Param: N/A"
       ::= {acKpiMediaStatsIntervalIpGroupEntry 33}



     acKpiMediaStatsIntervalIpGroupMediaQualityInMax OBJECT-TYPE
       SYNTAX Gauge32
       MAX-ACCESS read-only
       STATUS current
       DESCRIPTION
           "Maximum inbound media quality (0: Red, 1: Yellow, 2: Green).
AC INI-Param: N/A"
       ::= {acKpiMediaStatsIntervalIpGroupEntry 34}



     acKpiMediaStatsIntervalIpGroupMediaQualityOutMin OBJECT-TYPE
       SYNTAX Gauge32
       MAX-ACCESS read-only
       STATUS current
       DESCRIPTION
           "Minimum outbound media quality (0: Red, 1: Yellow, 2: Green).
AC INI-Param: N/A"
       ::= {acKpiMediaStatsIntervalIpGroupEntry 35}



     acKpiMediaStatsIntervalIpGroupMediaQualityOutMax OBJECT-TYPE
       SYNTAX Gauge32
       MAX-ACCESS read-only
       STATUS current
       DESCRIPTION
           "Maximum outbound media quality (0: Red, 1: Yellow, 2: Green).
AC INI-Param: N/A"
       ::= {acKpiMediaStatsIntervalIpGroupEntry 36}



     acKpiMediaStatsIntervalIpGroupMediaStreamsAvg OBJECT-TYPE
       SYNTAX Gauge32
       MAX-ACCESS read-only
       STATUS current
       DESCRIPTION
           "Average number of media streams (legs).
AC INI-Param: N/A"
       ::= {acKpiMediaStatsIntervalIpGroupEntry 37}



     acKpiMediaStatsIntervalIpGroupMediaStreamsMax OBJECT-TYPE
       SYNTAX Gauge32
       MAX-ACCESS read-only
       STATUS current
       DESCRIPTION
           "Maximum number of media streams (legs).
AC INI-Param: N/A"
       ::= {acKpiMediaStatsIntervalIpGroupEntry 38}



     acKpiMediaStatsIntervalIpGroupMediaRtpStreamsAvg OBJECT-TYPE
       SYNTAX Gauge32
       MAX-ACCESS read-only
       STATUS current
       DESCRIPTION
           "Average number of media RTP streams (legs).
AC INI-Param: N/A"
       ::= {acKpiMediaStatsIntervalIpGroupEntry 39}



     acKpiMediaStatsIntervalIpGroupMediaRtpStreamsMax OBJECT-TYPE
       SYNTAX Gauge32
       MAX-ACCESS read-only
       STATUS current
       DESCRIPTION
           "Maximum number of media RTP streams (legs).
AC INI-Param: N/A"
       ::= {acKpiMediaStatsIntervalIpGroupEntry 40}



     acKpiMediaStatsIntervalIpGroupMediaSrtpStreamsAvg OBJECT-TYPE
       SYNTAX Gauge32
       MAX-ACCESS read-only
       STATUS current
       DESCRIPTION
           "Average number of media SRTP streams (legs).
AC INI-Param: N/A"
       ::= {acKpiMediaStatsIntervalIpGroupEntry 41}



     acKpiMediaStatsIntervalIpGroupMediaSrtpStreamsMax OBJECT-TYPE
       SYNTAX Gauge32
       MAX-ACCESS read-only
       STATUS current
       DESCRIPTION
           "Maximum number of media SRTP streams (legs).
AC INI-Param: N/A"
       ::= {acKpiMediaStatsIntervalIpGroupEntry 42}



     acKpiMediaStatsIntervalIpGroupMediaSipRecStreamsAvg OBJECT-TYPE
       SYNTAX Gauge32
       MAX-ACCESS read-only
       STATUS current
       DESCRIPTION
           "Average number of media SIP-REC streams (legs).
AC INI-Param: N/A"
       ::= {acKpiMediaStatsIntervalIpGroupEntry 43}



     acKpiMediaStatsIntervalIpGroupMediaSipRecStreamsMax OBJECT-TYPE
       SYNTAX Gauge32
       MAX-ACCESS read-only
       STATUS current
       DESCRIPTION
           "Maximum number of media SIP-REC streams (legs).
AC INI-Param: N/A"
       ::= {acKpiMediaStatsIntervalIpGroupEntry 44}



     acKpiMediaStatsIntervalIpGroupMediaWebRTCStreamsAvg OBJECT-TYPE
       SYNTAX Gauge32
       MAX-ACCESS read-only
       STATUS current
       DESCRIPTION
           "Average number of media WebRTC streams (legs).
AC INI-Param: N/A"
       ::= {acKpiMediaStatsIntervalIpGroupEntry 45}



     acKpiMediaStatsIntervalIpGroupMediaWebRTCStreamsMax OBJECT-TYPE
       SYNTAX Gauge32
       MAX-ACCESS read-only
       STATUS current
       DESCRIPTION
           "Maximum number of media WebRTC streams (legs).
AC INI-Param: N/A"
       ::= {acKpiMediaStatsIntervalIpGroupEntry 46}



     -- ****************************************
     -- acKpiMediaStatsIntervalCpMediaRealm table declaration
     -- ****************************************
     acKpiMediaStatsIntervalCpMediaRealmTable OBJECT-TYPE
       SYNTAX SEQUENCE OF AcKpiMediaStatsIntervalCpMediaRealmEntry
       MAX-ACCESS not-accessible
       STATUS obsolete
       DESCRIPTION
           ""
       ::= {acKpiMediaStatsIntervalTables 2}



     -- ****************************************
     -- acKpiMediaStatsIntervalCpMediaRealm table entry
     -- ****************************************
     acKpiMediaStatsIntervalCpMediaRealmEntry OBJECT-TYPE
       SYNTAX AcKpiMediaStatsIntervalCpMediaRealmEntry
       MAX-ACCESS not-accessible
       STATUS obsolete
       DESCRIPTION
           ""
       INDEX {acKpiMediaStatsIntervalCpMediaRealmIndex,acKpiMediaStatsIntervalCpMediaRealmInterval}
       ::= {acKpiMediaStatsIntervalCpMediaRealmTable 1}



     -- ****************************************
     -- acKpiMediaStatsIntervalCpMediaRealm TABLE
     -- ****************************************
     AcKpiMediaStatsIntervalCpMediaRealmEntry ::= SEQUENCE {
       acKpiMediaStatsIntervalCpMediaRealmIndex        Unsigned32,
       acKpiMediaStatsIntervalCpMediaRealmInterval     Unsigned32,
       acKpiMediaStatsIntervalCpMediaRealmMediaPacketsIn 
                                                       Counter64,
       acKpiMediaStatsIntervalCpMediaRealmMediaPacketsOut 
                                                       Counter64,
       acKpiMediaStatsIntervalCpMediaRealmMediaKBytesIn 
                                                       Counter64,
       acKpiMediaStatsIntervalCpMediaRealmMediaKBytesOut 
                                                       Counter64,
       acKpiMediaStatsIntervalCpMediaRealmMediaBandwidthInAvg 
                                                       Gauge32,
       acKpiMediaStatsIntervalCpMediaRealmMediaBandwidthOutAvg 
                                                       Gauge32,
       acKpiMediaStatsIntervalCpMediaRealmMediaPacketLossInAvg 
                                                       Gauge32,
       acKpiMediaStatsIntervalCpMediaRealmMediaPacketLossInMin 
                                                       Gauge32,
       acKpiMediaStatsIntervalCpMediaRealmMediaPacketLossInMax 
                                                       Gauge32,
       acKpiMediaStatsIntervalCpMediaRealmMediaPacketLossOutAvg 
                                                       Gauge32,
       acKpiMediaStatsIntervalCpMediaRealmMediaPacketLossOutMin 
                                                       Gauge32,
       acKpiMediaStatsIntervalCpMediaRealmMediaPacketLossOutMax 
                                                       Gauge32,
       acKpiMediaStatsIntervalCpMediaRealmMediaJitterInAvg 
                                                       Gauge32,
       acKpiMediaStatsIntervalCpMediaRealmMediaJitterInMin 
                                                       Gauge32,
       acKpiMediaStatsIntervalCpMediaRealmMediaJitterInMax 
                                                       Gauge32,
       acKpiMediaStatsIntervalCpMediaRealmMediaJitterOutAvg 
                                                       Gauge32,
       acKpiMediaStatsIntervalCpMediaRealmMediaJitterOutMin 
                                                       Gauge32,
       acKpiMediaStatsIntervalCpMediaRealmMediaJitterOutMax 
                                                       Gauge32,
       acKpiMediaStatsIntervalCpMediaRealmMediaDelayInAvg 
                                                       Gauge32,
       acKpiMediaStatsIntervalCpMediaRealmMediaDelayInMin 
                                                       Gauge32,
       acKpiMediaStatsIntervalCpMediaRealmMediaDelayInMax 
                                                       Gauge32,
       acKpiMediaStatsIntervalCpMediaRealmMediaDelayOutAvg 
                                                       Gauge32,
       acKpiMediaStatsIntervalCpMediaRealmMediaDelayOutMin 
                                                       Gauge32,
       acKpiMediaStatsIntervalCpMediaRealmMediaDelayOutMax 
                                                       Gauge32,
       acKpiMediaStatsIntervalCpMediaRealmMediaMOSInAvg 
                                                       Gauge32,
       acKpiMediaStatsIntervalCpMediaRealmMediaMOSInMin 
                                                       Gauge32,
       acKpiMediaStatsIntervalCpMediaRealmMediaMOSInMax 
                                                       Gauge32,
       acKpiMediaStatsIntervalCpMediaRealmMediaMOSOutAvg 
                                                       Gauge32,
       acKpiMediaStatsIntervalCpMediaRealmMediaMOSOutMin 
                                                       Gauge32,
       acKpiMediaStatsIntervalCpMediaRealmMediaMOSOutMax 
                                                       Gauge32,
       acKpiMediaStatsIntervalCpMediaRealmMediaQualityInMin 
                                                       Gauge32,
       acKpiMediaStatsIntervalCpMediaRealmMediaQualityInMax 
                                                       Gauge32,
       acKpiMediaStatsIntervalCpMediaRealmMediaQualityOutMin 
                                                       Gauge32,
       acKpiMediaStatsIntervalCpMediaRealmMediaQualityOutMax 
                                                       Gauge32
     }



     acKpiMediaStatsIntervalCpMediaRealmIndex OBJECT-TYPE
       SYNTAX Unsigned32 (0..32767)
       MAX-ACCESS not-accessible
       STATUS obsolete
       DESCRIPTION
           "
AC INI-Param: N/A"
       ::= {acKpiMediaStatsIntervalCpMediaRealmEntry 1}



     acKpiMediaStatsIntervalCpMediaRealmInterval OBJECT-TYPE
       SYNTAX Unsigned32 (1..200)
       MAX-ACCESS not-accessible
       STATUS obsolete
       DESCRIPTION
           "
AC INI-Param: N/A"
       ::= {acKpiMediaStatsIntervalCpMediaRealmEntry 2}



     acKpiMediaStatsIntervalCpMediaRealmMediaPacketsIn OBJECT-TYPE
       SYNTAX Counter64
       MAX-ACCESS read-only
       STATUS obsolete
       DESCRIPTION
           "Number of received media packets.
AC INI-Param: N/A"
       ::= {acKpiMediaStatsIntervalCpMediaRealmEntry 3}



     acKpiMediaStatsIntervalCpMediaRealmMediaPacketsOut OBJECT-TYPE
       SYNTAX Counter64
       MAX-ACCESS read-only
       STATUS obsolete
       DESCRIPTION
           "Number of transmitted media packets.
AC INI-Param: N/A"
       ::= {acKpiMediaStatsIntervalCpMediaRealmEntry 4}



     acKpiMediaStatsIntervalCpMediaRealmMediaKBytesIn OBJECT-TYPE
       SYNTAX Counter64
       MAX-ACCESS read-only
       STATUS obsolete
       DESCRIPTION
           "Amount of inbound media traffic (KBytes).
AC INI-Param: N/A"
       ::= {acKpiMediaStatsIntervalCpMediaRealmEntry 5}



     acKpiMediaStatsIntervalCpMediaRealmMediaKBytesOut OBJECT-TYPE
       SYNTAX Counter64
       MAX-ACCESS read-only
       STATUS obsolete
       DESCRIPTION
           "Amount of outbound media traffic (KBytes).
AC INI-Param: N/A"
       ::= {acKpiMediaStatsIntervalCpMediaRealmEntry 6}



     acKpiMediaStatsIntervalCpMediaRealmMediaBandwidthInAvg OBJECT-TYPE
       SYNTAX Gauge32
       MAX-ACCESS read-only
       STATUS obsolete
       DESCRIPTION
           "Average inbound media bandwidth (Kbits per sec).
AC INI-Param: N/A"
       ::= {acKpiMediaStatsIntervalCpMediaRealmEntry 7}



     acKpiMediaStatsIntervalCpMediaRealmMediaBandwidthOutAvg OBJECT-TYPE
       SYNTAX Gauge32
       MAX-ACCESS read-only
       STATUS obsolete
       DESCRIPTION
           "Average outbound media bandwidth (Kbits per sec).
AC INI-Param: N/A"
       ::= {acKpiMediaStatsIntervalCpMediaRealmEntry 8}



     acKpiMediaStatsIntervalCpMediaRealmMediaPacketLossInAvg OBJECT-TYPE
       SYNTAX Gauge32
       MAX-ACCESS read-only
       STATUS obsolete
       DESCRIPTION
           "Average inbound media packet loss (in 0.01% units).
AC INI-Param: N/A"
       ::= {acKpiMediaStatsIntervalCpMediaRealmEntry 9}



     acKpiMediaStatsIntervalCpMediaRealmMediaPacketLossInMin OBJECT-TYPE
       SYNTAX Gauge32
       MAX-ACCESS read-only
       STATUS obsolete
       DESCRIPTION
           "Minimum inbound media packet loss (in 0.01% units).
AC INI-Param: N/A"
       ::= {acKpiMediaStatsIntervalCpMediaRealmEntry 10}



     acKpiMediaStatsIntervalCpMediaRealmMediaPacketLossInMax OBJECT-TYPE
       SYNTAX Gauge32
       MAX-ACCESS read-only
       STATUS obsolete
       DESCRIPTION
           "Maximum inbound media packet loss (in 0.01% units).
AC INI-Param: N/A"
       ::= {acKpiMediaStatsIntervalCpMediaRealmEntry 11}



     acKpiMediaStatsIntervalCpMediaRealmMediaPacketLossOutAvg OBJECT-TYPE
       SYNTAX Gauge32
       MAX-ACCESS read-only
       STATUS obsolete
       DESCRIPTION
           "Average outbound media packet loss (in 0.01% units).
AC INI-Param: N/A"
       ::= {acKpiMediaStatsIntervalCpMediaRealmEntry 12}



     acKpiMediaStatsIntervalCpMediaRealmMediaPacketLossOutMin OBJECT-TYPE
       SYNTAX Gauge32
       MAX-ACCESS read-only
       STATUS obsolete
       DESCRIPTION
           "Minimum outbound media packet loss (in 0.01% units).
AC INI-Param: N/A"
       ::= {acKpiMediaStatsIntervalCpMediaRealmEntry 13}



     acKpiMediaStatsIntervalCpMediaRealmMediaPacketLossOutMax OBJECT-TYPE
       SYNTAX Gauge32
       MAX-ACCESS read-only
       STATUS obsolete
       DESCRIPTION
           "Maximum outbound media packet loss (in 0.01% units).
AC INI-Param: N/A"
       ::= {acKpiMediaStatsIntervalCpMediaRealmEntry 14}



     acKpiMediaStatsIntervalCpMediaRealmMediaJitterInAvg OBJECT-TYPE
       SYNTAX Gauge32
       MAX-ACCESS read-only
       STATUS obsolete
       DESCRIPTION
           "Average inbound media jitter (msec).
AC INI-Param: N/A"
       ::= {acKpiMediaStatsIntervalCpMediaRealmEntry 15}



     acKpiMediaStatsIntervalCpMediaRealmMediaJitterInMin OBJECT-TYPE
       SYNTAX Gauge32
       MAX-ACCESS read-only
       STATUS obsolete
       DESCRIPTION
           "Minimum inbound media jitter (msec).
AC INI-Param: N/A"
       ::= {acKpiMediaStatsIntervalCpMediaRealmEntry 16}



     acKpiMediaStatsIntervalCpMediaRealmMediaJitterInMax OBJECT-TYPE
       SYNTAX Gauge32
       MAX-ACCESS read-only
       STATUS obsolete
       DESCRIPTION
           "Maximum inbound media jitter (msec).
AC INI-Param: N/A"
       ::= {acKpiMediaStatsIntervalCpMediaRealmEntry 17}



     acKpiMediaStatsIntervalCpMediaRealmMediaJitterOutAvg OBJECT-TYPE
       SYNTAX Gauge32
       MAX-ACCESS read-only
       STATUS obsolete
       DESCRIPTION
           "Average outbound media jitter (msec).
AC INI-Param: N/A"
       ::= {acKpiMediaStatsIntervalCpMediaRealmEntry 18}



     acKpiMediaStatsIntervalCpMediaRealmMediaJitterOutMin OBJECT-TYPE
       SYNTAX Gauge32
       MAX-ACCESS read-only
       STATUS obsolete
       DESCRIPTION
           "Minimum outbound media jitter (msec).
AC INI-Param: N/A"
       ::= {acKpiMediaStatsIntervalCpMediaRealmEntry 19}



     acKpiMediaStatsIntervalCpMediaRealmMediaJitterOutMax OBJECT-TYPE
       SYNTAX Gauge32
       MAX-ACCESS read-only
       STATUS obsolete
       DESCRIPTION
           "Maximum outbound media jitter (msec).
AC INI-Param: N/A"
       ::= {acKpiMediaStatsIntervalCpMediaRealmEntry 20}



     acKpiMediaStatsIntervalCpMediaRealmMediaDelayInAvg OBJECT-TYPE
       SYNTAX Gauge32
       MAX-ACCESS read-only
       STATUS obsolete
       DESCRIPTION
           "Average inbound media delay (msec).
AC INI-Param: N/A"
       ::= {acKpiMediaStatsIntervalCpMediaRealmEntry 21}



     acKpiMediaStatsIntervalCpMediaRealmMediaDelayInMin OBJECT-TYPE
       SYNTAX Gauge32
       MAX-ACCESS read-only
       STATUS obsolete
       DESCRIPTION
           "Minimum inbound media delay (msec).
AC INI-Param: N/A"
       ::= {acKpiMediaStatsIntervalCpMediaRealmEntry 22}



     acKpiMediaStatsIntervalCpMediaRealmMediaDelayInMax OBJECT-TYPE
       SYNTAX Gauge32
       MAX-ACCESS read-only
       STATUS obsolete
       DESCRIPTION
           "Maximum inbound media delay (msec).
AC INI-Param: N/A"
       ::= {acKpiMediaStatsIntervalCpMediaRealmEntry 23}



     acKpiMediaStatsIntervalCpMediaRealmMediaDelayOutAvg OBJECT-TYPE
       SYNTAX Gauge32
       MAX-ACCESS read-only
       STATUS obsolete
       DESCRIPTION
           "Average outbound media delay (msec).
AC INI-Param: N/A"
       ::= {acKpiMediaStatsIntervalCpMediaRealmEntry 24}



     acKpiMediaStatsIntervalCpMediaRealmMediaDelayOutMin OBJECT-TYPE
       SYNTAX Gauge32
       MAX-ACCESS read-only
       STATUS obsolete
       DESCRIPTION
           "Minimum outbound media delay (msec).
AC INI-Param: N/A"
       ::= {acKpiMediaStatsIntervalCpMediaRealmEntry 25}



     acKpiMediaStatsIntervalCpMediaRealmMediaDelayOutMax OBJECT-TYPE
       SYNTAX Gauge32
       MAX-ACCESS read-only
       STATUS obsolete
       DESCRIPTION
           "Maximum outbound media delay (msec).
AC INI-Param: N/A"
       ::= {acKpiMediaStatsIntervalCpMediaRealmEntry 26}



     acKpiMediaStatsIntervalCpMediaRealmMediaMOSInAvg OBJECT-TYPE
       SYNTAX Gauge32
       MAX-ACCESS read-only
       STATUS obsolete
       DESCRIPTION
           "Average inbound media Mean Opinion Score (MOS) on a scale from
1 to 5.
AC INI-Param: N/A"
       ::= {acKpiMediaStatsIntervalCpMediaRealmEntry 27}



     acKpiMediaStatsIntervalCpMediaRealmMediaMOSInMin OBJECT-TYPE
       SYNTAX Gauge32
       MAX-ACCESS read-only
       STATUS obsolete
       DESCRIPTION
           "Minimum inbound media Mean Opinion Score (MOS) on a scale from
1 to 5.
AC INI-Param: N/A"
       ::= {acKpiMediaStatsIntervalCpMediaRealmEntry 28}



     acKpiMediaStatsIntervalCpMediaRealmMediaMOSInMax OBJECT-TYPE
       SYNTAX Gauge32
       MAX-ACCESS read-only
       STATUS obsolete
       DESCRIPTION
           "Maximum inbound media Mean Opinion Score (MOS) on a scale from
1 to 5.
AC INI-Param: N/A"
       ::= {acKpiMediaStatsIntervalCpMediaRealmEntry 29}



     acKpiMediaStatsIntervalCpMediaRealmMediaMOSOutAvg OBJECT-TYPE
       SYNTAX Gauge32
       MAX-ACCESS read-only
       STATUS obsolete
       DESCRIPTION
           "Average outbound media Mean Opinion Score (MOS) on a scale from
1 to 5.
AC INI-Param: N/A"
       ::= {acKpiMediaStatsIntervalCpMediaRealmEntry 30}



     acKpiMediaStatsIntervalCpMediaRealmMediaMOSOutMin OBJECT-TYPE
       SYNTAX Gauge32
       MAX-ACCESS read-only
       STATUS obsolete
       DESCRIPTION
           "Minimum outbound media Mean Opinion Score (MOS) on a scale from
1 to 5.
AC INI-Param: N/A"
       ::= {acKpiMediaStatsIntervalCpMediaRealmEntry 31}



     acKpiMediaStatsIntervalCpMediaRealmMediaMOSOutMax OBJECT-TYPE
       SYNTAX Gauge32
       MAX-ACCESS read-only
       STATUS obsolete
       DESCRIPTION
           "Maximum outbound media Mean Opinion Score (MOS) on a scale from
1 to 5.
AC INI-Param: N/A"
       ::= {acKpiMediaStatsIntervalCpMediaRealmEntry 32}



     acKpiMediaStatsIntervalCpMediaRealmMediaQualityInMin OBJECT-TYPE
       SYNTAX Gauge32
       MAX-ACCESS read-only
       STATUS obsolete
       DESCRIPTION
           "Minimum inbound media quality (0: Red, 1: Yellow, 2: Green).
AC INI-Param: N/A"
       ::= {acKpiMediaStatsIntervalCpMediaRealmEntry 33}



     acKpiMediaStatsIntervalCpMediaRealmMediaQualityInMax OBJECT-TYPE
       SYNTAX Gauge32
       MAX-ACCESS read-only
       STATUS obsolete
       DESCRIPTION
           "Maximum inbound media quality (0: Red, 1: Yellow, 2: Green).
AC INI-Param: N/A"
       ::= {acKpiMediaStatsIntervalCpMediaRealmEntry 34}



     acKpiMediaStatsIntervalCpMediaRealmMediaQualityOutMin OBJECT-TYPE
       SYNTAX Gauge32
       MAX-ACCESS read-only
       STATUS obsolete
       DESCRIPTION
           "Minimum outbound media quality (0: Red, 1: Yellow, 2: Green).
AC INI-Param: N/A"
       ::= {acKpiMediaStatsIntervalCpMediaRealmEntry 35}



     acKpiMediaStatsIntervalCpMediaRealmMediaQualityOutMax OBJECT-TYPE
       SYNTAX Gauge32
       MAX-ACCESS read-only
       STATUS obsolete
       DESCRIPTION
           "Maximum outbound media quality (0: Red, 1: Yellow, 2: Green).
AC INI-Param: N/A"
       ::= {acKpiMediaStatsIntervalCpMediaRealmEntry 36}



     acKpiCoderStats OBJECT IDENTIFIER ::= {acKpiMedia 2}


     acKpiCoderStatsCurrent OBJECT IDENTIFIER ::= {acKpiCoderStats 1}


     acKpiCoderStatsCurrentGlobal OBJECT IDENTIFIER ::= {acKpiCoderStatsCurrent 1}


     acKpiCoderStatsCurrentGlobalCoderG711 OBJECT-TYPE
       SYNTAX Gauge32
       MAX-ACCESS read-only
       STATUS current
       DESCRIPTION
           "Number of active channels with G.711 coder.
AC INI-Param: N/A"
       ::= {acKpiCoderStatsCurrentGlobal 1}



     acKpiCoderStatsCurrentGlobalCoderG711alaw OBJECT-TYPE
       SYNTAX Gauge32
       MAX-ACCESS read-only
       STATUS current
       DESCRIPTION
           "Number of active channels with G.711alaw coder.
AC INI-Param: N/A"
       ::= {acKpiCoderStatsCurrentGlobal 2}



     acKpiCoderStatsCurrentGlobalCoderG711ulaw OBJECT-TYPE
       SYNTAX Gauge32
       MAX-ACCESS read-only
       STATUS current
       DESCRIPTION
           "Number of active channels with G.711ulaw coder.
AC INI-Param: N/A"
       ::= {acKpiCoderStatsCurrentGlobal 3}



     acKpiCoderStatsCurrentGlobalCoderG722 OBJECT-TYPE
       SYNTAX Gauge32
       MAX-ACCESS read-only
       STATUS current
       DESCRIPTION
           "Number of active channels with G.722 coder.
AC INI-Param: N/A"
       ::= {acKpiCoderStatsCurrentGlobal 4}



     acKpiCoderStatsCurrentGlobalCoderG723 OBJECT-TYPE
       SYNTAX Gauge32
       MAX-ACCESS read-only
       STATUS current
       DESCRIPTION
           "Number of active channels with G.723 coder.
AC INI-Param: N/A"
       ::= {acKpiCoderStatsCurrentGlobal 5}



     acKpiCoderStatsCurrentGlobalCoderG726 OBJECT-TYPE
       SYNTAX Gauge32
       MAX-ACCESS read-only
       STATUS current
       DESCRIPTION
           "Number of active channels with G.726 coder.
AC INI-Param: N/A"
       ::= {acKpiCoderStatsCurrentGlobal 6}



     acKpiCoderStatsCurrentGlobalCoderG729 OBJECT-TYPE
       SYNTAX Gauge32
       MAX-ACCESS read-only
       STATUS current
       DESCRIPTION
           "Number of active channels with G.729 coder.
AC INI-Param: N/A"
       ::= {acKpiCoderStatsCurrentGlobal 7}



     acKpiCoderStatsCurrentGlobalCoderG729EV OBJECT-TYPE
       SYNTAX Gauge32
       MAX-ACCESS read-only
       STATUS current
       DESCRIPTION
           "Number of active channels with G.729EV coder.
AC INI-Param: N/A"
       ::= {acKpiCoderStatsCurrentGlobal 8}



     acKpiCoderStatsCurrentGlobalCoderGSMFR OBJECT-TYPE
       SYNTAX Gauge32
       MAX-ACCESS read-only
       STATUS current
       DESCRIPTION
           "Number of active channels with GSM-FR coder.
AC INI-Param: N/A"
       ::= {acKpiCoderStatsCurrentGlobal 9}



     acKpiCoderStatsCurrentGlobalCoderGSMEFR OBJECT-TYPE
       SYNTAX Gauge32
       MAX-ACCESS read-only
       STATUS current
       DESCRIPTION
           "Number of active channels with GSM-EFR coder.
AC INI-Param: N/A"
       ::= {acKpiCoderStatsCurrentGlobal 10}



     acKpiCoderStatsCurrentGlobalCoderILBC OBJECT-TYPE
       SYNTAX Gauge32
       MAX-ACCESS read-only
       STATUS current
       DESCRIPTION
           "Number of active channels with iLBC coder.
AC INI-Param: N/A"
       ::= {acKpiCoderStatsCurrentGlobal 11}



     acKpiCoderStatsCurrentGlobalCoderEVRC OBJECT-TYPE
       SYNTAX Gauge32
       MAX-ACCESS read-only
       STATUS current
       DESCRIPTION
           "Number of active channels with EVRC coder.
AC INI-Param: N/A"
       ::= {acKpiCoderStatsCurrentGlobal 12}



     acKpiCoderStatsCurrentGlobalCoderQCELP OBJECT-TYPE
       SYNTAX Gauge32
       MAX-ACCESS read-only
       STATUS current
       DESCRIPTION
           "Number of active channels with QCELP coder.
AC INI-Param: N/A"
       ::= {acKpiCoderStatsCurrentGlobal 13}



     acKpiCoderStatsCurrentGlobalCoderAMRNB OBJECT-TYPE
       SYNTAX Gauge32
       MAX-ACCESS read-only
       STATUS current
       DESCRIPTION
           "Number of active channels with AMR-NB coder.
AC INI-Param: N/A"
       ::= {acKpiCoderStatsCurrentGlobal 14}



     acKpiCoderStatsCurrentGlobalCoderAMRWB OBJECT-TYPE
       SYNTAX Gauge32
       MAX-ACCESS read-only
       STATUS current
       DESCRIPTION
           "Number of active channels with AMR-WB coder.
AC INI-Param: N/A"
       ::= {acKpiCoderStatsCurrentGlobal 15}



     acKpiCoderStatsCurrentGlobalCoderT38 OBJECT-TYPE
       SYNTAX Gauge32
       MAX-ACCESS read-only
       STATUS current
       DESCRIPTION
           "Number of active channels with T.38.
AC INI-Param: N/A"
       ::= {acKpiCoderStatsCurrentGlobal 16}



     acKpiCoderStatsCurrentGlobalCoderSILKNB OBJECT-TYPE
       SYNTAX Gauge32
       MAX-ACCESS read-only
       STATUS current
       DESCRIPTION
           "Number of active channels with SILK-NB coder.
AC INI-Param: N/A"
       ::= {acKpiCoderStatsCurrentGlobal 17}



     acKpiCoderStatsCurrentGlobalCoderSILKWB OBJECT-TYPE
       SYNTAX Gauge32
       MAX-ACCESS read-only
       STATUS current
       DESCRIPTION
           "Number of active channels with SILK-WB coder.
AC INI-Param: N/A"
       ::= {acKpiCoderStatsCurrentGlobal 18}



     acKpiCoderStatsCurrentGlobalCoderOPUSNB OBJECT-TYPE
       SYNTAX Gauge32
       MAX-ACCESS read-only
       STATUS current
       DESCRIPTION
           "Number of active channels with OPUS-NB coder.
AC INI-Param: N/A"
       ::= {acKpiCoderStatsCurrentGlobal 19}



     acKpiCoderStatsCurrentGlobalCoderOPUSWB OBJECT-TYPE
       SYNTAX Gauge32
       MAX-ACCESS read-only
       STATUS current
       DESCRIPTION
           "Number of active channels with OPUS-WB coder.
AC INI-Param: N/A"
       ::= {acKpiCoderStatsCurrentGlobal 20}



     acKpiCoderStatsCurrentGlobalCoderRTA OBJECT-TYPE
       SYNTAX Gauge32
       MAX-ACCESS read-only
       STATUS current
       DESCRIPTION
           "Number of active channels with RTA coder.
AC INI-Param: N/A"
       ::= {acKpiCoderStatsCurrentGlobal 21}



     acKpiCoderStatsCurrentGlobalCoderOther OBJECT-TYPE
       SYNTAX Gauge32
       MAX-ACCESS read-only
       STATUS current
       DESCRIPTION
           "Number of active channels with other coders.
AC INI-Param: N/A"
       ::= {acKpiCoderStatsCurrentGlobal 22}



     acKpiCoderStatsCurrentTables OBJECT IDENTIFIER ::= {acKpiCoderStatsCurrent 2}


     -- ****************************************
     -- acKpiCoderStatsCurrentIpGroup table declaration
     -- ****************************************
     acKpiCoderStatsCurrentIpGroupTable OBJECT-TYPE
       SYNTAX SEQUENCE OF AcKpiCoderStatsCurrentIpGroupEntry
       MAX-ACCESS not-accessible
       STATUS current
       DESCRIPTION
           ""
       ::= {acKpiCoderStatsCurrentTables 1}



     -- ****************************************
     -- acKpiCoderStatsCurrentIpGroup table entry
     -- ****************************************
     acKpiCoderStatsCurrentIpGroupEntry OBJECT-TYPE
       SYNTAX AcKpiCoderStatsCurrentIpGroupEntry
       MAX-ACCESS not-accessible
       STATUS current
       DESCRIPTION
           ""
       INDEX {acKpiCoderStatsCurrentIpGroupIndex}
       ::= {acKpiCoderStatsCurrentIpGroupTable 1}



     -- ****************************************
     -- acKpiCoderStatsCurrentIpGroup TABLE
     -- ****************************************
     AcKpiCoderStatsCurrentIpGroupEntry ::= SEQUENCE {
       acKpiCoderStatsCurrentIpGroupIndex              Unsigned32,
       acKpiCoderStatsCurrentIpGroupCoderG711          Gauge32,
       acKpiCoderStatsCurrentIpGroupCoderG711alaw      Gauge32,
       acKpiCoderStatsCurrentIpGroupCoderG711ulaw      Gauge32,
       acKpiCoderStatsCurrentIpGroupCoderG722          Gauge32,
       acKpiCoderStatsCurrentIpGroupCoderG723          Gauge32,
       acKpiCoderStatsCurrentIpGroupCoderG726          Gauge32,
       acKpiCoderStatsCurrentIpGroupCoderG729          Gauge32,
       acKpiCoderStatsCurrentIpGroupCoderG729EV        Gauge32,
       acKpiCoderStatsCurrentIpGroupCoderGSMFR         Gauge32,
       acKpiCoderStatsCurrentIpGroupCoderGSMEFR        Gauge32,
       acKpiCoderStatsCurrentIpGroupCoderILBC          Gauge32,
       acKpiCoderStatsCurrentIpGroupCoderEVRC          Gauge32,
       acKpiCoderStatsCurrentIpGroupCoderQCELP         Gauge32,
       acKpiCoderStatsCurrentIpGroupCoderAMRNB         Gauge32,
       acKpiCoderStatsCurrentIpGroupCoderAMRWB         Gauge32,
       acKpiCoderStatsCurrentIpGroupCoderT38           Gauge32,
       acKpiCoderStatsCurrentIpGroupCoderSILKNB        Gauge32,
       acKpiCoderStatsCurrentIpGroupCoderSILKWB        Gauge32,
       acKpiCoderStatsCurrentIpGroupCoderOPUSNB        Gauge32,
       acKpiCoderStatsCurrentIpGroupCoderOPUSWB        Gauge32,
       acKpiCoderStatsCurrentIpGroupCoderRTA           Gauge32,
       acKpiCoderStatsCurrentIpGroupCoderOther         Gauge32
     }



     acKpiCoderStatsCurrentIpGroupIndex OBJECT-TYPE
       SYNTAX Unsigned32 (0..32767)
       MAX-ACCESS not-accessible
       STATUS current
       DESCRIPTION
           "
AC INI-Param: N/A"
       ::= {acKpiCoderStatsCurrentIpGroupEntry 1}



     acKpiCoderStatsCurrentIpGroupCoderG711 OBJECT-TYPE
       SYNTAX Gauge32
       MAX-ACCESS read-only
       STATUS current
       DESCRIPTION
           "Number of active channels with G.711 coder.
AC INI-Param: N/A"
       ::= {acKpiCoderStatsCurrentIpGroupEntry 2}



     acKpiCoderStatsCurrentIpGroupCoderG711alaw OBJECT-TYPE
       SYNTAX Gauge32
       MAX-ACCESS read-only
       STATUS current
       DESCRIPTION
           "Number of active channels with G.711alaw coder.
AC INI-Param: N/A"
       ::= {acKpiCoderStatsCurrentIpGroupEntry 3}



     acKpiCoderStatsCurrentIpGroupCoderG711ulaw OBJECT-TYPE
       SYNTAX Gauge32
       MAX-ACCESS read-only
       STATUS current
       DESCRIPTION
           "Number of active channels with G.711ulaw coder.
AC INI-Param: N/A"
       ::= {acKpiCoderStatsCurrentIpGroupEntry 4}



     acKpiCoderStatsCurrentIpGroupCoderG722 OBJECT-TYPE
       SYNTAX Gauge32
       MAX-ACCESS read-only
       STATUS current
       DESCRIPTION
           "Number of active channels with G.722 coder.
AC INI-Param: N/A"
       ::= {acKpiCoderStatsCurrentIpGroupEntry 5}



     acKpiCoderStatsCurrentIpGroupCoderG723 OBJECT-TYPE
       SYNTAX Gauge32
       MAX-ACCESS read-only
       STATUS current
       DESCRIPTION
           "Number of active channels with G.723 coder.
AC INI-Param: N/A"
       ::= {acKpiCoderStatsCurrentIpGroupEntry 6}



     acKpiCoderStatsCurrentIpGroupCoderG726 OBJECT-TYPE
       SYNTAX Gauge32
       MAX-ACCESS read-only
       STATUS current
       DESCRIPTION
           "Number of active channels with G.726 coder.
AC INI-Param: N/A"
       ::= {acKpiCoderStatsCurrentIpGroupEntry 7}



     acKpiCoderStatsCurrentIpGroupCoderG729 OBJECT-TYPE
       SYNTAX Gauge32
       MAX-ACCESS read-only
       STATUS current
       DESCRIPTION
           "Number of active channels with G.729 coder.
AC INI-Param: N/A"
       ::= {acKpiCoderStatsCurrentIpGroupEntry 8}



     acKpiCoderStatsCurrentIpGroupCoderG729EV OBJECT-TYPE
       SYNTAX Gauge32
       MAX-ACCESS read-only
       STATUS current
       DESCRIPTION
           "Number of active channels with G.729EV coder.
AC INI-Param: N/A"
       ::= {acKpiCoderStatsCurrentIpGroupEntry 9}



     acKpiCoderStatsCurrentIpGroupCoderGSMFR OBJECT-TYPE
       SYNTAX Gauge32
       MAX-ACCESS read-only
       STATUS current
       DESCRIPTION
           "Number of active channels with GSM-FR coder.
AC INI-Param: N/A"
       ::= {acKpiCoderStatsCurrentIpGroupEntry 10}



     acKpiCoderStatsCurrentIpGroupCoderGSMEFR OBJECT-TYPE
       SYNTAX Gauge32
       MAX-ACCESS read-only
       STATUS current
       DESCRIPTION
           "Number of active channels with GSM-EFR coder.
AC INI-Param: N/A"
       ::= {acKpiCoderStatsCurrentIpGroupEntry 11}



     acKpiCoderStatsCurrentIpGroupCoderILBC OBJECT-TYPE
       SYNTAX Gauge32
       MAX-ACCESS read-only
       STATUS current
       DESCRIPTION
           "Number of active channels with iLBC coder.
AC INI-Param: N/A"
       ::= {acKpiCoderStatsCurrentIpGroupEntry 12}



     acKpiCoderStatsCurrentIpGroupCoderEVRC OBJECT-TYPE
       SYNTAX Gauge32
       MAX-ACCESS read-only
       STATUS current
       DESCRIPTION
           "Number of active channels with EVRC coder.
AC INI-Param: N/A"
       ::= {acKpiCoderStatsCurrentIpGroupEntry 13}



     acKpiCoderStatsCurrentIpGroupCoderQCELP OBJECT-TYPE
       SYNTAX Gauge32
       MAX-ACCESS read-only
       STATUS current
       DESCRIPTION
           "Number of active channels with QCELP coder.
AC INI-Param: N/A"
       ::= {acKpiCoderStatsCurrentIpGroupEntry 14}



     acKpiCoderStatsCurrentIpGroupCoderAMRNB OBJECT-TYPE
       SYNTAX Gauge32
       MAX-ACCESS read-only
       STATUS current
       DESCRIPTION
           "Number of active channels with AMR-NB coder.
AC INI-Param: N/A"
       ::= {acKpiCoderStatsCurrentIpGroupEntry 15}



     acKpiCoderStatsCurrentIpGroupCoderAMRWB OBJECT-TYPE
       SYNTAX Gauge32
       MAX-ACCESS read-only
       STATUS current
       DESCRIPTION
           "Number of active channels with AMR-WB coder.
AC INI-Param: N/A"
       ::= {acKpiCoderStatsCurrentIpGroupEntry 16}



     acKpiCoderStatsCurrentIpGroupCoderT38 OBJECT-TYPE
       SYNTAX Gauge32
       MAX-ACCESS read-only
       STATUS current
       DESCRIPTION
           "Number of active channels with T.38.
AC INI-Param: N/A"
       ::= {acKpiCoderStatsCurrentIpGroupEntry 17}



     acKpiCoderStatsCurrentIpGroupCoderSILKNB OBJECT-TYPE
       SYNTAX Gauge32
       MAX-ACCESS read-only
       STATUS current
       DESCRIPTION
           "Number of active channels with SILK-NB coder.
AC INI-Param: N/A"
       ::= {acKpiCoderStatsCurrentIpGroupEntry 18}



     acKpiCoderStatsCurrentIpGroupCoderSILKWB OBJECT-TYPE
       SYNTAX Gauge32
       MAX-ACCESS read-only
       STATUS current
       DESCRIPTION
           "Number of active channels with SILK-WB coder.
AC INI-Param: N/A"
       ::= {acKpiCoderStatsCurrentIpGroupEntry 19}



     acKpiCoderStatsCurrentIpGroupCoderOPUSNB OBJECT-TYPE
       SYNTAX Gauge32
       MAX-ACCESS read-only
       STATUS current
       DESCRIPTION
           "Number of active channels with OPUS-NB coder.
AC INI-Param: N/A"
       ::= {acKpiCoderStatsCurrentIpGroupEntry 20}



     acKpiCoderStatsCurrentIpGroupCoderOPUSWB OBJECT-TYPE
       SYNTAX Gauge32
       MAX-ACCESS read-only
       STATUS current
       DESCRIPTION
           "Number of active channels with OPUS-WB coder.
AC INI-Param: N/A"
       ::= {acKpiCoderStatsCurrentIpGroupEntry 21}



     acKpiCoderStatsCurrentIpGroupCoderRTA OBJECT-TYPE
       SYNTAX Gauge32
       MAX-ACCESS read-only
       STATUS current
       DESCRIPTION
           "Number of active channels with RTA coder.
AC INI-Param: N/A"
       ::= {acKpiCoderStatsCurrentIpGroupEntry 22}



     acKpiCoderStatsCurrentIpGroupCoderOther OBJECT-TYPE
       SYNTAX Gauge32
       MAX-ACCESS read-only
       STATUS current
       DESCRIPTION
           "Number of active channels with other coders.
AC INI-Param: N/A"
       ::= {acKpiCoderStatsCurrentIpGroupEntry 23}



     acKpiCoderStatsInterval OBJECT IDENTIFIER ::= {acKpiCoderStats 2}


     acKpiCoderStatsIntervalGlobal OBJECT IDENTIFIER ::= {acKpiCoderStatsInterval 1}


     -- ****************************************
     -- acKpiCoderStatsIntervalGlobal table declaration
     -- ****************************************
     acKpiCoderStatsIntervalGlobalTable OBJECT-TYPE
       SYNTAX SEQUENCE OF AcKpiCoderStatsIntervalGlobalEntry
       MAX-ACCESS not-accessible
       STATUS current
       DESCRIPTION
           ""
       ::= {acKpiCoderStatsIntervalGlobal 1}



     -- ****************************************
     -- acKpiCoderStatsIntervalGlobal table entry
     -- ****************************************
     acKpiCoderStatsIntervalGlobalEntry OBJECT-TYPE
       SYNTAX AcKpiCoderStatsIntervalGlobalEntry
       MAX-ACCESS not-accessible
       STATUS current
       DESCRIPTION
           ""
       INDEX {acKpiCoderStatsIntervalGlobalInterval}
       ::= {acKpiCoderStatsIntervalGlobalTable 1}



     -- ****************************************
     -- acKpiCoderStatsIntervalGlobal TABLE
     -- ****************************************
     AcKpiCoderStatsIntervalGlobalEntry ::= SEQUENCE {
       acKpiCoderStatsIntervalGlobalInterval           Unsigned32,
       acKpiCoderStatsIntervalGlobalCoderG711Avg       Gauge32,
       acKpiCoderStatsIntervalGlobalCoderG711Max       Gauge32,
       acKpiCoderStatsIntervalGlobalCoderG711alawAvg   Gauge32,
       acKpiCoderStatsIntervalGlobalCoderG711alawMax   Gauge32,
       acKpiCoderStatsIntervalGlobalCoderG711ulawAvg   Gauge32,
       acKpiCoderStatsIntervalGlobalCoderG711ulawMax   Gauge32,
       acKpiCoderStatsIntervalGlobalCoderG722Avg       Gauge32,
       acKpiCoderStatsIntervalGlobalCoderG722Max       Gauge32,
       acKpiCoderStatsIntervalGlobalCoderG723Avg       Gauge32,
       acKpiCoderStatsIntervalGlobalCoderG723Max       Gauge32,
       acKpiCoderStatsIntervalGlobalCoderG726Avg       Gauge32,
       acKpiCoderStatsIntervalGlobalCoderG726Max       Gauge32,
       acKpiCoderStatsIntervalGlobalCoderG729Avg       Gauge32,
       acKpiCoderStatsIntervalGlobalCoderG729Max       Gauge32,
       acKpiCoderStatsIntervalGlobalCoderG729EVAvg     Gauge32,
       acKpiCoderStatsIntervalGlobalCoderG729EVMax     Gauge32,
       acKpiCoderStatsIntervalGlobalCoderGSMFRAvg      Gauge32,
       acKpiCoderStatsIntervalGlobalCoderGSMFRMax      Gauge32,
       acKpiCoderStatsIntervalGlobalCoderGSMEFRAvg     Gauge32,
       acKpiCoderStatsIntervalGlobalCoderGSMEFRMax     Gauge32,
       acKpiCoderStatsIntervalGlobalCoderILBCAvg       Gauge32,
       acKpiCoderStatsIntervalGlobalCoderILBCMax       Gauge32,
       acKpiCoderStatsIntervalGlobalCoderEVRCAvg       Gauge32,
       acKpiCoderStatsIntervalGlobalCoderEVRCMax       Gauge32,
       acKpiCoderStatsIntervalGlobalCoderQCELPAvg      Gauge32,
       acKpiCoderStatsIntervalGlobalCoderQCELPMax      Gauge32,
       acKpiCoderStatsIntervalGlobalCoderAMRNBAvg      Gauge32,
       acKpiCoderStatsIntervalGlobalCoderAMRNBMax      Gauge32,
       acKpiCoderStatsIntervalGlobalCoderAMRWBAvg      Gauge32,
       acKpiCoderStatsIntervalGlobalCoderAMRWBMax      Gauge32,
       acKpiCoderStatsIntervalGlobalCoderT38Avg        Gauge32,
       acKpiCoderStatsIntervalGlobalCoderT38Max        Gauge32,
       acKpiCoderStatsIntervalGlobalCoderSILKNBAvg     Gauge32,
       acKpiCoderStatsIntervalGlobalCoderSILKNBMax     Gauge32,
       acKpiCoderStatsIntervalGlobalCoderSILKWBAvg     Gauge32,
       acKpiCoderStatsIntervalGlobalCoderSILKWBMax     Gauge32,
       acKpiCoderStatsIntervalGlobalCoderOPUSNBAvg     Gauge32,
       acKpiCoderStatsIntervalGlobalCoderOPUSNBMax     Gauge32,
       acKpiCoderStatsIntervalGlobalCoderOPUSWBAvg     Gauge32,
       acKpiCoderStatsIntervalGlobalCoderOPUSWBMax     Gauge32,
       acKpiCoderStatsIntervalGlobalCoderRTAAvg        Gauge32,
       acKpiCoderStatsIntervalGlobalCoderRTAMax        Gauge32,
       acKpiCoderStatsIntervalGlobalCoderOtherAvg      Gauge32,
       acKpiCoderStatsIntervalGlobalCoderOtherMax      Gauge32
     }



     acKpiCoderStatsIntervalGlobalInterval OBJECT-TYPE
       SYNTAX Unsigned32 (1..200)
       MAX-ACCESS not-accessible
       STATUS current
       DESCRIPTION
           "
AC INI-Param: N/A"
       ::= {acKpiCoderStatsIntervalGlobalEntry 1}



     acKpiCoderStatsIntervalGlobalCoderG711Avg OBJECT-TYPE
       SYNTAX Gauge32
       MAX-ACCESS read-only
       STATUS current
       DESCRIPTION
           "Number of active channels with G.711 coder.
AC INI-Param: N/A"
       ::= {acKpiCoderStatsIntervalGlobalEntry 2}



     acKpiCoderStatsIntervalGlobalCoderG711Max OBJECT-TYPE
       SYNTAX Gauge32
       MAX-ACCESS read-only
       STATUS current
       DESCRIPTION
           "Maximum number of active channels with G.711 coder.
AC INI-Param: N/A"
       ::= {acKpiCoderStatsIntervalGlobalEntry 3}



     acKpiCoderStatsIntervalGlobalCoderG711alawAvg OBJECT-TYPE
       SYNTAX Gauge32
       MAX-ACCESS read-only
       STATUS current
       DESCRIPTION
           "Average number of active channels with G.711alaw coder.
AC INI-Param: N/A"
       ::= {acKpiCoderStatsIntervalGlobalEntry 4}



     acKpiCoderStatsIntervalGlobalCoderG711alawMax OBJECT-TYPE
       SYNTAX Gauge32
       MAX-ACCESS read-only
       STATUS current
       DESCRIPTION
           "Maximum number of active channels with G.711alaw coder.
AC INI-Param: N/A"
       ::= {acKpiCoderStatsIntervalGlobalEntry 5}



     acKpiCoderStatsIntervalGlobalCoderG711ulawAvg OBJECT-TYPE
       SYNTAX Gauge32
       MAX-ACCESS read-only
       STATUS current
       DESCRIPTION
           "Average number of active channels with G.711ulaw coder.
AC INI-Param: N/A"
       ::= {acKpiCoderStatsIntervalGlobalEntry 6}



     acKpiCoderStatsIntervalGlobalCoderG711ulawMax OBJECT-TYPE
       SYNTAX Gauge32
       MAX-ACCESS read-only
       STATUS current
       DESCRIPTION
           "Maximum number of active channels with G.711ulaw coder.
AC INI-Param: N/A"
       ::= {acKpiCoderStatsIntervalGlobalEntry 7}



     acKpiCoderStatsIntervalGlobalCoderG722Avg OBJECT-TYPE
       SYNTAX Gauge32
       MAX-ACCESS read-only
       STATUS current
       DESCRIPTION
           "Average number of active channels with G.722 coder.
AC INI-Param: N/A"
       ::= {acKpiCoderStatsIntervalGlobalEntry 8}



     acKpiCoderStatsIntervalGlobalCoderG722Max OBJECT-TYPE
       SYNTAX Gauge32
       MAX-ACCESS read-only
       STATUS current
       DESCRIPTION
           "Maximum number of active channels with G.722 coder.
AC INI-Param: N/A"
       ::= {acKpiCoderStatsIntervalGlobalEntry 9}



     acKpiCoderStatsIntervalGlobalCoderG723Avg OBJECT-TYPE
       SYNTAX Gauge32
       MAX-ACCESS read-only
       STATUS current
       DESCRIPTION
           "Average number of active channels with G.723 coder.
AC INI-Param: N/A"
       ::= {acKpiCoderStatsIntervalGlobalEntry 10}



     acKpiCoderStatsIntervalGlobalCoderG723Max OBJECT-TYPE
       SYNTAX Gauge32
       MAX-ACCESS read-only
       STATUS current
       DESCRIPTION
           "Maximum number of active channels with G.723 coder.
AC INI-Param: N/A"
       ::= {acKpiCoderStatsIntervalGlobalEntry 11}



     acKpiCoderStatsIntervalGlobalCoderG726Avg OBJECT-TYPE
       SYNTAX Gauge32
       MAX-ACCESS read-only
       STATUS current
       DESCRIPTION
           "Average number of active channels with G.726 coder.
AC INI-Param: N/A"
       ::= {acKpiCoderStatsIntervalGlobalEntry 12}



     acKpiCoderStatsIntervalGlobalCoderG726Max OBJECT-TYPE
       SYNTAX Gauge32
       MAX-ACCESS read-only
       STATUS current
       DESCRIPTION
           "Maximum number of active channels with G.726 coder.
AC INI-Param: N/A"
       ::= {acKpiCoderStatsIntervalGlobalEntry 13}



     acKpiCoderStatsIntervalGlobalCoderG729Avg OBJECT-TYPE
       SYNTAX Gauge32
       MAX-ACCESS read-only
       STATUS current
       DESCRIPTION
           "Average number of active channels with G.729 coder.
AC INI-Param: N/A"
       ::= {acKpiCoderStatsIntervalGlobalEntry 14}



     acKpiCoderStatsIntervalGlobalCoderG729Max OBJECT-TYPE
       SYNTAX Gauge32
       MAX-ACCESS read-only
       STATUS current
       DESCRIPTION
           "Maximum number of active channels with G.729 coder.
AC INI-Param: N/A"
       ::= {acKpiCoderStatsIntervalGlobalEntry 15}



     acKpiCoderStatsIntervalGlobalCoderG729EVAvg OBJECT-TYPE
       SYNTAX Gauge32
       MAX-ACCESS read-only
       STATUS current
       DESCRIPTION
           "Average number of active channels with G.729EV coder.
AC INI-Param: N/A"
       ::= {acKpiCoderStatsIntervalGlobalEntry 16}



     acKpiCoderStatsIntervalGlobalCoderG729EVMax OBJECT-TYPE
       SYNTAX Gauge32
       MAX-ACCESS read-only
       STATUS current
       DESCRIPTION
           "Maximum number of active channels with G.729EV coder.
AC INI-Param: N/A"
       ::= {acKpiCoderStatsIntervalGlobalEntry 17}



     acKpiCoderStatsIntervalGlobalCoderGSMFRAvg OBJECT-TYPE
       SYNTAX Gauge32
       MAX-ACCESS read-only
       STATUS current
       DESCRIPTION
           "Average number of active channels with GSM-FR coder.
AC INI-Param: N/A"
       ::= {acKpiCoderStatsIntervalGlobalEntry 18}



     acKpiCoderStatsIntervalGlobalCoderGSMFRMax OBJECT-TYPE
       SYNTAX Gauge32
       MAX-ACCESS read-only
       STATUS current
       DESCRIPTION
           "Maximum number of active channels with GSM-FR coder.
AC INI-Param: N/A"
       ::= {acKpiCoderStatsIntervalGlobalEntry 19}



     acKpiCoderStatsIntervalGlobalCoderGSMEFRAvg OBJECT-TYPE
       SYNTAX Gauge32
       MAX-ACCESS read-only
       STATUS current
       DESCRIPTION
           "Average number of active channels with GSM-EFR coder.
AC INI-Param: N/A"
       ::= {acKpiCoderStatsIntervalGlobalEntry 20}



     acKpiCoderStatsIntervalGlobalCoderGSMEFRMax OBJECT-TYPE
       SYNTAX Gauge32
       MAX-ACCESS read-only
       STATUS current
       DESCRIPTION
           "Maximum number of active channels with GSM-EFR coder.
AC INI-Param: N/A"
       ::= {acKpiCoderStatsIntervalGlobalEntry 21}



     acKpiCoderStatsIntervalGlobalCoderILBCAvg OBJECT-TYPE
       SYNTAX Gauge32
       MAX-ACCESS read-only
       STATUS current
       DESCRIPTION
           "Average number of active channels with iLBC coder.
AC INI-Param: N/A"
       ::= {acKpiCoderStatsIntervalGlobalEntry 22}



     acKpiCoderStatsIntervalGlobalCoderILBCMax OBJECT-TYPE
       SYNTAX Gauge32
       MAX-ACCESS read-only
       STATUS current
       DESCRIPTION
           "Maximum number of active channels with iLBC coder.
AC INI-Param: N/A"
       ::= {acKpiCoderStatsIntervalGlobalEntry 23}



     acKpiCoderStatsIntervalGlobalCoderEVRCAvg OBJECT-TYPE
       SYNTAX Gauge32
       MAX-ACCESS read-only
       STATUS current
       DESCRIPTION
           "Average number of active channels with EVRC coder.
AC INI-Param: N/A"
       ::= {acKpiCoderStatsIntervalGlobalEntry 24}



     acKpiCoderStatsIntervalGlobalCoderEVRCMax OBJECT-TYPE
       SYNTAX Gauge32
       MAX-ACCESS read-only
       STATUS current
       DESCRIPTION
           "Maximum number of active channels with EVRC coder.
AC INI-Param: N/A"
       ::= {acKpiCoderStatsIntervalGlobalEntry 25}



     acKpiCoderStatsIntervalGlobalCoderQCELPAvg OBJECT-TYPE
       SYNTAX Gauge32
       MAX-ACCESS read-only
       STATUS current
       DESCRIPTION
           "Average number of active channels with QCELP coder.
AC INI-Param: N/A"
       ::= {acKpiCoderStatsIntervalGlobalEntry 26}



     acKpiCoderStatsIntervalGlobalCoderQCELPMax OBJECT-TYPE
       SYNTAX Gauge32
       MAX-ACCESS read-only
       STATUS current
       DESCRIPTION
           "Maximum number of active channels with QCELP coder.
AC INI-Param: N/A"
       ::= {acKpiCoderStatsIntervalGlobalEntry 27}



     acKpiCoderStatsIntervalGlobalCoderAMRNBAvg OBJECT-TYPE
       SYNTAX Gauge32
       MAX-ACCESS read-only
       STATUS current
       DESCRIPTION
           "Average number of active channels with AMR-NB coder.
AC INI-Param: N/A"
       ::= {acKpiCoderStatsIntervalGlobalEntry 28}



     acKpiCoderStatsIntervalGlobalCoderAMRNBMax OBJECT-TYPE
       SYNTAX Gauge32
       MAX-ACCESS read-only
       STATUS current
       DESCRIPTION
           "Maximum number of active channels with AMR-NB coder.
AC INI-Param: N/A"
       ::= {acKpiCoderStatsIntervalGlobalEntry 29}



     acKpiCoderStatsIntervalGlobalCoderAMRWBAvg OBJECT-TYPE
       SYNTAX Gauge32
       MAX-ACCESS read-only
       STATUS current
       DESCRIPTION
           "Average number of active channels with AMR-WB coder.
AC INI-Param: N/A"
       ::= {acKpiCoderStatsIntervalGlobalEntry 30}



     acKpiCoderStatsIntervalGlobalCoderAMRWBMax OBJECT-TYPE
       SYNTAX Gauge32
       MAX-ACCESS read-only
       STATUS current
       DESCRIPTION
           "Maximum number of active channels with AMR-WB coder.
AC INI-Param: N/A"
       ::= {acKpiCoderStatsIntervalGlobalEntry 31}



     acKpiCoderStatsIntervalGlobalCoderT38Avg OBJECT-TYPE
       SYNTAX Gauge32
       MAX-ACCESS read-only
       STATUS current
       DESCRIPTION
           "Average number of active channels with T.38 coder.
AC INI-Param: N/A"
       ::= {acKpiCoderStatsIntervalGlobalEntry 32}



     acKpiCoderStatsIntervalGlobalCoderT38Max OBJECT-TYPE
       SYNTAX Gauge32
       MAX-ACCESS read-only
       STATUS current
       DESCRIPTION
           "Maximum number of active channels with T.38 coder.
AC INI-Param: N/A"
       ::= {acKpiCoderStatsIntervalGlobalEntry 33}



     acKpiCoderStatsIntervalGlobalCoderSILKNBAvg OBJECT-TYPE
       SYNTAX Gauge32
       MAX-ACCESS read-only
       STATUS current
       DESCRIPTION
           "Average number of active channels with SILK-NB coder.
AC INI-Param: N/A"
       ::= {acKpiCoderStatsIntervalGlobalEntry 34}



     acKpiCoderStatsIntervalGlobalCoderSILKNBMax OBJECT-TYPE
       SYNTAX Gauge32
       MAX-ACCESS read-only
       STATUS current
       DESCRIPTION
           "Maximum number of active channels with SILK-NB coder.
AC INI-Param: N/A"
       ::= {acKpiCoderStatsIntervalGlobalEntry 35}



     acKpiCoderStatsIntervalGlobalCoderSILKWBAvg OBJECT-TYPE
       SYNTAX Gauge32
       MAX-ACCESS read-only
       STATUS current
       DESCRIPTION
           "Average number of active channels with SILK-WB coder.
AC INI-Param: N/A"
       ::= {acKpiCoderStatsIntervalGlobalEntry 36}



     acKpiCoderStatsIntervalGlobalCoderSILKWBMax OBJECT-TYPE
       SYNTAX Gauge32
       MAX-ACCESS read-only
       STATUS current
       DESCRIPTION
           "Maximum number of active channels with SILK-WB coder.
AC INI-Param: N/A"
       ::= {acKpiCoderStatsIntervalGlobalEntry 37}



     acKpiCoderStatsIntervalGlobalCoderOPUSNBAvg OBJECT-TYPE
       SYNTAX Gauge32
       MAX-ACCESS read-only
       STATUS current
       DESCRIPTION
           "Average number of active channels with OPUS-NB coder.
AC INI-Param: N/A"
       ::= {acKpiCoderStatsIntervalGlobalEntry 38}



     acKpiCoderStatsIntervalGlobalCoderOPUSNBMax OBJECT-TYPE
       SYNTAX Gauge32
       MAX-ACCESS read-only
       STATUS current
       DESCRIPTION
           "Maximum number of active channels with OPUS-NB coder.
AC INI-Param: N/A"
       ::= {acKpiCoderStatsIntervalGlobalEntry 39}



     acKpiCoderStatsIntervalGlobalCoderOPUSWBAvg OBJECT-TYPE
       SYNTAX Gauge32
       MAX-ACCESS read-only
       STATUS current
       DESCRIPTION
           "Average number of active channels with OPUS-WB coder.
AC INI-Param: N/A"
       ::= {acKpiCoderStatsIntervalGlobalEntry 40}



     acKpiCoderStatsIntervalGlobalCoderOPUSWBMax OBJECT-TYPE
       SYNTAX Gauge32
       MAX-ACCESS read-only
       STATUS current
       DESCRIPTION
           "Maximum number of active channels with OPUS-WB coder.
AC INI-Param: N/A"
       ::= {acKpiCoderStatsIntervalGlobalEntry 41}



     acKpiCoderStatsIntervalGlobalCoderRTAAvg OBJECT-TYPE
       SYNTAX Gauge32
       MAX-ACCESS read-only
       STATUS current
       DESCRIPTION
           "Average number of active channels with RTA coder.
AC INI-Param: N/A"
       ::= {acKpiCoderStatsIntervalGlobalEntry 42}



     acKpiCoderStatsIntervalGlobalCoderRTAMax OBJECT-TYPE
       SYNTAX Gauge32
       MAX-ACCESS read-only
       STATUS current
       DESCRIPTION
           "Maximum number of active channels with RTA coder.
AC INI-Param: N/A"
       ::= {acKpiCoderStatsIntervalGlobalEntry 43}



     acKpiCoderStatsIntervalGlobalCoderOtherAvg OBJECT-TYPE
       SYNTAX Gauge32
       MAX-ACCESS read-only
       STATUS current
       DESCRIPTION
           "Average number of active channels with other coders.
AC INI-Param: N/A"
       ::= {acKpiCoderStatsIntervalGlobalEntry 44}



     acKpiCoderStatsIntervalGlobalCoderOtherMax OBJECT-TYPE
       SYNTAX Gauge32
       MAX-ACCESS read-only
       STATUS current
       DESCRIPTION
           "Maximum number of active channels with other coders.
AC INI-Param: N/A"
       ::= {acKpiCoderStatsIntervalGlobalEntry 45}



     acKpiCoderStatsIntervalTables OBJECT IDENTIFIER ::= {acKpiCoderStatsInterval 2}


     -- ****************************************
     -- acKpiCoderStatsIntervalIpGroup table declaration
     -- ****************************************
     acKpiCoderStatsIntervalIpGroupTable OBJECT-TYPE
       SYNTAX SEQUENCE OF AcKpiCoderStatsIntervalIpGroupEntry
       MAX-ACCESS not-accessible
       STATUS current
       DESCRIPTION
           ""
       ::= {acKpiCoderStatsIntervalTables 1}



     -- ****************************************
     -- acKpiCoderStatsIntervalIpGroup table entry
     -- ****************************************
     acKpiCoderStatsIntervalIpGroupEntry OBJECT-TYPE
       SYNTAX AcKpiCoderStatsIntervalIpGroupEntry
       MAX-ACCESS not-accessible
       STATUS current
       DESCRIPTION
           ""
       INDEX {acKpiCoderStatsIntervalIpGroupIndex,acKpiCoderStatsIntervalIpGroupInterval}
       ::= {acKpiCoderStatsIntervalIpGroupTable 1}



     -- ****************************************
     -- acKpiCoderStatsIntervalIpGroup TABLE
     -- ****************************************
     AcKpiCoderStatsIntervalIpGroupEntry ::= SEQUENCE {
       acKpiCoderStatsIntervalIpGroupIndex             Unsigned32,
       acKpiCoderStatsIntervalIpGroupInterval          Unsigned32,
       acKpiCoderStatsIntervalIpGroupCoderG711Avg      Gauge32,
       acKpiCoderStatsIntervalIpGroupCoderG711Max      Gauge32,
       acKpiCoderStatsIntervalIpGroupCoderG711alawAvg  Gauge32,
       acKpiCoderStatsIntervalIpGroupCoderG711alawMax  Gauge32,
       acKpiCoderStatsIntervalIpGroupCoderG711ulawAvg  Gauge32,
       acKpiCoderStatsIntervalIpGroupCoderG711ulawMax  Gauge32,
       acKpiCoderStatsIntervalIpGroupCoderG722Avg      Gauge32,
       acKpiCoderStatsIntervalIpGroupCoderG722Max      Gauge32,
       acKpiCoderStatsIntervalIpGroupCoderG723Avg      Gauge32,
       acKpiCoderStatsIntervalIpGroupCoderG723Max      Gauge32,
       acKpiCoderStatsIntervalIpGroupCoderG726Avg      Gauge32,
       acKpiCoderStatsIntervalIpGroupCoderG726Max      Gauge32,
       acKpiCoderStatsIntervalIpGroupCoderG729Avg      Gauge32,
       acKpiCoderStatsIntervalIpGroupCoderG729Max      Gauge32,
       acKpiCoderStatsIntervalIpGroupCoderG729EVAvg    Gauge32,
       acKpiCoderStatsIntervalIpGroupCoderG729EVMax    Gauge32,
       acKpiCoderStatsIntervalIpGroupCoderGSMFRAvg     Gauge32,
       acKpiCoderStatsIntervalIpGroupCoderGSMFRMax     Gauge32,
       acKpiCoderStatsIntervalIpGroupCoderGSMEFRAvg    Gauge32,
       acKpiCoderStatsIntervalIpGroupCoderGSMEFRMax    Gauge32,
       acKpiCoderStatsIntervalIpGroupCoderILBCAvg      Gauge32,
       acKpiCoderStatsIntervalIpGroupCoderILBCMax      Gauge32,
       acKpiCoderStatsIntervalIpGroupCoderEVRCAvg      Gauge32,
       acKpiCoderStatsIntervalIpGroupCoderEVRCMax      Gauge32,
       acKpiCoderStatsIntervalIpGroupCoderQCELPAvg     Gauge32,
       acKpiCoderStatsIntervalIpGroupCoderQCELPMax     Gauge32,
       acKpiCoderStatsIntervalIpGroupCoderAMRNBAvg     Gauge32,
       acKpiCoderStatsIntervalIpGroupCoderAMRNBMax     Gauge32,
       acKpiCoderStatsIntervalIpGroupCoderAMRWBAvg     Gauge32,
       acKpiCoderStatsIntervalIpGroupCoderAMRWBMax     Gauge32,
       acKpiCoderStatsIntervalIpGroupCoderT38Avg       Gauge32,
       acKpiCoderStatsIntervalIpGroupCoderT38Max       Gauge32,
       acKpiCoderStatsIntervalIpGroupCoderSILKNBAvg    Gauge32,
       acKpiCoderStatsIntervalIpGroupCoderSILKNBMax    Gauge32,
       acKpiCoderStatsIntervalIpGroupCoderSILKWBAvg    Gauge32,
       acKpiCoderStatsIntervalIpGroupCoderSILKWBMax    Gauge32,
       acKpiCoderStatsIntervalIpGroupCoderOPUSNBAvg    Gauge32,
       acKpiCoderStatsIntervalIpGroupCoderOPUSNBMax    Gauge32,
       acKpiCoderStatsIntervalIpGroupCoderOPUSWBAvg    Gauge32,
       acKpiCoderStatsIntervalIpGroupCoderOPUSWBMax    Gauge32,
       acKpiCoderStatsIntervalIpGroupCoderRTAAvg       Gauge32,
       acKpiCoderStatsIntervalIpGroupCoderRTAMax       Gauge32,
       acKpiCoderStatsIntervalIpGroupCoderOtherAvg     Gauge32,
       acKpiCoderStatsIntervalIpGroupCoderOtherMax     Gauge32
     }



     acKpiCoderStatsIntervalIpGroupIndex OBJECT-TYPE
       SYNTAX Unsigned32 (0..32767)
       MAX-ACCESS not-accessible
       STATUS current
       DESCRIPTION
           "
AC INI-Param: N/A"
       ::= {acKpiCoderStatsIntervalIpGroupEntry 1}



     acKpiCoderStatsIntervalIpGroupInterval OBJECT-TYPE
       SYNTAX Unsigned32 (1..200)
       MAX-ACCESS not-accessible
       STATUS current
       DESCRIPTION
           "
AC INI-Param: N/A"
       ::= {acKpiCoderStatsIntervalIpGroupEntry 2}



     acKpiCoderStatsIntervalIpGroupCoderG711Avg OBJECT-TYPE
       SYNTAX Gauge32
       MAX-ACCESS read-only
       STATUS current
       DESCRIPTION
           "Number of active channels with G.711 coder.
AC INI-Param: N/A"
       ::= {acKpiCoderStatsIntervalIpGroupEntry 3}



     acKpiCoderStatsIntervalIpGroupCoderG711Max OBJECT-TYPE
       SYNTAX Gauge32
       MAX-ACCESS read-only
       STATUS current
       DESCRIPTION
           "Maximum number of active channels with G.711 coder.
AC INI-Param: N/A"
       ::= {acKpiCoderStatsIntervalIpGroupEntry 4}



     acKpiCoderStatsIntervalIpGroupCoderG711alawAvg OBJECT-TYPE
       SYNTAX Gauge32
       MAX-ACCESS read-only
       STATUS current
       DESCRIPTION
           "Average number of active channels with G.711alaw coder.
AC INI-Param: N/A"
       ::= {acKpiCoderStatsIntervalIpGroupEntry 5}



     acKpiCoderStatsIntervalIpGroupCoderG711alawMax OBJECT-TYPE
       SYNTAX Gauge32
       MAX-ACCESS read-only
       STATUS current
       DESCRIPTION
           "Maximum number of active channels with G.711alaw coder.
AC INI-Param: N/A"
       ::= {acKpiCoderStatsIntervalIpGroupEntry 6}



     acKpiCoderStatsIntervalIpGroupCoderG711ulawAvg OBJECT-TYPE
       SYNTAX Gauge32
       MAX-ACCESS read-only
       STATUS current
       DESCRIPTION
           "Average number of active channels with G.711ulaw coder.
AC INI-Param: N/A"
       ::= {acKpiCoderStatsIntervalIpGroupEntry 7}



     acKpiCoderStatsIntervalIpGroupCoderG711ulawMax OBJECT-TYPE
       SYNTAX Gauge32
       MAX-ACCESS read-only
       STATUS current
       DESCRIPTION
           "Maximum number of active channels with G.711ulaw coder.
AC INI-Param: N/A"
       ::= {acKpiCoderStatsIntervalIpGroupEntry 8}



     acKpiCoderStatsIntervalIpGroupCoderG722Avg OBJECT-TYPE
       SYNTAX Gauge32
       MAX-ACCESS read-only
       STATUS current
       DESCRIPTION
           "Average number of active channels with G.722 coder.
AC INI-Param: N/A"
       ::= {acKpiCoderStatsIntervalIpGroupEntry 9}



     acKpiCoderStatsIntervalIpGroupCoderG722Max OBJECT-TYPE
       SYNTAX Gauge32
       MAX-ACCESS read-only
       STATUS current
       DESCRIPTION
           "Maximum number of active channels with G.722 coder.
AC INI-Param: N/A"
       ::= {acKpiCoderStatsIntervalIpGroupEntry 10}



     acKpiCoderStatsIntervalIpGroupCoderG723Avg OBJECT-TYPE
       SYNTAX Gauge32
       MAX-ACCESS read-only
       STATUS current
       DESCRIPTION
           "Average number of active channels with G.723 coder.
AC INI-Param: N/A"
       ::= {acKpiCoderStatsIntervalIpGroupEntry 11}



     acKpiCoderStatsIntervalIpGroupCoderG723Max OBJECT-TYPE
       SYNTAX Gauge32
       MAX-ACCESS read-only
       STATUS current
       DESCRIPTION
           "Maximum number of active channels with G.723 coder.
AC INI-Param: N/A"
       ::= {acKpiCoderStatsIntervalIpGroupEntry 12}



     acKpiCoderStatsIntervalIpGroupCoderG726Avg OBJECT-TYPE
       SYNTAX Gauge32
       MAX-ACCESS read-only
       STATUS current
       DESCRIPTION
           "Average number of active channels with G.726 coder.
AC INI-Param: N/A"
       ::= {acKpiCoderStatsIntervalIpGroupEntry 13}



     acKpiCoderStatsIntervalIpGroupCoderG726Max OBJECT-TYPE
       SYNTAX Gauge32
       MAX-ACCESS read-only
       STATUS current
       DESCRIPTION
           "Maximum number of active channels with G.726 coder.
AC INI-Param: N/A"
       ::= {acKpiCoderStatsIntervalIpGroupEntry 14}



     acKpiCoderStatsIntervalIpGroupCoderG729Avg OBJECT-TYPE
       SYNTAX Gauge32
       MAX-ACCESS read-only
       STATUS current
       DESCRIPTION
           "Average number of active channels with G.729 coder.
AC INI-Param: N/A"
       ::= {acKpiCoderStatsIntervalIpGroupEntry 15}



     acKpiCoderStatsIntervalIpGroupCoderG729Max OBJECT-TYPE
       SYNTAX Gauge32
       MAX-ACCESS read-only
       STATUS current
       DESCRIPTION
           "Maximum number of active channels with G.729 coder.
AC INI-Param: N/A"
       ::= {acKpiCoderStatsIntervalIpGroupEntry 16}



     acKpiCoderStatsIntervalIpGroupCoderG729EVAvg OBJECT-TYPE
       SYNTAX Gauge32
       MAX-ACCESS read-only
       STATUS current
       DESCRIPTION
           "Average number of active channels with G.729EV coder.
AC INI-Param: N/A"
       ::= {acKpiCoderStatsIntervalIpGroupEntry 17}



     acKpiCoderStatsIntervalIpGroupCoderG729EVMax OBJECT-TYPE
       SYNTAX Gauge32
       MAX-ACCESS read-only
       STATUS current
       DESCRIPTION
           "Maximum number of active channels with G.729EV coder.
AC INI-Param: N/A"
       ::= {acKpiCoderStatsIntervalIpGroupEntry 18}



     acKpiCoderStatsIntervalIpGroupCoderGSMFRAvg OBJECT-TYPE
       SYNTAX Gauge32
       MAX-ACCESS read-only
       STATUS current
       DESCRIPTION
           "Average number of active channels with GSM-FR coder.
AC INI-Param: N/A"
       ::= {acKpiCoderStatsIntervalIpGroupEntry 19}



     acKpiCoderStatsIntervalIpGroupCoderGSMFRMax OBJECT-TYPE
       SYNTAX Gauge32
       MAX-ACCESS read-only
       STATUS current
       DESCRIPTION
           "Maximum number of active channels with GSM-FR coder.
AC INI-Param: N/A"
       ::= {acKpiCoderStatsIntervalIpGroupEntry 20}



     acKpiCoderStatsIntervalIpGroupCoderGSMEFRAvg OBJECT-TYPE
       SYNTAX Gauge32
       MAX-ACCESS read-only
       STATUS current
       DESCRIPTION
           "Average number of active channels with GSM-EFR coder.
AC INI-Param: N/A"
       ::= {acKpiCoderStatsIntervalIpGroupEntry 21}



     acKpiCoderStatsIntervalIpGroupCoderGSMEFRMax OBJECT-TYPE
       SYNTAX Gauge32
       MAX-ACCESS read-only
       STATUS current
       DESCRIPTION
           "Maximum number of active channels with GSM-EFR coder.
AC INI-Param: N/A"
       ::= {acKpiCoderStatsIntervalIpGroupEntry 22}



     acKpiCoderStatsIntervalIpGroupCoderILBCAvg OBJECT-TYPE
       SYNTAX Gauge32
       MAX-ACCESS read-only
       STATUS current
       DESCRIPTION
           "Average number of active channels with iLBC coder.
AC INI-Param: N/A"
       ::= {acKpiCoderStatsIntervalIpGroupEntry 23}



     acKpiCoderStatsIntervalIpGroupCoderILBCMax OBJECT-TYPE
       SYNTAX Gauge32
       MAX-ACCESS read-only
       STATUS current
       DESCRIPTION
           "Maximum number of active channels with iLBC coder.
AC INI-Param: N/A"
       ::= {acKpiCoderStatsIntervalIpGroupEntry 24}



     acKpiCoderStatsIntervalIpGroupCoderEVRCAvg OBJECT-TYPE
       SYNTAX Gauge32
       MAX-ACCESS read-only
       STATUS current
       DESCRIPTION
           "Average number of active channels with EVRC coder.
AC INI-Param: N/A"
       ::= {acKpiCoderStatsIntervalIpGroupEntry 25}



     acKpiCoderStatsIntervalIpGroupCoderEVRCMax OBJECT-TYPE
       SYNTAX Gauge32
       MAX-ACCESS read-only
       STATUS current
       DESCRIPTION
           "Maximum number of active channels with EVRC coder.
AC INI-Param: N/A"
       ::= {acKpiCoderStatsIntervalIpGroupEntry 26}



     acKpiCoderStatsIntervalIpGroupCoderQCELPAvg OBJECT-TYPE
       SYNTAX Gauge32
       MAX-ACCESS read-only
       STATUS current
       DESCRIPTION
           "Average number of active channels with QCELP coder.
AC INI-Param: N/A"
       ::= {acKpiCoderStatsIntervalIpGroupEntry 27}



     acKpiCoderStatsIntervalIpGroupCoderQCELPMax OBJECT-TYPE
       SYNTAX Gauge32
       MAX-ACCESS read-only
       STATUS current
       DESCRIPTION
           "Maximum number of active channels with QCELP coder.
AC INI-Param: N/A"
       ::= {acKpiCoderStatsIntervalIpGroupEntry 28}



     acKpiCoderStatsIntervalIpGroupCoderAMRNBAvg OBJECT-TYPE
       SYNTAX Gauge32
       MAX-ACCESS read-only
       STATUS current
       DESCRIPTION
           "Average number of active channels with AMR-NB coder.
AC INI-Param: N/A"
       ::= {acKpiCoderStatsIntervalIpGroupEntry 29}



     acKpiCoderStatsIntervalIpGroupCoderAMRNBMax OBJECT-TYPE
       SYNTAX Gauge32
       MAX-ACCESS read-only
       STATUS current
       DESCRIPTION
           "Maximum number of active channels with AMR-NB coder.
AC INI-Param: N/A"
       ::= {acKpiCoderStatsIntervalIpGroupEntry 30}



     acKpiCoderStatsIntervalIpGroupCoderAMRWBAvg OBJECT-TYPE
       SYNTAX Gauge32
       MAX-ACCESS read-only
       STATUS current
       DESCRIPTION
           "Average number of active channels with AMR-WB coder.
AC INI-Param: N/A"
       ::= {acKpiCoderStatsIntervalIpGroupEntry 31}



     acKpiCoderStatsIntervalIpGroupCoderAMRWBMax OBJECT-TYPE
       SYNTAX Gauge32
       MAX-ACCESS read-only
       STATUS current
       DESCRIPTION
           "Maximum number of active channels with AMR-WB coder.
AC INI-Param: N/A"
       ::= {acKpiCoderStatsIntervalIpGroupEntry 32}



     acKpiCoderStatsIntervalIpGroupCoderT38Avg OBJECT-TYPE
       SYNTAX Gauge32
       MAX-ACCESS read-only
       STATUS current
       DESCRIPTION
           "Average number of active channels with T.38 coder.
AC INI-Param: N/A"
       ::= {acKpiCoderStatsIntervalIpGroupEntry 33}



     acKpiCoderStatsIntervalIpGroupCoderT38Max OBJECT-TYPE
       SYNTAX Gauge32
       MAX-ACCESS read-only
       STATUS current
       DESCRIPTION
           "Maximum number of active channels with T.38 coder.
AC INI-Param: N/A"
       ::= {acKpiCoderStatsIntervalIpGroupEntry 34}



     acKpiCoderStatsIntervalIpGroupCoderSILKNBAvg OBJECT-TYPE
       SYNTAX Gauge32
       MAX-ACCESS read-only
       STATUS current
       DESCRIPTION
           "Average number of active channels with SILK-NB coder.
AC INI-Param: N/A"
       ::= {acKpiCoderStatsIntervalIpGroupEntry 35}



     acKpiCoderStatsIntervalIpGroupCoderSILKNBMax OBJECT-TYPE
       SYNTAX Gauge32
       MAX-ACCESS read-only
       STATUS current
       DESCRIPTION
           "Maximum number of active channels with SILK-NB coder.
AC INI-Param: N/A"
       ::= {acKpiCoderStatsIntervalIpGroupEntry 36}



     acKpiCoderStatsIntervalIpGroupCoderSILKWBAvg OBJECT-TYPE
       SYNTAX Gauge32
       MAX-ACCESS read-only
       STATUS current
       DESCRIPTION
           "Average number of active channels with SILK-WB coder.
AC INI-Param: N/A"
       ::= {acKpiCoderStatsIntervalIpGroupEntry 37}



     acKpiCoderStatsIntervalIpGroupCoderSILKWBMax OBJECT-TYPE
       SYNTAX Gauge32
       MAX-ACCESS read-only
       STATUS current
       DESCRIPTION
           "Maximum number of active channels with SILK-WB coder.
AC INI-Param: N/A"
       ::= {acKpiCoderStatsIntervalIpGroupEntry 38}



     acKpiCoderStatsIntervalIpGroupCoderOPUSNBAvg OBJECT-TYPE
       SYNTAX Gauge32
       MAX-ACCESS read-only
       STATUS current
       DESCRIPTION
           "Average number of active channels with OPUS-NB coder.
AC INI-Param: N/A"
       ::= {acKpiCoderStatsIntervalIpGroupEntry 39}



     acKpiCoderStatsIntervalIpGroupCoderOPUSNBMax OBJECT-TYPE
       SYNTAX Gauge32
       MAX-ACCESS read-only
       STATUS current
       DESCRIPTION
           "Maximum number of active channels with OPUS-NB coder.
AC INI-Param: N/A"
       ::= {acKpiCoderStatsIntervalIpGroupEntry 40}



     acKpiCoderStatsIntervalIpGroupCoderOPUSWBAvg OBJECT-TYPE
       SYNTAX Gauge32
       MAX-ACCESS read-only
       STATUS current
       DESCRIPTION
           "Average number of active channels with OPUS-WB coder.
AC INI-Param: N/A"
       ::= {acKpiCoderStatsIntervalIpGroupEntry 41}



     acKpiCoderStatsIntervalIpGroupCoderOPUSWBMax OBJECT-TYPE
       SYNTAX Gauge32
       MAX-ACCESS read-only
       STATUS current
       DESCRIPTION
           "Maximum number of active channels with OPUS-WB coder.
AC INI-Param: N/A"
       ::= {acKpiCoderStatsIntervalIpGroupEntry 42}



     acKpiCoderStatsIntervalIpGroupCoderRTAAvg OBJECT-TYPE
       SYNTAX Gauge32
       MAX-ACCESS read-only
       STATUS current
       DESCRIPTION
           "Average number of active channels with RTA coder.
AC INI-Param: N/A"
       ::= {acKpiCoderStatsIntervalIpGroupEntry 43}



     acKpiCoderStatsIntervalIpGroupCoderRTAMax OBJECT-TYPE
       SYNTAX Gauge32
       MAX-ACCESS read-only
       STATUS current
       DESCRIPTION
           "Maximum number of active channels with RTA coder.
AC INI-Param: N/A"
       ::= {acKpiCoderStatsIntervalIpGroupEntry 44}



     acKpiCoderStatsIntervalIpGroupCoderOtherAvg OBJECT-TYPE
       SYNTAX Gauge32
       MAX-ACCESS read-only
       STATUS current
       DESCRIPTION
           "Average number of active channels with other coders.
AC INI-Param: N/A"
       ::= {acKpiCoderStatsIntervalIpGroupEntry 45}



     acKpiCoderStatsIntervalIpGroupCoderOtherMax OBJECT-TYPE
       SYNTAX Gauge32
       MAX-ACCESS read-only
       STATUS current
       DESCRIPTION
           "Maximum number of active channels with other coders.
AC INI-Param: N/A"
       ::= {acKpiCoderStatsIntervalIpGroupEntry 46}



     acKpiNetwork OBJECT IDENTIFIER ::= {acKpi 6}


     acKpiDdosStats OBJECT IDENTIFIER ::= {acKpiNetwork 1}


     acKpiDdosStatsCurrent OBJECT IDENTIFIER ::= {acKpiDdosStats 1}


     acKpiDdosStatsCurrentGlobal OBJECT IDENTIFIER ::= {acKpiDdosStatsCurrent 1}


     acKpiDdosStatsCurrentGlobalAclDroppedTotal OBJECT-TYPE
       SYNTAX Counter64
       MAX-ACCESS read-only
       STATUS current
       DESCRIPTION
           "Total number of IP packets dropped by Access List.
AC INI-Param: N/A"
       ::= {acKpiDdosStatsCurrentGlobal 1}



     acKpiDdosStatsCurrentGlobalRejectedSipTlsConnTotal OBJECT-TYPE
       SYNTAX Counter64
       MAX-ACCESS read-only
       STATUS current
       DESCRIPTION
           "Total number of rejected SIP TLS connections.
AC INI-Param: N/A"
       ::= {acKpiDdosStatsCurrentGlobal 2}



     acKpiDdosStatsCurrentGlobalAttemptedSipTlsConnTotal OBJECT-TYPE
       SYNTAX Counter64
       MAX-ACCESS read-only
       STATUS current
       DESCRIPTION
           "Total number of attempted SIP TLS connections.
AC INI-Param: N/A"
       ::= {acKpiDdosStatsCurrentGlobal 3}



     acKpiDdosStatsCurrentGlobalConntrackDroppedTotal OBJECT-TYPE
       SYNTAX Counter64
       MAX-ACCESS read-only
       STATUS current
       DESCRIPTION
           "Total number of TCP connections dropped by conntrack.
AC INI-Param: N/A"
       ::= {acKpiDdosStatsCurrentGlobal 4}



     acKpiDdosStatsCurrentGlobalWlEntries OBJECT-TYPE
       SYNTAX Gauge32
       MAX-ACCESS read-only
       STATUS current
       DESCRIPTION
           "Number of entries in White List table.
AC INI-Param: N/A"
       ::= {acKpiDdosStatsCurrentGlobal 5}



     acKpiDdosStatsCurrentGlobalBlDroppedTotal OBJECT-TYPE
       SYNTAX Counter64
       MAX-ACCESS read-only
       STATUS current
       DESCRIPTION
           "Total number of IP packets dropped by Black List.
AC INI-Param: N/A"
       ::= {acKpiDdosStatsCurrentGlobal 6}



     acKpiDdosStatsCurrentGlobalWlDropRate OBJECT-TYPE
       SYNTAX Gauge32
       MAX-ACCESS read-only
       STATUS current
       DESCRIPTION
           "Packet drop rate by White List (0.1% units).
AC INI-Param: N/A"
       ::= {acKpiDdosStatsCurrentGlobal 7}



     acKpiDdosStatsCurrentGlobalWlDroppedTotal OBJECT-TYPE
       SYNTAX Counter64
       MAX-ACCESS read-only
       STATUS current
       DESCRIPTION
           "Total number of IP packets dropped by White List.
AC INI-Param: N/A"
       ::= {acKpiDdosStatsCurrentGlobal 8}



     acKpiDdosStatsCurrentGlobalWlRatio OBJECT-TYPE
       SYNTAX Gauge32
       MAX-ACCESS read-only
       STATUS current
       DESCRIPTION
           "Percentage of SIP packets processed by White List (0.1% units).
AC INI-Param: N/A"
       ::= {acKpiDdosStatsCurrentGlobal 9}



     acKpiDdosStatsCurrentGlobalWlProcessedTotal OBJECT-TYPE
       SYNTAX Counter64
       MAX-ACCESS read-only
       STATUS current
       DESCRIPTION
           "Total number of IP packets processed by White List.
AC INI-Param: N/A"
       ::= {acKpiDdosStatsCurrentGlobal 10}



     acKpiDdosStatsCurrentGlobalGlRatio OBJECT-TYPE
       SYNTAX Gauge32
       MAX-ACCESS read-only
       STATUS current
       DESCRIPTION
           "Percentage of SIP packets processed by Grey List (0.1% units).
AC INI-Param: N/A"
       ::= {acKpiDdosStatsCurrentGlobal 11}



     acKpiDdosStatsCurrentGlobalNonSipPacketsTotal OBJECT-TYPE
       SYNTAX Counter64
       MAX-ACCESS read-only
       STATUS current
       DESCRIPTION
           "Total number of non-SIP packets received.
AC INI-Param: N/A"
       ::= {acKpiDdosStatsCurrentGlobal 12}



     acKpiDdosStatsCurrentGlobalSipPacketsTotal OBJECT-TYPE
       SYNTAX Counter64
       MAX-ACCESS read-only
       STATUS current
       DESCRIPTION
           "Total number of SIP packets received.
AC INI-Param: N/A"
       ::= {acKpiDdosStatsCurrentGlobal 13}



     acKpiDdosStatsCurrentGlobalSynDropRate OBJECT-TYPE
       SYNTAX Gauge32
       MAX-ACCESS read-only
       STATUS current
       DESCRIPTION
           "Drop rate of TCP SYN packets (0.1% units).
AC INI-Param: N/A"
       ::= {acKpiDdosStatsCurrentGlobal 14}



     acKpiDdosStatsCurrentGlobalSynProcessedTotal OBJECT-TYPE
       SYNTAX Counter64
       MAX-ACCESS read-only
       STATUS current
       DESCRIPTION
           "Total number of TCP SYN packets processed.
AC INI-Param: N/A"
       ::= {acKpiDdosStatsCurrentGlobal 15}



     acKpiDdosStatsCurrentGlobalSynDroppedTotal OBJECT-TYPE
       SYNTAX Counter64
       MAX-ACCESS read-only
       STATUS current
       DESCRIPTION
           "Total number of TCP SYN packets dropped.
AC INI-Param: N/A"
       ::= {acKpiDdosStatsCurrentGlobal 16}



     acKpiDdosStatsCurrentGlobalGlDropRate OBJECT-TYPE
       SYNTAX Gauge32
       MAX-ACCESS read-only
       STATUS current
       DESCRIPTION
           "Packet drop rate by Grey List (0.1% units).
AC INI-Param: N/A"
       ::= {acKpiDdosStatsCurrentGlobal 17}



     acKpiDdosStatsCurrentGlobalGlProcessedTotal OBJECT-TYPE
       SYNTAX Counter64
       MAX-ACCESS read-only
       STATUS current
       DESCRIPTION
           "Total number IP packets processed by Grey List.
AC INI-Param: N/A"
       ::= {acKpiDdosStatsCurrentGlobal 18}



     acKpiDdosStatsCurrentGlobalGlDroppedTotal OBJECT-TYPE
       SYNTAX Counter64
       MAX-ACCESS read-only
       STATUS current
       DESCRIPTION
           "Total number IP packets dropped by Grey List.
AC INI-Param: N/A"
       ::= {acKpiDdosStatsCurrentGlobal 19}



     acKpiDdosStatsCurrentGlobalActiveSipTlsConnTotal OBJECT-TYPE
       SYNTAX Gauge32
       MAX-ACCESS read-only
       STATUS current
       DESCRIPTION
           "Total number of active SIP TLS connections.
AC INI-Param: N/A"
       ::= {acKpiDdosStatsCurrentGlobal 20}



     acKpiDdosStatsInterval OBJECT IDENTIFIER ::= {acKpiDdosStats 2}


     acKpiDdosStatsIntervalGlobal OBJECT IDENTIFIER ::= {acKpiDdosStatsInterval 1}


     -- ****************************************
     -- acKpiDdosStatsIntervalGlobal table declaration
     -- ****************************************
     acKpiDdosStatsIntervalGlobalTable OBJECT-TYPE
       SYNTAX SEQUENCE OF AcKpiDdosStatsIntervalGlobalEntry
       MAX-ACCESS not-accessible
       STATUS current
       DESCRIPTION
           ""
       ::= {acKpiDdosStatsIntervalGlobal 1}



     -- ****************************************
     -- acKpiDdosStatsIntervalGlobal table entry
     -- ****************************************
     acKpiDdosStatsIntervalGlobalEntry OBJECT-TYPE
       SYNTAX AcKpiDdosStatsIntervalGlobalEntry
       MAX-ACCESS not-accessible
       STATUS current
       DESCRIPTION
           ""
       INDEX {acKpiDdosStatsIntervalGlobalInterval}
       ::= {acKpiDdosStatsIntervalGlobalTable 1}



     -- ****************************************
     -- acKpiDdosStatsIntervalGlobal TABLE
     -- ****************************************
     AcKpiDdosStatsIntervalGlobalEntry ::= SEQUENCE {
       acKpiDdosStatsIntervalGlobalInterval            Unsigned32,
       acKpiDdosStatsIntervalGlobalRejectedSipTlsConn  Counter64,
       acKpiDdosStatsIntervalGlobalAttemptedSipTlsConn Counter64,
       acKpiDdosStatsIntervalGlobalConntrackDropped    Counter64,
       acKpiDdosStatsIntervalGlobalWlEntriesMax        Gauge32,
       acKpiDdosStatsIntervalGlobalWlEntriesAvg        Gauge32,
       acKpiDdosStatsIntervalGlobalBlDropped           Counter64,
       acKpiDdosStatsIntervalGlobalWlDropRateMax       Gauge32,
       acKpiDdosStatsIntervalGlobalWlDropRateAvg       Gauge32,
       acKpiDdosStatsIntervalGlobalWlDropped           Counter64,
       acKpiDdosStatsIntervalGlobalWlRatioMax          Gauge32,
       acKpiDdosStatsIntervalGlobalWlRatioAvg          Gauge32,
       acKpiDdosStatsIntervalGlobalWlProcessed         Counter64,
       acKpiDdosStatsIntervalGlobalGlRatioMax          Gauge32,
       acKpiDdosStatsIntervalGlobalGlRatioAvg          Gauge32,
       acKpiDdosStatsIntervalGlobalNonSipPackets       Counter64,
       acKpiDdosStatsIntervalGlobalSipPackets          Counter64,
       acKpiDdosStatsIntervalGlobalSynDropRateMax      Gauge32,
       acKpiDdosStatsIntervalGlobalSynDropRateAvg      Gauge32,
       acKpiDdosStatsIntervalGlobalSynProcessed        Counter64,
       acKpiDdosStatsIntervalGlobalSynDropped          Counter64,
       acKpiDdosStatsIntervalGlobalGlDropRateMax       Gauge32,
       acKpiDdosStatsIntervalGlobalGlDropRateAvg       Gauge32,
       acKpiDdosStatsIntervalGlobalGlProcessed         Counter64,
       acKpiDdosStatsIntervalGlobalGlDropped           Counter64,
       acKpiDdosStatsIntervalGlobalActiveSipTlsConnAvg Gauge32,
       acKpiDdosStatsIntervalGlobalActiveSipTlsConnMax Gauge32
     }



     acKpiDdosStatsIntervalGlobalInterval OBJECT-TYPE
       SYNTAX Unsigned32 (1..200)
       MAX-ACCESS not-accessible
       STATUS current
       DESCRIPTION
           "
AC INI-Param: N/A"
       ::= {acKpiDdosStatsIntervalGlobalEntry 1}



     acKpiDdosStatsIntervalGlobalRejectedSipTlsConn OBJECT-TYPE
       SYNTAX Counter64
       MAX-ACCESS read-only
       STATUS current
       DESCRIPTION
           "Number of rejected SIP TLS connections.
AC INI-Param: N/A"
       ::= {acKpiDdosStatsIntervalGlobalEntry 2}



     acKpiDdosStatsIntervalGlobalAttemptedSipTlsConn OBJECT-TYPE
       SYNTAX Counter64
       MAX-ACCESS read-only
       STATUS current
       DESCRIPTION
           "Number of attempted SIP TLS connections.
AC INI-Param: N/A"
       ::= {acKpiDdosStatsIntervalGlobalEntry 3}



     acKpiDdosStatsIntervalGlobalConntrackDropped OBJECT-TYPE
       SYNTAX Counter64
       MAX-ACCESS read-only
       STATUS current
       DESCRIPTION
           "Number of TCP connections dropped by conntrack.
AC INI-Param: N/A"
       ::= {acKpiDdosStatsIntervalGlobalEntry 4}



     acKpiDdosStatsIntervalGlobalWlEntriesMax OBJECT-TYPE
       SYNTAX Gauge32
       MAX-ACCESS read-only
       STATUS current
       DESCRIPTION
           "Maximum number of entries in White List table.
AC INI-Param: N/A"
       ::= {acKpiDdosStatsIntervalGlobalEntry 5}



     acKpiDdosStatsIntervalGlobalWlEntriesAvg OBJECT-TYPE
       SYNTAX Gauge32
       MAX-ACCESS read-only
       STATUS current
       DESCRIPTION
           "Average number of entries in White List table.
AC INI-Param: N/A"
       ::= {acKpiDdosStatsIntervalGlobalEntry 6}



     acKpiDdosStatsIntervalGlobalBlDropped OBJECT-TYPE
       SYNTAX Counter64
       MAX-ACCESS read-only
       STATUS current
       DESCRIPTION
           "Number of IP packets dropped by Black List.
AC INI-Param: N/A"
       ::= {acKpiDdosStatsIntervalGlobalEntry 7}



     acKpiDdosStatsIntervalGlobalWlDropRateMax OBJECT-TYPE
       SYNTAX Gauge32
       MAX-ACCESS read-only
       STATUS current
       DESCRIPTION
           "Maximum packet drop rate by White List (0.1% units).
AC INI-Param: N/A"
       ::= {acKpiDdosStatsIntervalGlobalEntry 8}



     acKpiDdosStatsIntervalGlobalWlDropRateAvg OBJECT-TYPE
       SYNTAX Gauge32
       MAX-ACCESS read-only
       STATUS current
       DESCRIPTION
           "Average packet drop rate by White List (0.1% units).
AC INI-Param: N/A"
       ::= {acKpiDdosStatsIntervalGlobalEntry 9}



     acKpiDdosStatsIntervalGlobalWlDropped OBJECT-TYPE
       SYNTAX Counter64
       MAX-ACCESS read-only
       STATUS current
       DESCRIPTION
           "Number of IP packets dropped by White List.
AC INI-Param: N/A"
       ::= {acKpiDdosStatsIntervalGlobalEntry 10}



     acKpiDdosStatsIntervalGlobalWlRatioMax OBJECT-TYPE
       SYNTAX Gauge32
       MAX-ACCESS read-only
       STATUS current
       DESCRIPTION
           "Maximum percentage of SIP packets processed by White List (0.1%
units).
AC INI-Param: N/A"
       ::= {acKpiDdosStatsIntervalGlobalEntry 11}



     acKpiDdosStatsIntervalGlobalWlRatioAvg OBJECT-TYPE
       SYNTAX Gauge32
       MAX-ACCESS read-only
       STATUS current
       DESCRIPTION
           "Average percentage of SIP packets processed by White List (0.1%
units).
AC INI-Param: N/A"
       ::= {acKpiDdosStatsIntervalGlobalEntry 12}



     acKpiDdosStatsIntervalGlobalWlProcessed OBJECT-TYPE
       SYNTAX Counter64
       MAX-ACCESS read-only
       STATUS current
       DESCRIPTION
           "Number of IP packets processed by White List.
AC INI-Param: N/A"
       ::= {acKpiDdosStatsIntervalGlobalEntry 13}



     acKpiDdosStatsIntervalGlobalGlRatioMax OBJECT-TYPE
       SYNTAX Gauge32
       MAX-ACCESS read-only
       STATUS current
       DESCRIPTION
           "Maximum percentage of SIP packets processed by Grey List (0.1%
units).
AC INI-Param: N/A"
       ::= {acKpiDdosStatsIntervalGlobalEntry 14}



     acKpiDdosStatsIntervalGlobalGlRatioAvg OBJECT-TYPE
       SYNTAX Gauge32
       MAX-ACCESS read-only
       STATUS current
       DESCRIPTION
           "Average percentage of SIP packets processed by Grey List (0.1%
units).
AC INI-Param: N/A"
       ::= {acKpiDdosStatsIntervalGlobalEntry 15}



     acKpiDdosStatsIntervalGlobalNonSipPackets OBJECT-TYPE
       SYNTAX Counter64
       MAX-ACCESS read-only
       STATUS current
       DESCRIPTION
           "Number of non-SIP packets received.
AC INI-Param: N/A"
       ::= {acKpiDdosStatsIntervalGlobalEntry 16}



     acKpiDdosStatsIntervalGlobalSipPackets OBJECT-TYPE
       SYNTAX Counter64
       MAX-ACCESS read-only
       STATUS current
       DESCRIPTION
           "Number of SIP packets received.
AC INI-Param: N/A"
       ::= {acKpiDdosStatsIntervalGlobalEntry 17}



     acKpiDdosStatsIntervalGlobalSynDropRateMax OBJECT-TYPE
       SYNTAX Gauge32
       MAX-ACCESS read-only
       STATUS current
       DESCRIPTION
           "Maximum drop rate of TCP SYN packets (0.1% units).
AC INI-Param: N/A"
       ::= {acKpiDdosStatsIntervalGlobalEntry 18}



     acKpiDdosStatsIntervalGlobalSynDropRateAvg OBJECT-TYPE
       SYNTAX Gauge32
       MAX-ACCESS read-only
       STATUS current
       DESCRIPTION
           "Average drop rate of TCP SYN packets (0.1% units).
AC INI-Param: N/A"
       ::= {acKpiDdosStatsIntervalGlobalEntry 19}



     acKpiDdosStatsIntervalGlobalSynProcessed OBJECT-TYPE
       SYNTAX Counter64
       MAX-ACCESS read-only
       STATUS current
       DESCRIPTION
           "Number of TCP SYN packets processed.
AC INI-Param: N/A"
       ::= {acKpiDdosStatsIntervalGlobalEntry 20}



     acKpiDdosStatsIntervalGlobalSynDropped OBJECT-TYPE
       SYNTAX Counter64
       MAX-ACCESS read-only
       STATUS current
       DESCRIPTION
           "Number of TCP SYN packets dropped.
AC INI-Param: N/A"
       ::= {acKpiDdosStatsIntervalGlobalEntry 21}



     acKpiDdosStatsIntervalGlobalGlDropRateMax OBJECT-TYPE
       SYNTAX Gauge32
       MAX-ACCESS read-only
       STATUS current
       DESCRIPTION
           "Maximum packet drop rate by Grey List (0.1% units).
AC INI-Param: N/A"
       ::= {acKpiDdosStatsIntervalGlobalEntry 22}



     acKpiDdosStatsIntervalGlobalGlDropRateAvg OBJECT-TYPE
       SYNTAX Gauge32
       MAX-ACCESS read-only
       STATUS current
       DESCRIPTION
           "Average packet drop rate by Grey List (0.1% units).
AC INI-Param: N/A"
       ::= {acKpiDdosStatsIntervalGlobalEntry 23}



     acKpiDdosStatsIntervalGlobalGlProcessed OBJECT-TYPE
       SYNTAX Counter64
       MAX-ACCESS read-only
       STATUS current
       DESCRIPTION
           "Number of IP packets processed by Grey List.
AC INI-Param: N/A"
       ::= {acKpiDdosStatsIntervalGlobalEntry 24}



     acKpiDdosStatsIntervalGlobalGlDropped OBJECT-TYPE
       SYNTAX Counter64
       MAX-ACCESS read-only
       STATUS current
       DESCRIPTION
           "Number of IP packets dropped by Grey List.
AC INI-Param: N/A"
       ::= {acKpiDdosStatsIntervalGlobalEntry 25}



     acKpiDdosStatsIntervalGlobalActiveSipTlsConnAvg OBJECT-TYPE
       SYNTAX Gauge32
       MAX-ACCESS read-only
       STATUS current
       DESCRIPTION
           "Average number of active SIP TLS connections.
AC INI-Param: N/A"
       ::= {acKpiDdosStatsIntervalGlobalEntry 26}



     acKpiDdosStatsIntervalGlobalActiveSipTlsConnMax OBJECT-TYPE
       SYNTAX Gauge32
       MAX-ACCESS read-only
       STATUS current
       DESCRIPTION
           "Maximum number of active SIP TLS connections.
AC INI-Param: N/A"
       ::= {acKpiDdosStatsIntervalGlobalEntry 27}



     acKpiHaStats OBJECT IDENTIFIER ::= {acKpiNetwork 2}


     acKpiHaStatsCurrent OBJECT IDENTIFIER ::= {acKpiHaStats 1}


     acKpiHaStatsCurrentGlobal OBJECT IDENTIFIER ::= {acKpiHaStatsCurrent 1}


     acKpiHaStatsCurrentGlobalHaRedundantPacketLoss OBJECT-TYPE
       SYNTAX Gauge32
       MAX-ACCESS read-only
       STATUS current
       DESCRIPTION
           "Percent of HA keepalive packets lost by Redundant unit (in 0.01%).
AC INI-Param: N/A"
       ::= {acKpiHaStatsCurrentGlobal 1}



     acKpiHaStatsCurrentGlobalHaActivePacketLoss OBJECT-TYPE
       SYNTAX Gauge32
       MAX-ACCESS read-only
       STATUS current
       DESCRIPTION
           "Percent of HA keepalive packets lost by Active unit (in 0.01%).
AC INI-Param: N/A"
       ::= {acKpiHaStatsCurrentGlobal 2}



     acKpiHaStatsInterval OBJECT IDENTIFIER ::= {acKpiHaStats 2}


     acKpiHaStatsIntervalGlobal OBJECT IDENTIFIER ::= {acKpiHaStatsInterval 1}


     -- ****************************************
     -- acKpiHaStatsIntervalGlobal table declaration
     -- ****************************************
     acKpiHaStatsIntervalGlobalTable OBJECT-TYPE
       SYNTAX SEQUENCE OF AcKpiHaStatsIntervalGlobalEntry
       MAX-ACCESS not-accessible
       STATUS current
       DESCRIPTION
           ""
       ::= {acKpiHaStatsIntervalGlobal 1}



     -- ****************************************
     -- acKpiHaStatsIntervalGlobal table entry
     -- ****************************************
     acKpiHaStatsIntervalGlobalEntry OBJECT-TYPE
       SYNTAX AcKpiHaStatsIntervalGlobalEntry
       MAX-ACCESS not-accessible
       STATUS current
       DESCRIPTION
           ""
       INDEX {acKpiHaStatsIntervalGlobalInterval}
       ::= {acKpiHaStatsIntervalGlobalTable 1}



     -- ****************************************
     -- acKpiHaStatsIntervalGlobal TABLE
     -- ****************************************
     AcKpiHaStatsIntervalGlobalEntry ::= SEQUENCE {
       acKpiHaStatsIntervalGlobalInterval              Unsigned32,
       acKpiHaStatsIntervalGlobalHaRedundantPacketLossMax 
                                                       Gauge32,
       acKpiHaStatsIntervalGlobalHaRedundantPacketLossAvg 
                                                       Gauge32,
       acKpiHaStatsIntervalGlobalHaActivePacketLossMax Gauge32,
       acKpiHaStatsIntervalGlobalHaActivePacketLossAvg Gauge32
     }



     acKpiHaStatsIntervalGlobalInterval OBJECT-TYPE
       SYNTAX Unsigned32 (1..200)
       MAX-ACCESS not-accessible
       STATUS current
       DESCRIPTION
           "
AC INI-Param: N/A"
       ::= {acKpiHaStatsIntervalGlobalEntry 1}



     acKpiHaStatsIntervalGlobalHaRedundantPacketLossMax OBJECT-TYPE
       SYNTAX Gauge32
       MAX-ACCESS read-only
       STATUS current
       DESCRIPTION
           "Maximum percent of HA KA packets lost by Redundant unit (in
0.01%).
AC INI-Param: N/A"
       ::= {acKpiHaStatsIntervalGlobalEntry 2}



     acKpiHaStatsIntervalGlobalHaRedundantPacketLossAvg OBJECT-TYPE
       SYNTAX Gauge32
       MAX-ACCESS read-only
       STATUS current
       DESCRIPTION
           "Average percent of HA KA packets lost by Redundant unit (in
0.01%).
AC INI-Param: N/A"
       ::= {acKpiHaStatsIntervalGlobalEntry 3}



     acKpiHaStatsIntervalGlobalHaActivePacketLossMax OBJECT-TYPE
       SYNTAX Gauge32
       MAX-ACCESS read-only
       STATUS current
       DESCRIPTION
           "Maximum percent of HA KA packets lost by Active unit (in 0.01%).
AC INI-Param: N/A"
       ::= {acKpiHaStatsIntervalGlobalEntry 4}



     acKpiHaStatsIntervalGlobalHaActivePacketLossAvg OBJECT-TYPE
       SYNTAX Gauge32
       MAX-ACCESS read-only
       STATUS current
       DESCRIPTION
           "Average percent of HA KA packets lost by Active unit (in 0.01%).
AC INI-Param: N/A"
       ::= {acKpiHaStatsIntervalGlobalEntry 5}



     acKpiPortStats OBJECT IDENTIFIER ::= {acKpiNetwork 3}


     acKpiPortStatsCurrent OBJECT IDENTIFIER ::= {acKpiPortStats 1}


     acKpiPortStatsCurrentGlobal OBJECT IDENTIFIER ::= {acKpiPortStatsCurrent 1}


     acKpiPortStatsCurrentTables OBJECT IDENTIFIER ::= {acKpiPortStatsCurrent 2}


     -- ****************************************
     -- acKpiPortStatsCurrentPort table declaration
     -- ****************************************
     acKpiPortStatsCurrentPortTable OBJECT-TYPE
       SYNTAX SEQUENCE OF AcKpiPortStatsCurrentPortEntry
       MAX-ACCESS not-accessible
       STATUS current
       DESCRIPTION
           ""
       ::= {acKpiPortStatsCurrentTables 1}



     -- ****************************************
     -- acKpiPortStatsCurrentPort table entry
     -- ****************************************
     acKpiPortStatsCurrentPortEntry OBJECT-TYPE
       SYNTAX AcKpiPortStatsCurrentPortEntry
       MAX-ACCESS not-accessible
       STATUS current
       DESCRIPTION
           ""
       INDEX {acKpiPortStatsCurrentPortIndex}
       ::= {acKpiPortStatsCurrentPortTable 1}



     -- ****************************************
     -- acKpiPortStatsCurrentPort TABLE
     -- ****************************************
     AcKpiPortStatsCurrentPortEntry ::= SEQUENCE {
       acKpiPortStatsCurrentPortIndex                  Unsigned32,
       acKpiPortStatsCurrentPortDiscardInTotal         Counter64,
       acKpiPortStatsCurrentPortFcsErrorOutTotal       Counter64,
       acKpiPortStatsCurrentPortFcsErrorInTotal        Counter64,
       acKpiPortStatsCurrentPortBroadcastOutTotal      Counter64,
       acKpiPortStatsCurrentPortBroadcastInTotal       Counter64,
       acKpiPortStatsCurrentPortMulticastOutTotal      Counter64,
       acKpiPortStatsCurrentPortMulticastInTotal       Counter64,
       acKpiPortStatsCurrentPortUnicastOutTotal        Counter64,
       acKpiPortStatsCurrentPortUnicastInTotal         Counter64,
       acKpiPortStatsCurrentPortCompressedOutTotal     Counter64,
       acKpiPortStatsCurrentPortCarrierErrorsOutTotal  Counter64,
       acKpiPortStatsCurrentPortCollisionsTotal        Counter64,
       acKpiPortStatsCurrentPortCompressedInTotal      Counter64,
       acKpiPortStatsCurrentPortFrameErrorInTotal      Counter64,
       acKpiPortStatsCurrentPortDroppedOutTotal        Counter64,
       acKpiPortStatsCurrentPortDroppedInTotal         Counter64,
       acKpiPortStatsCurrentPortFifoErrorOutTotal      Counter64,
       acKpiPortStatsCurrentPortFifoErrorInTotal       Counter64,
       acKpiPortStatsCurrentPortPacketsOutTotal        Counter64,
       acKpiPortStatsCurrentPortPacketsInTotal         Counter64,
       acKpiPortStatsCurrentPortBytesOutTotal          Counter64,
       acKpiPortStatsCurrentPortBytesInTotal           Counter64
     }



     acKpiPortStatsCurrentPortIndex OBJECT-TYPE
       SYNTAX Unsigned32 (0..32767)
       MAX-ACCESS not-accessible
       STATUS current
       DESCRIPTION
           "
AC INI-Param: N/A"
       ::= {acKpiPortStatsCurrentPortEntry 1}



     acKpiPortStatsCurrentPortDiscardInTotal OBJECT-TYPE
       SYNTAX Counter64
       MAX-ACCESS read-only
       STATUS current
       DESCRIPTION
           "Total number of received packets discarded.
AC INI-Param: N/A"
       ::= {acKpiPortStatsCurrentPortEntry 2}



     acKpiPortStatsCurrentPortFcsErrorOutTotal OBJECT-TYPE
       SYNTAX Counter64
       MAX-ACCESS read-only
       STATUS current
       DESCRIPTION
           "Total number of transmitted FCS errors.
AC INI-Param: N/A"
       ::= {acKpiPortStatsCurrentPortEntry 3}



     acKpiPortStatsCurrentPortFcsErrorInTotal OBJECT-TYPE
       SYNTAX Counter64
       MAX-ACCESS read-only
       STATUS current
       DESCRIPTION
           "Total number of received FCS errors.
AC INI-Param: N/A"
       ::= {acKpiPortStatsCurrentPortEntry 4}



     acKpiPortStatsCurrentPortBroadcastOutTotal OBJECT-TYPE
       SYNTAX Counter64
       MAX-ACCESS read-only
       STATUS current
       DESCRIPTION
           "Total number of trasmitted broadcast packets.
AC INI-Param: N/A"
       ::= {acKpiPortStatsCurrentPortEntry 5}



     acKpiPortStatsCurrentPortBroadcastInTotal OBJECT-TYPE
       SYNTAX Counter64
       MAX-ACCESS read-only
       STATUS current
       DESCRIPTION
           "Total number of received broadcast packets.
AC INI-Param: N/A"
       ::= {acKpiPortStatsCurrentPortEntry 6}



     acKpiPortStatsCurrentPortMulticastOutTotal OBJECT-TYPE
       SYNTAX Counter64
       MAX-ACCESS read-only
       STATUS current
       DESCRIPTION
           "Total number of transmitted unicast packets.
AC INI-Param: N/A"
       ::= {acKpiPortStatsCurrentPortEntry 7}



     acKpiPortStatsCurrentPortMulticastInTotal OBJECT-TYPE
       SYNTAX Counter64
       MAX-ACCESS read-only
       STATUS current
       DESCRIPTION
           "Total number of received multicast packets.
AC INI-Param: N/A"
       ::= {acKpiPortStatsCurrentPortEntry 8}



     acKpiPortStatsCurrentPortUnicastOutTotal OBJECT-TYPE
       SYNTAX Counter64
       MAX-ACCESS read-only
       STATUS current
       DESCRIPTION
           "Total number of transmitted unicast packets.
AC INI-Param: N/A"
       ::= {acKpiPortStatsCurrentPortEntry 9}



     acKpiPortStatsCurrentPortUnicastInTotal OBJECT-TYPE
       SYNTAX Counter64
       MAX-ACCESS read-only
       STATUS current
       DESCRIPTION
           "Total number of received unicast packets.
AC INI-Param: N/A"
       ::= {acKpiPortStatsCurrentPortEntry 10}



     acKpiPortStatsCurrentPortCompressedOutTotal OBJECT-TYPE
       SYNTAX Counter64
       MAX-ACCESS read-only
       STATUS current
       DESCRIPTION
           "Total number of transmitted compressed packets.
AC INI-Param: N/A"
       ::= {acKpiPortStatsCurrentPortEntry 11}



     acKpiPortStatsCurrentPortCarrierErrorsOutTotal OBJECT-TYPE
       SYNTAX Counter64
       MAX-ACCESS read-only
       STATUS current
       DESCRIPTION
           "Total number of transmitted carrier errors.
AC INI-Param: N/A"
       ::= {acKpiPortStatsCurrentPortEntry 12}



     acKpiPortStatsCurrentPortCollisionsTotal OBJECT-TYPE
       SYNTAX Counter64
       MAX-ACCESS read-only
       STATUS current
       DESCRIPTION
           "Total number of collisions.
AC INI-Param: N/A"
       ::= {acKpiPortStatsCurrentPortEntry 13}



     acKpiPortStatsCurrentPortCompressedInTotal OBJECT-TYPE
       SYNTAX Counter64
       MAX-ACCESS read-only
       STATUS current
       DESCRIPTION
           "Total number of received compressed packets.
AC INI-Param: N/A"
       ::= {acKpiPortStatsCurrentPortEntry 14}



     acKpiPortStatsCurrentPortFrameErrorInTotal OBJECT-TYPE
       SYNTAX Counter64
       MAX-ACCESS read-only
       STATUS current
       DESCRIPTION
           "Total number of received frame errors.
AC INI-Param: N/A"
       ::= {acKpiPortStatsCurrentPortEntry 15}



     acKpiPortStatsCurrentPortDroppedOutTotal OBJECT-TYPE
       SYNTAX Counter64
       MAX-ACCESS read-only
       STATUS current
       DESCRIPTION
           "Total number of transmitted packets dropped.
AC INI-Param: N/A"
       ::= {acKpiPortStatsCurrentPortEntry 16}



     acKpiPortStatsCurrentPortDroppedInTotal OBJECT-TYPE
       SYNTAX Counter64
       MAX-ACCESS read-only
       STATUS current
       DESCRIPTION
           "Total number of received packets dropped.
AC INI-Param: N/A"
       ::= {acKpiPortStatsCurrentPortEntry 17}



     acKpiPortStatsCurrentPortFifoErrorOutTotal OBJECT-TYPE
       SYNTAX Counter64
       MAX-ACCESS read-only
       STATUS current
       DESCRIPTION
           "Total number of transmitted FIFO errors.
AC INI-Param: N/A"
       ::= {acKpiPortStatsCurrentPortEntry 18}



     acKpiPortStatsCurrentPortFifoErrorInTotal OBJECT-TYPE
       SYNTAX Counter64
       MAX-ACCESS read-only
       STATUS current
       DESCRIPTION
           "Total number of received FIFO errors.
AC INI-Param: N/A"
       ::= {acKpiPortStatsCurrentPortEntry 19}



     acKpiPortStatsCurrentPortPacketsOutTotal OBJECT-TYPE
       SYNTAX Counter64
       MAX-ACCESS read-only
       STATUS current
       DESCRIPTION
           "Total number of transmitted packets.
AC INI-Param: N/A"
       ::= {acKpiPortStatsCurrentPortEntry 20}



     acKpiPortStatsCurrentPortPacketsInTotal OBJECT-TYPE
       SYNTAX Counter64
       MAX-ACCESS read-only
       STATUS current
       DESCRIPTION
           "Total number of received packets.
AC INI-Param: N/A"
       ::= {acKpiPortStatsCurrentPortEntry 21}



     acKpiPortStatsCurrentPortBytesOutTotal OBJECT-TYPE
       SYNTAX Counter64
       MAX-ACCESS read-only
       STATUS current
       DESCRIPTION
           "Total number of transmitted bytes.
AC INI-Param: N/A"
       ::= {acKpiPortStatsCurrentPortEntry 22}



     acKpiPortStatsCurrentPortBytesInTotal OBJECT-TYPE
       SYNTAX Counter64
       MAX-ACCESS read-only
       STATUS current
       DESCRIPTION
           "Total number of received bytes.
AC INI-Param: N/A"
       ::= {acKpiPortStatsCurrentPortEntry 23}



     acKpiPortStatsInterval OBJECT IDENTIFIER ::= {acKpiPortStats 2}


     acKpiPortStatsIntervalGlobal OBJECT IDENTIFIER ::= {acKpiPortStatsInterval 1}


     acKpiPortStatsIntervalTables OBJECT IDENTIFIER ::= {acKpiPortStatsInterval 2}


     -- ****************************************
     -- acKpiPortStatsIntervalPort table declaration
     -- ****************************************
     acKpiPortStatsIntervalPortTable OBJECT-TYPE
       SYNTAX SEQUENCE OF AcKpiPortStatsIntervalPortEntry
       MAX-ACCESS not-accessible
       STATUS current
       DESCRIPTION
           ""
       ::= {acKpiPortStatsIntervalTables 1}



     -- ****************************************
     -- acKpiPortStatsIntervalPort table entry
     -- ****************************************
     acKpiPortStatsIntervalPortEntry OBJECT-TYPE
       SYNTAX AcKpiPortStatsIntervalPortEntry
       MAX-ACCESS not-accessible
       STATUS current
       DESCRIPTION
           ""
       INDEX {acKpiPortStatsIntervalPortIndex,acKpiPortStatsIntervalPortInterval}
       ::= {acKpiPortStatsIntervalPortTable 1}



     -- ****************************************
     -- acKpiPortStatsIntervalPort TABLE
     -- ****************************************
     AcKpiPortStatsIntervalPortEntry ::= SEQUENCE {
       acKpiPortStatsIntervalPortIndex                 Unsigned32,
       acKpiPortStatsIntervalPortInterval              Unsigned32,
       acKpiPortStatsIntervalPortDiscardIn             Counter64,
       acKpiPortStatsIntervalPortFcsErrorOut           Counter64,
       acKpiPortStatsIntervalPortFcsErrorIn            Counter64,
       acKpiPortStatsIntervalPortBroadcastOut          Counter64,
       acKpiPortStatsIntervalPortBroadcastIn           Counter64,
       acKpiPortStatsIntervalPortMulticastOut          Counter64,
       acKpiPortStatsIntervalPortMulticastIn           Counter64,
       acKpiPortStatsIntervalPortUnicastOut            Counter64,
       acKpiPortStatsIntervalPortUnicastIn             Counter64,
       acKpiPortStatsIntervalPortCompressedOut         Counter64,
       acKpiPortStatsIntervalPortCarrierErrorsOut      Counter64,
       acKpiPortStatsIntervalPortCollisions            Counter64,
       acKpiPortStatsIntervalPortCompressedIn          Counter64,
       acKpiPortStatsIntervalPortFrameErrorIn          Counter64,
       acKpiPortStatsIntervalPortDroppedOut            Counter64,
       acKpiPortStatsIntervalPortDroppedIn             Counter64,
       acKpiPortStatsIntervalPortFifoErrorOut          Counter64,
       acKpiPortStatsIntervalPortFifoErrorIn           Counter64,
       acKpiPortStatsIntervalPortPacketsOut            Counter64,
       acKpiPortStatsIntervalPortPacketsIn             Counter64,
       acKpiPortStatsIntervalPortBytesOut              Counter64,
       acKpiPortStatsIntervalPortBytesIn               Counter64
     }



     acKpiPortStatsIntervalPortIndex OBJECT-TYPE
       SYNTAX Unsigned32 (0..32767)
       MAX-ACCESS not-accessible
       STATUS current
       DESCRIPTION
           "
AC INI-Param: N/A"
       ::= {acKpiPortStatsIntervalPortEntry 1}



     acKpiPortStatsIntervalPortInterval OBJECT-TYPE
       SYNTAX Unsigned32 (1..200)
       MAX-ACCESS not-accessible
       STATUS current
       DESCRIPTION
           "
AC INI-Param: N/A"
       ::= {acKpiPortStatsIntervalPortEntry 2}



     acKpiPortStatsIntervalPortDiscardIn OBJECT-TYPE
       SYNTAX Counter64
       MAX-ACCESS read-only
       STATUS current
       DESCRIPTION
           "Number of received packets discarded.
AC INI-Param: N/A"
       ::= {acKpiPortStatsIntervalPortEntry 3}



     acKpiPortStatsIntervalPortFcsErrorOut OBJECT-TYPE
       SYNTAX Counter64
       MAX-ACCESS read-only
       STATUS current
       DESCRIPTION
           "Number of transmitted FCS errors.
AC INI-Param: N/A"
       ::= {acKpiPortStatsIntervalPortEntry 4}



     acKpiPortStatsIntervalPortFcsErrorIn OBJECT-TYPE
       SYNTAX Counter64
       MAX-ACCESS read-only
       STATUS current
       DESCRIPTION
           "Number of received FCS errors.
AC INI-Param: N/A"
       ::= {acKpiPortStatsIntervalPortEntry 5}



     acKpiPortStatsIntervalPortBroadcastOut OBJECT-TYPE
       SYNTAX Counter64
       MAX-ACCESS read-only
       STATUS current
       DESCRIPTION
           "Number of trasmitted broadcast packets.
AC INI-Param: N/A"
       ::= {acKpiPortStatsIntervalPortEntry 6}



     acKpiPortStatsIntervalPortBroadcastIn OBJECT-TYPE
       SYNTAX Counter64
       MAX-ACCESS read-only
       STATUS current
       DESCRIPTION
           "Number of received broadcast packets.
AC INI-Param: N/A"
       ::= {acKpiPortStatsIntervalPortEntry 7}



     acKpiPortStatsIntervalPortMulticastOut OBJECT-TYPE
       SYNTAX Counter64
       MAX-ACCESS read-only
       STATUS current
       DESCRIPTION
           "Number of transmitted unicast packets.
AC INI-Param: N/A"
       ::= {acKpiPortStatsIntervalPortEntry 8}



     acKpiPortStatsIntervalPortMulticastIn OBJECT-TYPE
       SYNTAX Counter64
       MAX-ACCESS read-only
       STATUS current
       DESCRIPTION
           "Number of received multicast packets.
AC INI-Param: N/A"
       ::= {acKpiPortStatsIntervalPortEntry 9}



     acKpiPortStatsIntervalPortUnicastOut OBJECT-TYPE
       SYNTAX Counter64
       MAX-ACCESS read-only
       STATUS current
       DESCRIPTION
           "Number of transmitted unicast packets.
AC INI-Param: N/A"
       ::= {acKpiPortStatsIntervalPortEntry 10}



     acKpiPortStatsIntervalPortUnicastIn OBJECT-TYPE
       SYNTAX Counter64
       MAX-ACCESS read-only
       STATUS current
       DESCRIPTION
           "Number of received unicast packets.
AC INI-Param: N/A"
       ::= {acKpiPortStatsIntervalPortEntry 11}



     acKpiPortStatsIntervalPortCompressedOut OBJECT-TYPE
       SYNTAX Counter64
       MAX-ACCESS read-only
       STATUS current
       DESCRIPTION
           "Number of transmitted compressed packets.
AC INI-Param: N/A"
       ::= {acKpiPortStatsIntervalPortEntry 12}



     acKpiPortStatsIntervalPortCarrierErrorsOut OBJECT-TYPE
       SYNTAX Counter64
       MAX-ACCESS read-only
       STATUS current
       DESCRIPTION
           "Number of transmitted carrier errors.
AC INI-Param: N/A"
       ::= {acKpiPortStatsIntervalPortEntry 13}



     acKpiPortStatsIntervalPortCollisions OBJECT-TYPE
       SYNTAX Counter64
       MAX-ACCESS read-only
       STATUS current
       DESCRIPTION
           "Number of collisions.
AC INI-Param: N/A"
       ::= {acKpiPortStatsIntervalPortEntry 14}



     acKpiPortStatsIntervalPortCompressedIn OBJECT-TYPE
       SYNTAX Counter64
       MAX-ACCESS read-only
       STATUS current
       DESCRIPTION
           "Number of received compressed packets.
AC INI-Param: N/A"
       ::= {acKpiPortStatsIntervalPortEntry 15}



     acKpiPortStatsIntervalPortFrameErrorIn OBJECT-TYPE
       SYNTAX Counter64
       MAX-ACCESS read-only
       STATUS current
       DESCRIPTION
           "Number of received frame errors.
AC INI-Param: N/A"
       ::= {acKpiPortStatsIntervalPortEntry 16}



     acKpiPortStatsIntervalPortDroppedOut OBJECT-TYPE
       SYNTAX Counter64
       MAX-ACCESS read-only
       STATUS current
       DESCRIPTION
           "Number of transmitted packets dropped.
AC INI-Param: N/A"
       ::= {acKpiPortStatsIntervalPortEntry 17}



     acKpiPortStatsIntervalPortDroppedIn OBJECT-TYPE
       SYNTAX Counter64
       MAX-ACCESS read-only
       STATUS current
       DESCRIPTION
           "Number of received packets dropped.
AC INI-Param: N/A"
       ::= {acKpiPortStatsIntervalPortEntry 18}



     acKpiPortStatsIntervalPortFifoErrorOut OBJECT-TYPE
       SYNTAX Counter64
       MAX-ACCESS read-only
       STATUS current
       DESCRIPTION
           "Number of transmitted FIFO errors.
AC INI-Param: N/A"
       ::= {acKpiPortStatsIntervalPortEntry 19}



     acKpiPortStatsIntervalPortFifoErrorIn OBJECT-TYPE
       SYNTAX Counter64
       MAX-ACCESS read-only
       STATUS current
       DESCRIPTION
           "Number of received FIFO errors.
AC INI-Param: N/A"
       ::= {acKpiPortStatsIntervalPortEntry 20}



     acKpiPortStatsIntervalPortPacketsOut OBJECT-TYPE
       SYNTAX Counter64
       MAX-ACCESS read-only
       STATUS current
       DESCRIPTION
           "Number of transmitted packets.
AC INI-Param: N/A"
       ::= {acKpiPortStatsIntervalPortEntry 21}



     acKpiPortStatsIntervalPortPacketsIn OBJECT-TYPE
       SYNTAX Counter64
       MAX-ACCESS read-only
       STATUS current
       DESCRIPTION
           "Number of received packets.
AC INI-Param: N/A"
       ::= {acKpiPortStatsIntervalPortEntry 22}



     acKpiPortStatsIntervalPortBytesOut OBJECT-TYPE
       SYNTAX Counter64
       MAX-ACCESS read-only
       STATUS current
       DESCRIPTION
           "Number of transmitted bytes.
AC INI-Param: N/A"
       ::= {acKpiPortStatsIntervalPortEntry 23}



     acKpiPortStatsIntervalPortBytesIn OBJECT-TYPE
       SYNTAX Counter64
       MAX-ACCESS read-only
       STATUS current
       DESCRIPTION
           "Number of received bytes.
AC INI-Param: N/A"
       ::= {acKpiPortStatsIntervalPortEntry 24}



     acKpiTlsStats OBJECT IDENTIFIER ::= {acKpiNetwork 4}


     acKpiTlsStatsCurrent OBJECT IDENTIFIER ::= {acKpiTlsStats 1}


     acKpiTlsStatsCurrentGlobal OBJECT IDENTIFIER ::= {acKpiTlsStatsCurrent 1}


     acKpiTlsStatsCurrentGlobalAttemptedSipTlsConnTotal OBJECT-TYPE
       SYNTAX Counter64
       MAX-ACCESS read-only
       STATUS current
       DESCRIPTION
           "Total number of attempted SIP TLS connections.
AC INI-Param: N/A"
       ::= {acKpiTlsStatsCurrentGlobal 1}



     acKpiTlsStatsCurrentGlobalRejectedSipTlsConnTotal OBJECT-TYPE
       SYNTAX Counter64
       MAX-ACCESS read-only
       STATUS current
       DESCRIPTION
           "Total number of rejected SIP TLS connections.
AC INI-Param: N/A"
       ::= {acKpiTlsStatsCurrentGlobal 2}



     acKpiTlsStatsCurrentGlobalActiveSipTlsConn OBJECT-TYPE
       SYNTAX Gauge32
       MAX-ACCESS read-only
       STATUS current
       DESCRIPTION
           "Total number of active SIP TLS connections.
AC INI-Param: N/A"
       ::= {acKpiTlsStatsCurrentGlobal 3}



     acKpiTlsStatsInterval OBJECT IDENTIFIER ::= {acKpiTlsStats 2}


     acKpiTlsStatsIntervalGlobal OBJECT IDENTIFIER ::= {acKpiTlsStatsInterval 1}


     -- ****************************************
     -- acKpiTlsStatsIntervalGlobal table declaration
     -- ****************************************
     acKpiTlsStatsIntervalGlobalTable OBJECT-TYPE
       SYNTAX SEQUENCE OF AcKpiTlsStatsIntervalGlobalEntry
       MAX-ACCESS not-accessible
       STATUS current
       DESCRIPTION
           ""
       ::= {acKpiTlsStatsIntervalGlobal 1}



     -- ****************************************
     -- acKpiTlsStatsIntervalGlobal table entry
     -- ****************************************
     acKpiTlsStatsIntervalGlobalEntry OBJECT-TYPE
       SYNTAX AcKpiTlsStatsIntervalGlobalEntry
       MAX-ACCESS not-accessible
       STATUS current
       DESCRIPTION
           ""
       INDEX {acKpiTlsStatsIntervalGlobalInterval}
       ::= {acKpiTlsStatsIntervalGlobalTable 1}



     -- ****************************************
     -- acKpiTlsStatsIntervalGlobal TABLE
     -- ****************************************
     AcKpiTlsStatsIntervalGlobalEntry ::= SEQUENCE {
       acKpiTlsStatsIntervalGlobalInterval             Unsigned32,
       acKpiTlsStatsIntervalGlobalActiveSipTlsConnAvg  Gauge32,
       acKpiTlsStatsIntervalGlobalActiveSipTlsConnMax  Gauge32,
       acKpiTlsStatsIntervalGlobalRejectedSipTlsConn   Counter64,
       acKpiTlsStatsIntervalGlobalAttemptedSipTlsConn  Counter64
     }



     acKpiTlsStatsIntervalGlobalInterval OBJECT-TYPE
       SYNTAX Unsigned32 (1..200)
       MAX-ACCESS not-accessible
       STATUS current
       DESCRIPTION
           "
AC INI-Param: N/A"
       ::= {acKpiTlsStatsIntervalGlobalEntry 1}



     acKpiTlsStatsIntervalGlobalActiveSipTlsConnAvg OBJECT-TYPE
       SYNTAX Gauge32
       MAX-ACCESS read-only
       STATUS current
       DESCRIPTION
           "Average number of active SIP TLS connections.
AC INI-Param: N/A"
       ::= {acKpiTlsStatsIntervalGlobalEntry 2}



     acKpiTlsStatsIntervalGlobalActiveSipTlsConnMax OBJECT-TYPE
       SYNTAX Gauge32
       MAX-ACCESS read-only
       STATUS current
       DESCRIPTION
           "Maximum number of active SIP TLS connections.
AC INI-Param: N/A"
       ::= {acKpiTlsStatsIntervalGlobalEntry 3}



     acKpiTlsStatsIntervalGlobalRejectedSipTlsConn OBJECT-TYPE
       SYNTAX Counter64
       MAX-ACCESS read-only
       STATUS current
       DESCRIPTION
           "Number of rejected SIP TLS connections.
AC INI-Param: N/A"
       ::= {acKpiTlsStatsIntervalGlobalEntry 4}



     acKpiTlsStatsIntervalGlobalAttemptedSipTlsConn OBJECT-TYPE
       SYNTAX Counter64
       MAX-ACCESS read-only
       STATUS current
       DESCRIPTION
           "Number of attempted SIP TLS connections.
AC INI-Param: N/A"
       ::= {acKpiTlsStatsIntervalGlobalEntry 5}





END
