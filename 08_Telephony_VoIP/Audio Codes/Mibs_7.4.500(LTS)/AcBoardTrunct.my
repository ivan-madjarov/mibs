AcBoard DEFINITIONS ::= BEGIN


    IMPORTS
       
       OBJECT-TYPE,
       Gauge32,
       MODULE-IDENTITY                             FROM SNMPv2-SMI
       TAddress, 
       DisplayString, 
       DateAndTime, TEXTUAL-CONVENTION             FROM SNMPv2-TC
       IpAddress                                   FROM RFC1155-SMI
       enterprises                                 FROM SNMPv2-SMI;

	audioCodes       OBJECT IDENTIFIER ::= {enterprises 5003}
	acRegistrations  OBJECT IDENTIFIER ::= {audioCodes 7}
	acGeneric        OBJECT IDENTIFIER ::= {audioCodes 8}
	acProducts       OBJECT IDENTIFIER ::= {audioCodes 9}	
        acBoardMibs     OBJECT IDENTIFIER ::= {acProducts 10}

       
acBoard        MODULE-IDENTITY       
    LAST-UPDATED "202312214144Z"          --Thursday, December 21, 2023
    ORGANIZATION "AudioCodes Ltd"
    CONTACT-INFO
    "Postal: Support
	     AudioCodes LTD
             1 Hayarden Street
             Airport City 
	     Lod, ISRAEL 70151
     Tel:    972-3-9764000
     Fax:    972-3-9764040
     Email:  support@audiocodes.com
     Web:    www.audiocodes.com"		

    DESCRIPTION       
    "AudioCodes Proprietary MIB 
     Contains The managed objects of AudioCodes systems.
     Through this MIB, the User can set up the board configuration parameters, reset the board, 
	 and monitor the board's operational robustness and quality of service during run-time. 

    This MIB has the following Groups: 
	    boardConfiguration     
	    boardInformation   
	    channelConfiguration 
	    channelStatus 
	    notifications    
	    reset

    boardConfiguration:     
        When The user Get Parameter from most of sub-groups in boardConfiguration group, 
	    he gets the value that should be burned to the board after the next Remote Reset. 
	    He can Set new values to many parameters, and these values will burned to the board after the next remote Reset 
        In the sub-group mGCPDefaultChannelSettings the parameters are the actual parameters, 
	    that will take place when opening channel. (Reset is not needed for that sub-group).

    BoardInformation: 
        Contains Read-only parameters like: board name, serial number, number of channels, software version.

    ChannelConfiguration:
        Read-only Parameters to see the configuratin of each channel: voice settings, fax settings, etc.         

    ChannelStatus:
        Read-only parameters about the status of channel, like: Is the channle active, is it in Silence Period, 
		is it in Fax mode, ON/Off hook, etc. 
        This group contains also counters: packets to DSP, errors, lost packets, underruns, etc.

    Notifications:
        In this version, the notification we have are: acEvBoardStarted, and acEvResetingBoard. 
        The board should send these notifications to its manager 
		that the user defined in INI file with the parameter: NMPManagerIP = (IP address). 

    Reset:
        To remote reset the board, the user should set an integer value to the parameter remoteReset.
		Then he should get the trap acEvResettingBoard. 
        Note: Before Reset, The current boardConfiguration parameters will be burned  to the board. 
		      The user should not use INI file, if he wants these parameters to take place.

		To set the default values, the user should set an integer value to the parameter acSetDefaults.
		"

    REVISION    "200401261153Z"          --Monday, January 26, 2004

    DESCRIPTION  " Update mib  for version 4.4  - obsolete atmSetting   and ss7Setting  families  "

    ::= {acBoardMibs 1}  

 
      -- ****************************************
     -- channelConfiguration Configuration
     -- ****************************************
     channelConfiguration          OBJECT IDENTIFIER ::= {acBoard 3}


     -- ****************************************
     -- voiceSettings Configuration
     -- ****************************************
     voiceSettings                 OBJECT IDENTIFIER ::= {channelConfiguration 2}


     -- ****************************************
     -- voiceSettings table decleration
     -- ****************************************
     voiceSettingsTable OBJECT-TYPE
       SYNTAX SEQUENCE OF VoiceSettingsEntry
       MAX-ACCESS not-accessible
       STATUS deprecated
       DESCRIPTION
           "Data in voice SettingsTable uniquely identify a voice parameters of channel."
       ::= {voiceSettings 1}



     -- ****************************************
     -- voiceSettings table entry
     -- ****************************************
     voiceSettingsEntry OBJECT-TYPE
       SYNTAX VoiceSettingsEntry
       MAX-ACCESS not-accessible
       STATUS deprecated
       DESCRIPTION
           ""
       INDEX {cID}
       ::= {voiceSettingsTable 1}



     -- ****************************************
     -- voiceSettings TABLE
     -- ****************************************
     VoiceSettingsEntry ::= SEQUENCE {
       cID                                             INTEGER,
       coder                                           INTEGER,
       eCE                                             INTEGER,
       sCE                                             INTEGER,
       pFE                                             INTEGER,
       hPFE                                            INTEGER,
       testMode                                        INTEGER,
       voiceVolume                                     INTEGER,
       inputGain                                       INTEGER,
       m                                               INTEGER,
       rTPRedundancyDepth                              INTEGER,
       eCLength                                        INTEGER,
       eCHybridLoss                                    INTEGER
     }



     cID OBJECT-TYPE
       SYNTAX INTEGER (0..2147483647)
       MAX-ACCESS read-only
       STATUS deprecated
       DESCRIPTION
           "Channel ID"
       ::= {voiceSettingsEntry 1}



     coder OBJECT-TYPE
       SYNTAX INTEGER {
                  g711Alaw(0)
,
                  g711Mulaw(1)
,
                  g726-16(2)
,
                  g726-24(3)
,
                  g726-32(4)
,
                  g726-40(5)
,
                  g727-16(6)
,
                  g727-24-16(7)
,
                  g727-24(8)
,
                  g727-32-16(9)
,
                  g727-32-24(10)
,
                  g727-32(11)
,
                  g727-40-16(12)
,
                  g727-40-24(13)
,
                  g727-40-32(14)
,
                  g723Low(15)
,
                  g723High(16)
,
                  g729(17)
,
                  gSM(19)
,
                  gSM610MS(20)
,
                   transparent(22)
,
                  g728(23)
,
                  hDLCCoder(24)
,
                  netCoder-4-8(25)
,
                  netCoder-5-6(26)
,
                  netCoder-6-4(27)
,
                  netCoder-7-2(28)
,
                  netCoder-8(29)
,
                  netCoder-8-8(30)
,
                  netCoder-9-6(31)
,
                  eVRC(32)
,
                  eVRC-TFO(33)
,
                  qCELP-8(34)
,
                  qCELP-8-TFO(35)
,
                  qCELP-13(36)
,
                  qCELP-13-TFO(37)
,
                  noCoder(40)
,
                  modemAnswer(41)
,
                  modemCall(42)
,
                  g711Alaw-5-5(45)
,
                  g711Mulaw-5-5(46)
,
                  g726-32-5-5(47)
,
                  aMR-4-75(50)
,
                  aMR-5-15(51)
,
                   aMR-5-9(52)
,
                  aMR-6-7(53)
,
                  aMR-7-4(54)
,
                  aMR-7-95(55)
,
                  aMR-10-2(56)
,
                  aMR-12-2(57)
,
                  iLBC-15(63)
,
                  iLBC-13(64)
,
                  bV-16(65)
,
                  acAMRWB-6-6(66)
,
                  acAMRWB-8-85(67)
,
                  acAMRWB-12-65(68)
,
                  acAMRWB-14-25(69)
,
                  acAMRWB-15-85(70)
,
                  acAMRWB-18-25(71)
,
                  acAMRWB-19-85(72)
,
                  acAMRWB-23-05(73)
,
                  acAMRWB-23-85(74)
,
                  acG722-48K(75)
,
                  acG722-56K(76)
,
                   acG722-64K(77)
,
                  acDPNSSCoder(78)

                  }
       MAX-ACCESS read-only
       STATUS deprecated
       DESCRIPTION
           "Digital voice coder"
       ::= {voiceSettingsEntry 2}



     eCE OBJECT-TYPE
       SYNTAX INTEGER {
                  disable(0)
,
                  enable(1)

                  }
       MAX-ACCESS read-only
       STATUS deprecated
       DESCRIPTION
           "Enable/Disable Echo Canceler"
       ::= {voiceSettingsEntry 3}



     sCE OBJECT-TYPE
       SYNTAX INTEGER {
                  disable(0)
,
                  enable(1)

                  }
       MAX-ACCESS read-only
       STATUS deprecated
       DESCRIPTION
           "Enable/Disable Silence Compresion mechanism"
       ::= {voiceSettingsEntry 4}



     pFE OBJECT-TYPE
       SYNTAX INTEGER {
                  disable(0)
,
                  enable(1)

                  }
       MAX-ACCESS read-only
       STATUS deprecated
       DESCRIPTION
           "Post Filter Enable of the voice coder"
       ::= {voiceSettingsEntry 5}



     hPFE OBJECT-TYPE
       SYNTAX INTEGER {
                  disable(0)
,
                  enable(1)

                  }
       MAX-ACCESS read-only
       STATUS deprecated
       DESCRIPTION
           "High Pass Filter Enabled of the voice coder"
       ::= {voiceSettingsEntry 6}



     testMode OBJECT-TYPE
       SYNTAX INTEGER {
                  coderLoopback(0)
,
                  pCMLoopback(1)
,
                  toneInjection(2)
,
                  noLoopback(3)

                  }
       MAX-ACCESS read-only
       STATUS deprecated
       DESCRIPTION
           "Testing mode to be applied. 
 Valid Range:CoderLoopback will perform an encoder-decoder loopback inside the DSP device, 
  PCMLoopback will loopback the incoming PCM to the outgoing PCM, 
  ToneInjection will generate a1000 Hz tone to outgoing PCM and 
  NoLoopback will set the channel to work in a normal mode. 
  Refer to TTestCode enumeration 
  (default =3= NoLoopBack).
"
       ::= {voiceSettingsEntry 7}



     voiceVolume OBJECT-TYPE
       SYNTAX INTEGER (0..63)
       MAX-ACCESS read-only
       STATUS deprecated
       DESCRIPTION
           "Voice Volume sets the voice decoder’s output gain
  Range: 0-63 corresponding to -31 dB to +31 dB in 1 dB steps"
       ::= {voiceSettingsEntry 8}



     inputGain OBJECT-TYPE
       SYNTAX INTEGER (0..63)
       MAX-ACCESS read-only
       STATUS deprecated
       DESCRIPTION
           "PCM input gain sets the gain at the encoder’s input."
       ::= {voiceSettingsEntry 9}



     m OBJECT-TYPE
       SYNTAX INTEGER (1..12)
       MAX-ACCESS read-only
       STATUS deprecated
       DESCRIPTION
           "This Packet Multiply Factor is the Number of 20 msec payloads 
  (30 msec for G.723) 
  to be used for generating one RTP packet. 
  Range: 1 - Until max Tx/Rx buffer size is reached"
       ::= {voiceSettingsEntry 10}



     rTPRedundancyDepth OBJECT-TYPE
       SYNTAX INTEGER {
                  disable(0)
,
                  enable(1)

                  }
       MAX-ACCESS read-only
       STATUS deprecated
       DESCRIPTION
           "RTP Redundancy Depth.
  Number of repetitions to be applied to each RTP payload 
  when transmitting to network.
   apply redundancy sequence per RFC2198. 
  Valid range:  Disable redundancy packets generation = 0.
  Enable generation of RFC2198 redundancy packets = 1."
       ::= {voiceSettingsEntry 11}



     eCLength OBJECT-TYPE
       SYNTAX INTEGER {
                  eCLength10MSec(0)
,
                  eCLength15Msec(1)
,
                  eCLength20Msec(2)
,
                  eCLength25Msec(3)
,
                  eCLength30Msec(4)
,
                  eCLength35Msec(5)
,
                  eCLength40Msec(6)
,
                  eCLength45Msec(7)
,
                  eCLength50Msec(8)
,
                  eCLength55Msec(9)
,
                  eCLength60Msec(10)

                  }
       MAX-ACCESS read-only
       STATUS deprecated
       DESCRIPTION
           "Length of echo canceler tail to be used
  according to TECLength enumeration. 
  Note that EC length has different length limitations for different boards."
       ::= {voiceSettingsEntry 12}



     eCHybridLoss OBJECT-TYPE
       SYNTAX INTEGER {
                  loss6DB(0)
,
                  loss9DB(1)
,
                  loss0DB(2)
,
                  loss3DB(3)

                  }
       MAX-ACCESS read-only
       STATUS deprecated
       DESCRIPTION
           "Echo Cancler Hybrid Loss.
  sets the worst case ratio between the signal level transmitted to the hybrid
  and the echo level returning from the hybrid.
  User should set this value according to the worst hybrid
  in the system in terms of echo return loss
  according to enum TECHybridLoss enumeration"
       ::= {voiceSettingsEntry 13}



     -- ****************************************
     -- channelStatus Configuration
     -- ****************************************
     channelStatus                 OBJECT IDENTIFIER ::= {acBoard 4}


     -- ****************************************
     -- channelStatus table decleration
     -- ****************************************
     channelStatusTable OBJECT-TYPE
       SYNTAX SEQUENCE OF ChannelStatusEntry
       MAX-ACCESS not-accessible
       STATUS deprecated
       DESCRIPTION
           "Data in voice SettingsTable uniquely identify a voice parameters of channel."
       ::= {channelStatus 1}



     -- ****************************************
     -- channelStatus table entry
     -- ****************************************
     channelStatusEntry OBJECT-TYPE
       SYNTAX ChannelStatusEntry
       MAX-ACCESS not-accessible
       STATUS deprecated
       DESCRIPTION
           ""
       INDEX { cID }
       ::= {channelStatusTable 1}



     -- ****************************************
     -- channelStatus TABLE
     -- ****************************************
     ChannelStatusEntry ::= SEQUENCE {
       rTPActive                                       INTEGER,
       bypassNIC                                       INTEGER,
       pendingIdle                                     INTEGER,
       txSilencePeriod                                 INTEGER,
       rxSilencePeriod                                 INTEGER,
       txFaxMode                                       INTEGER,
       rxFaxMode                                       INTEGER,
       txDTMFPeriod                                    INTEGER,
       rxDTMFPeriod                                    INTEGER,
       packetsToDSPCnt                                 INTEGER,
       jitterBufErrorCnt                               INTEGER,
       jitterBufForcedPacketLost                       INTEGER,
       jitterBufForcedPacketAddition                   INTEGER,
       jitterBufUnderRunCnt                            INTEGER,
       jitterBufOverRunCnt                             INTEGER,
       jitterBufAccumDelay                             INTEGER,
       fXSorFXO                                        INTEGER,
       channelHookState                                INTEGER
     }



     rTPActive OBJECT-TYPE
       SYNTAX INTEGER {
                  notActive(0)
,
                  active(1)

                  }
       MAX-ACCESS read-only
       STATUS deprecated
       DESCRIPTION
           "RTP Active"
       ::= {channelStatusEntry 1}



     bypassNIC OBJECT-TYPE
       SYNTAX INTEGER (0..1)
       MAX-ACCESS read-only
       STATUS deprecated
       DESCRIPTION
           "Bypass NIC"
       ::= {channelStatusEntry 2}



     pendingIdle OBJECT-TYPE
       SYNTAX INTEGER (0..1)
       MAX-ACCESS read-only
       STATUS obsolete
       DESCRIPTION
           "Pending Idle"
       ::= {channelStatusEntry 3}



     txSilencePeriod OBJECT-TYPE
       SYNTAX INTEGER (0..1)
       MAX-ACCESS read-only
       STATUS deprecated
       DESCRIPTION
           "Tx Silence Period
"
       ::= {channelStatusEntry 4}



     rxSilencePeriod OBJECT-TYPE
       SYNTAX INTEGER (0..1)
       MAX-ACCESS read-only
       STATUS deprecated
       DESCRIPTION
           "Rx Silence Period"
       ::= {channelStatusEntry 5}



     txFaxMode OBJECT-TYPE
       SYNTAX INTEGER (0..1)
       MAX-ACCESS read-only
       STATUS deprecated
       DESCRIPTION
           "Tx Fax Mode
"
       ::= {channelStatusEntry 6}



     rxFaxMode OBJECT-TYPE
       SYNTAX INTEGER (0..1)
       MAX-ACCESS read-only
       STATUS deprecated
       DESCRIPTION
           "Rx Fax Mode
"
       ::= {channelStatusEntry 7}



     txDTMFPeriod OBJECT-TYPE
       SYNTAX INTEGER (0..1)
       MAX-ACCESS read-only
       STATUS deprecated
       DESCRIPTION
           "Tx DTMF Period
"
       ::= {channelStatusEntry 8}



     rxDTMFPeriod OBJECT-TYPE
       SYNTAX INTEGER (0..1)
       MAX-ACCESS read-only
       STATUS deprecated
       DESCRIPTION
           "Rx DTMF Period"
       ::= {channelStatusEntry 9}



     packetsToDSPCnt OBJECT-TYPE
       SYNTAX INTEGER (0..2147483647)
       MAX-ACCESS read-only
       STATUS deprecated
       DESCRIPTION
           "Jitter Buffer Error Counter"
       ::= {channelStatusEntry 10}



     jitterBufErrorCnt OBJECT-TYPE
       SYNTAX INTEGER (0..2147483647)
       MAX-ACCESS read-only
       STATUS obsolete
       DESCRIPTION
           "Jitter Buffer Forced Packet count"
       ::= {channelStatusEntry 11}



     jitterBufForcedPacketLost OBJECT-TYPE
       SYNTAX INTEGER (0..2147483647)
       MAX-ACCESS read-only
       STATUS obsolete
       DESCRIPTION
           "Jitter Buffer Forced Packet Lost"
       ::= {channelStatusEntry 12}



     jitterBufForcedPacketAddition OBJECT-TYPE
       SYNTAX INTEGER (0..2147483647)
       MAX-ACCESS read-only
       STATUS obsolete
       DESCRIPTION
           "Jitter Buffer Forced Packet Addition"
       ::= {channelStatusEntry 13}



     jitterBufUnderRunCnt OBJECT-TYPE
       SYNTAX INTEGER (0..2147483647)
       MAX-ACCESS read-only
       STATUS deprecated
       DESCRIPTION
           "Jitter Buffer Under-Run Counter"
       ::= {channelStatusEntry 14}



     jitterBufOverRunCnt OBJECT-TYPE
       SYNTAX INTEGER (0..2147483647)
       MAX-ACCESS read-only
       STATUS deprecated
       DESCRIPTION
           "Jitter Buffer Over-Run Counter"
       ::= {channelStatusEntry 15}



     jitterBufAccumDelay OBJECT-TYPE
       SYNTAX INTEGER (0..2147483647)
       MAX-ACCESS read-only
       STATUS obsolete
       DESCRIPTION
           "Jitter Buffer accumulation Delay. In packets."
       ::= {channelStatusEntry 16}



     fXSorFXO OBJECT-TYPE
       SYNTAX INTEGER {
                  nonAnalogDevice(-1)
,
                  fXO(0)
,
                  fXS(1)

                  }
       MAX-ACCESS read-only
       STATUS deprecated
       DESCRIPTION
           "returns the type phisical type of endpoint"
       ::= {channelStatusEntry 17}



     channelHookState OBJECT-TYPE
       SYNTAX INTEGER {
                  nonAnalogDevice(-1)
,
                  offHook(0)
,
                  onHook(1)

                  }
       MAX-ACCESS read-only
       STATUS deprecated
       DESCRIPTION
           "Channel Hook State"
       ::= {channelStatusEntry 18}




     -- ****************************************
     -- acTrap Configuration
     -- ****************************************
     acTrap                        OBJECT IDENTIFIER ::= {acBoard 21}


     -- ****************************************
     -- acBoardTrapGlobals Configuration
     -- ****************************************
     acBoardTrapGlobals            OBJECT IDENTIFIER ::= {acTrap 1}


     acBoardTrapGlobalsName OBJECT-TYPE
       SYNTAX INTEGER (0..1000)
       MAX-ACCESS read-only
       STATUS current
       DESCRIPTION
           "trap name"
       ::= {acBoardTrapGlobals 1}



     acBoardTrapGlobalsTextualDescription OBJECT-TYPE
       SYNTAX OCTET STRING (SIZE (0..200))
       MAX-ACCESS read-only
       STATUS current
       DESCRIPTION
           "title of trap"
       ::= {acBoardTrapGlobals 2}



     acBoardTrapGlobalsSource OBJECT-TYPE
       SYNTAX OCTET STRING (SIZE (0..100))
       MAX-ACCESS read-only
       STATUS current
       DESCRIPTION
           "Trap Source - MG1/Shelf1/Board2/Trunk3"
       ::= {acBoardTrapGlobals 3}



     acBoardTrapGlobalsSeverity OBJECT-TYPE
       SYNTAX INTEGER {
                  cleared(0)
,
                  indeterminate(1)
,
                  warning(2)
,
                  minor(3)
,
                  major(4)
,
                  critical(5)

                  }
       MAX-ACCESS read-only
       STATUS current
       DESCRIPTION
           "Trap Severity"
       ::= {acBoardTrapGlobals 4}



     acBoardTrapGlobalsUniqID OBJECT-TYPE
       SYNTAX INTEGER (0..32000)
       MAX-ACCESS read-only
       STATUS current
       DESCRIPTION
           "Trap Uniq Id - generated by AcBoard and should be uniq for the entire EMS"
       ::= {acBoardTrapGlobals 5}



     acBoardTrapGlobalsType OBJECT-TYPE
       SYNTAX INTEGER {
                  other(0)
,
                  communicationsAlarm(1)
,
                  qualityOfServiceAlarm(2)
,
                  processingErrorAlarm(3)
,
                  equipmentAlarm(4)
,
                  environmentalAlarm(5)
,
                  integrityViolation(6)
,
                  operationalViolation(7)
,
                  physicalViolation(8)
,
                  securityServiceOrMechanismViolation(9)
,
                  timeDomainViolation(10)

                  }
       MAX-ACCESS read-only
       STATUS current
       DESCRIPTION
           "Trap type - ItuAlarmType"
       ::= {acBoardTrapGlobals 6}



     acBoardTrapGlobalsProbableCause OBJECT-TYPE
       SYNTAX INTEGER {
                  other(0)
,
                  adapterError(1)
,
                  applicationSubsystemFailure(2)
,
                  bandwidthReduced(3)
,
                  callEstablishmentError(4)
,
                  communicationsProtocolError(5)
,
                  communicationsSubsystemFailure(6)
,
                  configurationOrCustomizationError(7)
,
                  congestion(8)
,
                  corruptData(9)
,
                  cpuCyclesLimitExceeded(10)
,
                  dataSetOrModemError(11)
,
                  degradedSignal(12)
,
                  dteDceInterfaceError(13)
,
                  enclosureDoorOpen(14)
,
                  equipmentMalfunction(15)
,
                  excessiveVibration(16)
,
                  fileError(17)
,
                  fireDetected(18)
,
                  floodDetected(19)
,
                  framingError(20)
,
                  heatingVentCoolingSystemProblem(21)
,
                  humidityUnacceptable(22)
,
                  inputOutputDeviceError(23)
,
                  inputDeviceError(24)
,
                  lanError(25)
,
                  leakDetected(26)
,
                  localNodeTransmissionError(27)
,
                  lossOfFrame(28)
,
                  lossOfSignal(29)
,
                  materialSupplyExhausted(30)
,
                  multiplexerProblem(31)
,
                  outOfMemory(32)
,
                  ouputDeviceError(33)
,
                  performanceDegraded(34)
,
                  powerProblem(35)
,
                  pressureUnacceptable(36)
,
                  processorProblem(37)
,
                  pumpFailure(38)
,
                  queueSizeExceeded(39)
,
                  receiveFailure(40)
,
                  receiverFailure(41)
,
                  remoteNodeTransmissionError(42)
,
                  resourceAtOrNearingCapacity(43)
,
                  responseTimeExecessive(44)
,
                  retransmissionRateExcessive(45)
,
                  softwareError(46)
,
                  softwareProgramAbnormallyTerminated(47)
,
                  softwareProgramError(48)
,
                  storageCapacityProblem(49)
,
                  temperatureUnacceptable(50)
,
                  thresholdCrossed(51)
,
                  timingProblem(52)
,
                  toxicLeakDetected(53)
,
                  transmitFailure(54)
,
                  transmitterFailure(55)
,
                  underlyingResourceUnavailable(56)
,
                  versionMismatch(57)
,
                  authenticationFailure(58)
,
                  breachOfConfidentiality(59)
,
                  cableTamper(60)
,
                  delayedInformation(61)
,
                  denialOfService(62)
,
                  duplicateInformation(63)
,
                  informationMissing(64)
,
                  informationModificationDetected(65)
,
                  informationOutOfSequence(66)
,
                  intrusionDetection(67)
,
                  keyExpired(68)
,
                  nonRepudiationFailure(69)
,
                  outOfHoursActivity(70)
,
                  outOfService(71)
,
                  proceduralError(72)
,
                  unauthorizedAccessAttempt(73)
,
                  unexpectedInformation(74)

                  }
       MAX-ACCESS read-only
       STATUS current
       DESCRIPTION
           "Trap probable cause - SnmpAlarmProbableCause"
       ::= {acBoardTrapGlobals 7}



     acBoardTrapGlobalsAdditionalInfo1 OBJECT-TYPE
       SYNTAX OCTET STRING (SIZE (0..100))
       MAX-ACCESS read-only
       STATUS current
       DESCRIPTION
           "Trap additional info global field"
       ::= {acBoardTrapGlobals 8}



     acBoardTrapGlobalsAdditionalInfo2 OBJECT-TYPE
       SYNTAX OCTET STRING (SIZE (0..100))
       MAX-ACCESS read-only
       STATUS current
       DESCRIPTION
           "Trap additional info global field"
       ::= {acBoardTrapGlobals 9}



     acBoardTrapGlobalsAdditionalInfo3 OBJECT-TYPE
       SYNTAX OCTET STRING (SIZE (0..100))
       MAX-ACCESS read-only
       STATUS current
       DESCRIPTION
           "Trap additional info global field"
       ::= {acBoardTrapGlobals 10}



     acBoardTrapGlobalsDateAndTime OBJECT-TYPE
       SYNTAX DateAndTime
       MAX-ACCESS read-only
       STATUS current
       DESCRIPTION
           "Date and time that the trap was sent."
       ::= {acBoardTrapGlobals 11}



     acBoardTrapGlobalsSystemSeverity OBJECT-TYPE
       SYNTAX INTEGER {
                  noAlarm(0)
,
                  indeterminate(1)
,
                  warning(2)
,
                  minor(3)
,
                  major(4)
,
                  critical(5)

                  }
       MAX-ACCESS read-only
       STATUS current
       DESCRIPTION
           "The highest alarm severity on the system."
       ::= {acBoardTrapGlobals 12}




     acBoardTrapGlobalsDeviceName OBJECT-TYPE
	   SYNTAX OCTET STRING (SIZE (0..255))
       MAX-ACCESS read-only
       STATUS current
       DESCRIPTION
           "acBoardTrapGlobalsDeviceName Used by AC-EMS only"
       ::= {acBoardTrapGlobals 13}



     acBoardTrapGlobalsDeviceInfo OBJECT-TYPE
       SYNTAX OCTET STRING (SIZE (0..255))
       MAX-ACCESS read-only
       STATUS current
       DESCRIPTION
           "acBoardTrapGlobalsDeviceInfo Used by AC-EMS only"
       ::= {acBoardTrapGlobals 14}



     acBoardTrapGlobalsDeviceDescriprion OBJECT-TYPE
       SYNTAX OCTET STRING (SIZE (0..100))
       MAX-ACCESS read-only
       STATUS current
       DESCRIPTION
           "acBoardTrapGlobalsDeviceDescriprion Used by AC-EMS only"
       ::= {acBoardTrapGlobals 15}



     acBoardTrapGlobalsSystemSerialNumber OBJECT-TYPE
       SYNTAX OCTET STRING (SIZE (0..255))
       MAX-ACCESS read-only
       STATUS current
       DESCRIPTION
           "NE Serial Number represented as string."
       ::= {acBoardTrapGlobals 16}
       
       
       
     -- ****************************************







     -- ****************************************
     -- acBoardTrapDefinitions Configuration
     -- ****************************************
     acBoardTrapDefinitions        OBJECT IDENTIFIER ::= {acTrap 2}


     acBoardFatalError NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Board fatal error"
       ::= {acBoardTrapDefinitions 0 1}



     acBoardConfigurationError NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Configuration Error"
       ::= {acBoardTrapDefinitions 0 2}



     acBoardTemperatureAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Temperature Alarm. Turned on when temperature exceeds 60 degrees Celsius, and relaxes when temperature goes under 55 again."
       ::= {acBoardTrapDefinitions 0 3}



     acBoardEvBoardStarted NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Initialization Ended"
       ::= {acBoardTrapDefinitions 0 4}



     acBoardEvResettingBoard NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "The board start Reset process - following software reset"
       ::= {acBoardTrapDefinitions 0 5}



     acFeatureKeyError NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Feature key related Error"
       ::= {acBoardTrapDefinitions 0 6}



     acgwAdminStateChange NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "The administrative state of the gate way has been changed to a new state."
       ::= {acBoardTrapDefinitions 0 7}



     acBoardCallResourcesAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "No free channels available"
       ::= {acBoardTrapDefinitions 0 8}



     acBoardControllerFailureAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "The GK/Proxy not found or registration failed. internal routing table may be used for routing"
       ::= {acBoardTrapDefinitions 0 9}



     acBoardEthernetLinkAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Ethernet Link is down or remote Ethernet link is down and board has no communication to any other host"
       ::= {acBoardTrapDefinitions 0 10}



     acBoardOverloadAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Overload in one or some of the system's components"
       ::= {acBoardTrapDefinitions 0 11}



     acActiveAlarmTableOverflow NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "An active alarm could not be placed in the active alarm table because the table is full. 
This alarm will not clear. Reboot is the only way to completely clear the Active Alarm table overflow problem.
Any alarm raised at this state will not be Carrier Grade compatible. Therefore, Updates will not clear the alarm
before changing the bindings and re-raising alarms. The History tables remain unaffected. 
All Alarms raised prior to overflow will remain Carrier Grade compatible. 
Other alarms, raised after this alarm was raised, that are placed in the Active Alarm table will be Carrier Grade 
compatible. (This is for when after the alarm was raised there were some clears, clearing alarms off the Active Alarm table)."
       ::= {acBoardTrapDefinitions 0 12}



     acAtmPortAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           " ATM Port Alarm"
       ::= {acBoardTrapDefinitions 0 13}



     acAudioProvisioningAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           " This alarm is raised if the Media Server is unable to provision its audio. This could be because the Audio Provisioning System (APS) is down or there is a network problem."
       ::= {acBoardTrapDefinitions 0 14}



     acOperationalStateChange NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised if the operational state of the node goes to disabled. The alarm is cleared when the operational state of the node goes to enabled."
       ::= {acBoardTrapDefinitions 0 15}



     acKeepAlive NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This trap is the NAT Traversal keep alive trap. 
If the STUN application in the device detects a NAT then this trap will be sent out on a regular time laps - 9/10 of the acSysSTUNBindingLifeTime object. The AdditionalInfo1 varbind has the MAC address of the device.
Note that all traps are sent out from the SNMP Port (usually 161)."
       ::= {acBoardTrapDefinitions 0 16}



     acNATTraversalAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "When the NAT placed in front a device is identified as a symmetric NAT - this alarm is raised. It is cleared when a non-symmetric NAT or no NAT replace the symmetric one. "
       ::= {acBoardTrapDefinitions 0 17}



     acEnhancedBITStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This trap is used to for the status of the BIT (Built In Test).
The information in the trap contains board HW elements being tested and their status.
The information is presented in the additional info fields."
       ::= {acBoardTrapDefinitions 0 18}



     acSS7LinkStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised if the operational state of the SS7 link becomes XXXX. The alarm is cleared when the operational state of the link becomes XXXX."
       ::= {acBoardTrapDefinitions 0 19}



     acSS7LinkInhibitStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised if the SS7 link becomes inhibited (local or remote). The alarm is cleared when the link becomes uninhibited - local AND remote. Note that this alarm will be raised for any change in the remote or local inhibition status."
       ::= {acBoardTrapDefinitions 0 20}



     acSS7LinkBlockStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised if the SS7 link becomes blocked (local or remote). The alarm is cleared when the link becomes unblocked - local AND remote. Note that this alarm will be raised for any change in the remote or local blocking status."
       ::= {acBoardTrapDefinitions 0 21}



     acSS7LinkCongestionStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised if the SS7 link becomes congested (local or remote). The alarm is cleared when the link becomes uncongested - local AND remote. Note that this alarm will be raised for any change in the remote or local congestion status."
       ::= {acBoardTrapDefinitions 0 22}



     acSS7LinkSetStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised if the operational state of the SS7 linkset becomes BUSY. The alarm is cleared when the operational state of the linkset becomes IN-SERVICE or OFFLINE."
       ::= {acBoardTrapDefinitions 0 23}



     acSS7RouteSetStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised if the operational state of the SS7 routeset becomes BUSY. The alarm is cleared when the operational state of the routeset becomes IN-SERVICE or OFFLINE."
       ::= {acBoardTrapDefinitions 0 24}



     acSS7SNSetStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised if the operational state of the SS7 node becomes BUSY. The alarm is cleared when the operational state of the node becomes IN-SERVICE or OFFLINE."
       ::= {acBoardTrapDefinitions 0 25}



     acSS7RedundancyAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Raised when the SS7 redundancy degregated. Cleared when all entities of redundancy are fully functional and in serveice."
       ::= {acBoardTrapDefinitions 0 26}



     acPerformanceMonitoringThresholdCrossing NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This log trap is sent out for every time the threshold
of a Performance Monitored object is crossed.
The severity field is 'indeterminate' when the crossing is above the threshold
and 'cleared' when it goes back under the threshold.
The 'source' varbind in the trap indicates the object
for which the threshold is being crossed."
       ::= {acBoardTrapDefinitions 0 27}



     acHTTPDownloadResult NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This trap indicates the result of a recent file download (includes HTTP error code, if available)."
       ::= {acBoardTrapDefinitions 0 28}



     acFanTrayAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when the fan tray is missing or some of the fans are faulty.
If the fan tray is missing or more then X fans are faulty the severity will be Critical.
If more then one and less the X fans are faulty the severity will be Major.
"
       ::= {acBoardTrapDefinitions 0 29}



     acPowerSupplyAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when the HA (High Availability) feature is active and one of the power supply units is faulty."
       ::= {acBoardTrapDefinitions 0 30}



     acPEMAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when the HA (High Availability) feature is active. The severity is critical if one of the PEM units is missing and major if the electric wire to one of the units is disconnected. "
       ::= {acBoardTrapDefinitions 0 31}



     acSAMissingAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when the SA module in the M3K MG is missing. Whenthere is no SAT there are no other chassis HW related alarms.
Note - relevant only for M3K."
       ::= {acBoardTrapDefinitions 0 32}



     acHASystemFaultAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when the HA (High Availability) feature is active and the system is NOT HA.
Critical severity - 
1.Wrong HW Configuration.
2. Redundant module is missing (not in slot).
3. The redundant module is non operable.
Minor severity -  waiting for redunadant to connect (after reset!). "
       ::= {acBoardTrapDefinitions 0 33}



     acHASystemConfigMismatchAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when the HA (High Availability) feature is active and there has been a configuration change due to which the HA system may or may not be usable."
       ::= {acBoardTrapDefinitions 0 34}



     acHASystemSwitchOverAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when the HA (High Availability) feature is active and there has been a switchover due to failure or reset in the active module."
       ::= {acBoardTrapDefinitions 0 35}



     acUserInputAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This Alarm is raised when the input dry contact is short circuited. Cleared when the circuit is reopened."
       ::= {acBoardTrapDefinitions 0 36}



     acDChannelStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This non alarm trap is sent when establishment, re-establishment or release of LAPD link with its peer connection occurs.
The trap will be sent out with one of the following in the textual description:
D-channel synchronized
D-channel not-synchronized"
       ::= {acBoardTrapDefinitions 0 37}



     acSonetSectionLOFAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "SONET section Loss of Frame alarm."
       ::= {acBoardTrapDefinitions 0 38}



     acSonetSectionLOSAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "SONET section Loss of Signal alarm."
       ::= {acBoardTrapDefinitions 0 39}



     acSonetLineAISAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "SONET Line AIS alarm."
       ::= {acBoardTrapDefinitions 0 40}



     acSonetLineRDIAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "SONET Line RDI alarm."
       ::= {acBoardTrapDefinitions 0 41}



     acSonetIfHwFailureAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "SONET or SDH medium Interface has failed."
       ::= {acBoardTrapDefinitions 0 42}



     acHwFailureAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "HW failure alarm."
       ::= {acBoardTrapDefinitions 0 43}



     acH248LostConnectionWithCA NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "H248 lost connection with call agent"
       ::= {acBoardTrapDefinitions 0 44}



     acDialPlanFileReplaced NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "dial plan file replaced notification"
       ::= {acBoardTrapDefinitions 0 45}



     acAnalogPortSPIOutOfService NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Analog port out of service "
       ::= {acBoardTrapDefinitions 0 46}



     acAnalogPortHighTemperature NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Analog Port High Temperature"
       ::= {acBoardTrapDefinitions 0 47}



     acHitlessUpdateStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Notification trap that is sent out at the beginning and the end of a Hitless SW update.
Failure during the process will also instigate the trap.
Relevant to HA systems only."
       ::= {acBoardTrapDefinitions 0 48}



     acTrunksAlarmNearEndLOS NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Loss of signal at trunk's near end."
       ::= {acBoardTrapDefinitions 0 49}



     acTrunksAlarmNearEndLOF NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Loss of frame at trunk's near end."
       ::= {acBoardTrapDefinitions 0 50}



     acTrunksAlarmRcvAIS NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Received AIS from trunk's far end."
       ::= {acBoardTrapDefinitions 0 51}



     acTrunksAlarmFarEndLOF NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Loss of frame at trunk's far end."
       ::= {acBoardTrapDefinitions 0 52}



     acIPv6ErrorAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Alarm trap that is sent out for IPv6 related errors."
       ::= {acBoardTrapDefinitions 0 53}



     acAMSProcedureResult NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "AMS procedure related information"
       ::= {acBoardTrapDefinitions 0 54}



     acWeakRedundancy NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "The system is in weak redundancy mode. Switch over is done with a reset to the board taking over."
       ::= {acBoardTrapDefinitions 0 55}



     acTMInconsistentRemoteAndLocalPLLStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Inconsistent Remote And Local PLL Status "
       ::= {acBoardTrapDefinitions 0 56}



     acTMReferenceStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Timing manager reference status"
       ::= {acBoardTrapDefinitions 0 57}



     acTMReferenceChange NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Timing manager reference Change"
       ::= {acBoardTrapDefinitions 0 58}



     acGWSASEmergencyModeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "The alarm is raised when SAS enters the Emergency Mode and then cleared when SAS enters Normal Mode again."
       ::= {acBoardTrapDefinitions 0 59}



     acV52InterfaceAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "The alarm is raised for v5.2 interface errors and alarms.{@}For a detailed list of the interfaces' alarms see the acV5InterfceTable."
       ::= {acBoardTrapDefinitions 0 60}



     acSonetPathSTSLOPAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Sonet Path STS  LOP alarm."
       ::= {acBoardTrapDefinitions 0 61}



     acSonetPathSTSAISAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Sonet Path STS AIS alarm."
       ::= {acBoardTrapDefinitions 0 62}



     acSonetPathSTSRDIAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Sonet Path STS RDI alarm."
       ::= {acBoardTrapDefinitions 0 63}



     acSonetPathUnequippedAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Sonet Path Unequipped alarm."
       ::= {acBoardTrapDefinitions 0 64}



     acSonetPathSignalLabelMismatchAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Sonet Path Signal Label Mismatch alarm."
       ::= {acBoardTrapDefinitions 0 65}



     acDS3RAIAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "DS3 RAI alarm."
       ::= {acBoardTrapDefinitions 0 66}



     acDS3AISAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "DS3 AIS alarm."
       ::= {acBoardTrapDefinitions 0 67}



     acDS3LOFAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "DS3 LOF alarm."
       ::= {acBoardTrapDefinitions 0 68}



     acDS3LOSAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "DS3 LOS alarm."
       ::= {acBoardTrapDefinitions 0 69}



     acSWUpgradeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Raised for SW upgrade process errors."
       ::= {acBoardTrapDefinitions 0 70}



     acNTPServerStatusAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "NTP server status alarm. {@}Raised when the connection to the NTP server is lost. Cleared when the connection is reestablished. {@}Unset time (as a result of no connection to NTP server) may result with functionality degradation and failure in device."
       ::= {acBoardTrapDefinitions 0 71}



     acThreeWayConferenceOutOfResources NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Three way conference  out of resources.  "
       ::= {acBoardTrapDefinitions 0 72}



     acSS7AliasPcStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "raised when the Alias PC is in BUSY state. Cleared when it is in In-Service state."
       ::= {acBoardTrapDefinitions 0 73}



     acSS7UalGroupStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Raised when the Ual Group Asp state is not ACTIVE. Cleared when it is Active."
       ::= {acBoardTrapDefinitions 0 74}



     acLDAPLostConnection NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Raised when there is no connection to the LDAP server."
       ::= {acBoardTrapDefinitions 0 75}



     acAnalogPortGroundFaultOutOfService NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Raised when the MP500 FXS port is inactive due to ground fault."
       ::= {acBoardTrapDefinitions 0 76}



     acSSHConnectionStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This trap indicates the result of a recent SSH connection attempt."
       ::= {acBoardTrapDefinitions 0 77}



     acOCSPServerStatusAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "raised when OCSP connection is not available."
       ::= {acBoardTrapDefinitions 0 78}



     acBoardWanLinkAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Wan Link is down."
       ::= {acBoardTrapDefinitions 0 79}



     acPowerOverEthernetStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Raised when PEO resources are over allocated"
       ::= {acBoardTrapDefinitions 0 80}



     acMediaProcessOverloadAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Raised when media process overloads"
       ::= {acBoardTrapDefinitions 0 81}



     acWirelessCellularModemAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Raised when either the wireless modem is down or in backup mode."
       ::= {acBoardTrapDefinitions 0 82}



     acDataInterfaceStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Raised when a DSL interface state changes to up or down."
       ::= {acBoardTrapDefinitions 0 83}



     acNFASGroupAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Raised when an NFAS group goes Out-Of-Service"
       ::= {acBoardTrapDefinitions 0 84}



     acBChannelAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Raised when B-Channel service state changes"
       ::= {acBoardTrapDefinitions 0 85}



     acEthernetGroupAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Raised when the Ethernet group has no Ethernet port with its link up. Cleared when at least on port has established a link."
       ::= {acBoardTrapDefinitions 0 86}



     acMediaRealmBWThresholdAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Raised when a BW threshold is crossed"
       ::= {acBoardTrapDefinitions 0 87}



     acNqmConnectivityAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Connectivity with NQM probe destination is lost"
       ::= {acBoardTrapDefinitions 0 88}



     acNqmRttAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Detected high Round Trip Time towards NQM probe destination"
       ::= {acBoardTrapDefinitions 0 89}



     acNqmJitterAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Detected high Jitter towards NQM probe destination"
       ::= {acBoardTrapDefinitions 0 90}



     acNqmPacketLossAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Detected high Packet Loss towards NQM probe destination"
       ::= {acBoardTrapDefinitions 0 91}



     acCertificateExpiryNotification NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Send before the expiration of the installed credentials, which cannot be renewed automatically."
       ::= {acBoardTrapDefinitions 0 92}



     acWEBUserAccessDisabled NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Web user was disabled due to inactivity."
       ::= {acBoardTrapDefinitions 0 93}



     acProxyConnectionLost NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Raised when all connections in the proxy set are down."
       ::= {acBoardTrapDefinitions 0 94}



     acNqmCqMosAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Detected low conversational voice quality towards NQM probe destination"
       ::= {acBoardTrapDefinitions 0 95}



     acNqmLqMosAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Detected low listening voice quality towards NQM probe destination"
       ::= {acBoardTrapDefinitions 0 96}



     acRedundantBoardAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
	   STATUS obsolete
       DESCRIPTION
           "Active board sends notification when an alarm or notification is raised in the redundant board.
The information is as follow:
acBoardTrapGlobalsAdditionalInfo1: redundant’s original info
acBoardTrapGlobalsAdditionalInfo2: trap Id
acBoardTrapGlobalsAdditionalInfo3: redundant’s serial number
"
       ::= {acBoardTrapDefinitions 0 97}



     acHANetworkWatchdogStatusAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Sent when the module was enabled by the user but it is not running."
       ::= {acBoardTrapDefinitions 0 98}



     acIDSPolicyAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "IDS Policy Alarm"
       ::= {acBoardTrapDefinitions 0 99}



     acIDSThresholdCrossNotification NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Sent when IDS Threshold is crossed"
       ::= {acBoardTrapDefinitions 0 100}



     acIDSBlacklistNotification NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "IDS blacklist: Address [IP address with network interface] entered/exited"
       ::= {acBoardTrapDefinitions 0 101}



     acProxyConnectivity NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Sent when Proxy IP is offline or inline"
       ::= {acBoardTrapDefinitions 0 102}



     acBoardSignalingCpuUsageThresholdAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Raised when CPU utilization threshold value ( ) crossed [INI-CpuUsageThresholdAlarm]."
       ::= {acBoardTrapDefinitions 0 103}



     acWirelessCellularModemStatusChanged NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Indication of change of Wireless Cellular Modem Status"
       ::= {acBoardTrapDefinitions 0 104}



     acActivityLog NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Configuration Change event"
       ::= {acBoardTrapDefinitions 0 105}



     acLicensePoolInfraAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "will be issued in case of any infra failure"
       ::= {acBoardTrapDefinitions 0 106}



     acLicensePoolApplicationAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "will be issued by SIP, currently to indicate “out of resource” problem."
       ::= {acBoardTrapDefinitions 0 107}



     acHTTPProxyServiceAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "HTTP proxy service Alarm"
       ::= {acBoardTrapDefinitions 0 108}



     acReservedAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Reserved Alarm"
       ::= {acBoardTrapDefinitions 0 109}



     acResetNeededAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Configuration was changed. Reset the device for the new settings to take effect."
       ::= {acBoardTrapDefinitions 0 110}



     acASRThresholdAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "ASR threshold crossed"
       ::= {acBoardTrapDefinitions 0 111}



     acACDThresholdAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "ACD threshold crossed"
       ::= {acBoardTrapDefinitions 0 112}



     acNERThresholdAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "NER threshold crossed"
       ::= {acBoardTrapDefinitions 0 113}



     acIpGroupNoRouteAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "IP Group is temporarily blocked"
       ::= {acBoardTrapDefinitions 0 114}



     acMtcmClusterHaAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "At least one of the MTCEs is inactive, MTC will now provide only partial HA"
       ::= {acBoardTrapDefinitions 0 115}



     acMtceNetworkFailureAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Lost connection with board"
       ::= {acBoardTrapDefinitions 0 116}



     acMtceSwUpgradeFailureAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Reset of the MTCE is required"
       ::= {acBoardTrapDefinitions 0 117}



     acMtceHwTemperatureFailureAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "MTCE reached high temperature threshold"
       ::= {acBoardTrapDefinitions 0 118}



     acMtceHwFanTrayFailureAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "MTCE fan tray fault"
       ::= {acBoardTrapDefinitions 0 119}



     acMtcePsuFailureAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "MTCE power supply unit fault"
       ::= {acBoardTrapDefinitions 0 120}



     acTrackIdStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Will be issued when a Track goes down or up. Includes track id, interface name, destination adress and a new track state."
       ::= {acBoardTrapDefinitions 0 121}



     acModuleServiceAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Module service fault"
       ::= {acBoardTrapDefinitions 0 122}



     acModuleOperationAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Module operation fault"
       ::= {acBoardTrapDefinitions 0 123}



     acPortServiceAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Port service fault"
       ::= {acBoardTrapDefinitions 0 124}



     acLicensePoolOverAllocationAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Will be issued in case requested License pool exceeds the board ability"
       ::= {acBoardTrapDefinitions 0 125}



     acClusterBandwidthAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Sent when the bandwidth of the cluster Interface utilization is too high."
       ::= {acBoardTrapDefinitions 0 126}



     acLicensePoolExpirationAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Will be issued in case License pool is about or was expired"
       ::= {acBoardTrapDefinitions 0 127}



     acCertificateExpiryAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Send alarm before the expiration of the installed credentials, which cannot be renewed automatically (alarm type).  acCertificateExpiryNotification was obsolete."
       ::= {acBoardTrapDefinitions 0 128}



     acLicenseKeyHitlessUpgradeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "License key hitless upgrade failed due to HA switchover failure."
       ::= {acBoardTrapDefinitions 0 129}



     acNGINXConfigurationIsInvalidAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "NGINX configuration is invalid"
       ::= {acBoardTrapDefinitions 0 130}



     acNGINXPprocessIsNotRunningAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "NGINX process is not running"
       ::= {acBoardTrapDefinitions 0 131}



     acCloudLicenseManagerAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Cloud License Manager Alarm; Connection with Cloud License Manager not established or Connection with Cloud License Manager failed (response code)."
       ::= {acBoardTrapDefinitions 0 132}



     acMediaClusterAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Alarm will be raised in case that Cluster is enabled, but there is no Cluster Interface in interface Table."
       ::= {acBoardTrapDefinitions 0 133}



     acMediaClusterRemoteInterfaceAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Media Cluster Remote Interface Alarm;"
       ::= {acBoardTrapDefinitions 0 134}



     acHANetworkMismatchAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Mismatch of network devices in the cloud HA system between active and redundant instances."
       ::= {acBoardTrapDefinitions 0 135}



     acHANetworkMonitorAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Alarm will be raised when destination <IP address(es)> is unreachable."
       ::= {acBoardTrapDefinitions 0 136}



     acHAEthernetGroupAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Alarm will be raised when maintenance's Ethernet-group gets an alarm state."
       ::= {acBoardTrapDefinitions 0 137}



     acFloatingLicenseAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Alarm will be raised when there is not enough memory to allocate “custom” profile ."
       ::= {acBoardTrapDefinitions 0 138}



     acAWSSecurityRoleAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is sent when the AWS instance has not been configured with the required IAM role in order to access AWS services and resources."
       ::= {acBoardTrapDefinitions 0 139}



     acInstallationFailureAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is sent when one of Installation package was not install; it applicable to Hosted only."
       ::= {acBoardTrapDefinitions 0 140}



     acAnalogLineLeftOffhookAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is sent when a phone left Offhook for X seconds, defined by FXSOffhookTimeoutAlarm. The deault value is no alarm."
       ::= {acBoardTrapDefinitions 0 141}



     acCDRServerAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is sent when SBC failed to upload CDRs to all configured servers."
       ::= {acBoardTrapDefinitions 0 142}



     acDSPFarmsMismatchAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is sent when missing DSP farm was detected."
       ::= {acBoardTrapDefinitions 0 143}



     acFlexLicenseManagerAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Flex License Manager Alarm; Connection with Flex License Manager not established or Connection with Flex License Manager failed (response code)."
       ::= {acBoardTrapDefinitions 0 144}



     acRemoteMonitoringAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Remote Monitoring Alarm; There is no connetion with remote monitoring server."
       ::= {acBoardTrapDefinitions 0 145}



     acMeteringAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Warning severity: No connection to AWS marketplace API – service will be down in 1 hour.
Critical severity:  Service down due to lack of connection to AWS marketplace API.
"
       ::= {acBoardTrapDefinitions 0 146}



     acSDRServerAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is sent when SBC failed to upload SDRs to all configured servers."
       ::= {acBoardTrapDefinitions 0 147}



     acKpiThresholdCrossing NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This log trap is sent out for every time the threshold
of a Performance Monitored object is crossed.
The severity field is 'indeterminate' when the crossing is above the threshold
and 'cleared' when it goes back under the threshold.
The 'source' varbind in the trap indicates the object
for which the threshold is being crossed."
       ::= {acBoardTrapDefinitions 0 148}



     acClockConfigurationAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is sent when both NTP and Date Header Time Sync are enabled.
 NTP will be used as the source for the clock sync."
       ::= {acBoardTrapDefinitions 0 149}



     acDebugRecordingActivationAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is sent when Debug Recording is enabled."
       ::= {acBoardTrapDefinitions 0 150}



     acMCNotSecuredAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when the MC is connected using TCP rather than TLS."
       ::= {acBoardTrapDefinitions 0 151}



     acFaultyDSPAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when one or more DSPs fail to load properly."
       ::= {acBoardTrapDefinitions 0 152}



     acDspOperationAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "HW failure detected on DSP."
       ::= {acBoardTrapDefinitions 0 153}



     acTLSCertificateMismatchAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when there is a mismatch between Certificate and Private Key."
       ::= {acBoardTrapDefinitions 0 154}



     acNoReplyFromDNSServerAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when there is no reply from DNS server."
       ::= {acBoardTrapDefinitions 0 155}



     acWeakPasswordAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when a user <username> has weak password."
       ::= {acBoardTrapDefinitions 0 156}



     acVMMaintenanceAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when the maintenance events monitoring task detects an upcoming event."
       ::= {acBoardTrapDefinitions 0 157}



     acIPv4ErrorAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "Alarm trap that is sent out for IPv4 related errors."
       ::= {acBoardTrapDefinitions 0 158}



     acTLSSocketsLimitAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "The alarm is raised when the number of SIP incoming TLS connections reach 95% of max number supported."
       ::= {acBoardTrapDefinitions 0 159}



     acRtpOnlyBrokenRtpConnectionAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "The alarm is raised when there is a broken RTP connection on at least one of the RTP-only sessions"
       ::= {acBoardTrapDefinitions 0 160}



     acExpiredPasswordAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "The alarm is raised when the user password is nearing expiration."
       ::= {acBoardTrapDefinitions 0 161}



     acResourcePoolAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when utilization of the named resource pool has exceeded its defined threshold."
       ::= {acBoardTrapDefinitions 0 162}



     acIpGroupKeepAliveAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when there is no connection with IP Group."
       ::= {acBoardTrapDefinitions 0 163}



     acAccountRegistrationAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime,
                
                acBoardTrapGlobalsSystemSeverity,
                
                acBoardTrapGlobalsDeviceName,
                
                acBoardTrapGlobalsDeviceInfo,
                
                acBoardTrapGlobalsDeviceDescriprion,
                
                acBoardTrapGlobalsSystemSerialNumber
               }
       STATUS current
       DESCRIPTION
           "This alarm is raised when there is registration failure for account."
       ::= {acBoardTrapDefinitions 0 164}




END
