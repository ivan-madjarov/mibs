--
--				"%Z%%M% %D%"
--
-- Enterprise Specific Traps for Fibre Channel Switch (sw).
--		Version 4.0
--
-- This is specified based on RFC1215.
--
-- Changes since V2.1:
-- 11/11/99
-- added swThreshMonTrap to support snmp trap for threshold monitor subsystem.
-- 01/24/00
-- added swTrackChangesTrap.
-- 01/24/00
-- changed swThreshMonTrap severity to warning.
-- 01/25/00
-- changed swThreshMonTrap to swFabricWatchTrap.
-- 02/02/00
-- changed few threshold monitor reference overlooked with Fabric Watch
-- 02/16/00
-- th prefix for Fabric Watch has been changed to swFw
--

SW-TRAP DEFINITIONS ::= BEGIN
  IMPORTS
	enterprises
		FROM RFC1155-SMI
	
	TRAP-TYPE
		FROM RFC1215;

  bcsi		OBJECT IDENTIFIER ::= { enterprises 1588 }

  -- Product Lines or Generic Product information
  --  { bcsi 1 } is reserved
  commDev	OBJECT IDENTIFIER ::= { bcsi 2 } -- communication devices

  fibrechannel	OBJECT IDENTIFIER ::= { commDev 1 }
  fcSwitch	OBJECT IDENTIFIER ::= { fibrechannel 1 }

  sw		OBJECT IDENTIFIER ::= { fcSwitch 1 }
  --
  -- sw Traps
  --

  swFault		TRAP-TYPE
	ENTERPRISE	sw
	VARIABLES	{ swDiagResult }
	DESCRIPTION	"A swFault(1) is generated whenever the diagnostics
		detects a fault with the switch."
	--#TYPE		"Switch is faulty."
	--#SUMMARY	"Faulty reason: %d"
	--#ARGUMENTS	{ 0 }
	--#SEVERITY	CRITICAL
	--#TIMEINDEX	1
	--#STATE	NONOPERATIONAL
	::= 1

  swSensorScn	TRAP-TYPE
	ENTERPRISE	sw
	VARIABLES	{ swSensorStatus, swSensorIndex, swSensorType,
			  swSensorValue, swSensorInfo }
	DESCRIPTION	"A swSensorScn(2) is generated whenever an
		environment sensor changes its operational state. For instance,
		a fan stop working. The VarBind in the Trap Data Unit shall
		contain the corresponding instance of the sensor
		status, sensor index, sensor type, sensor value (reading)
		and sensor information. Note that the sensor information
		contains the type of sensor and its number in textual format."
	--#TYPE		"A sensor (temperature, fan, etc.) changed its operational state."
	--#SUMMARY	"%s: is currently in state %d"
	--#ARGUMENTS	{ 4, 0 }
	--#SEVERITY	INFORMATIONAL
	--#TIMEINDEX	1
	--#STATE	OPERATIONAL
	::= 2

   swFCPortScn		TRAP-TYPE
	ENTERPRISE	sw
	VARIABLES	{ swFCPortOpStatus, swFCPortIndex }
	DESCRIPTION	"A swFCPortScn(3) is generated whenever an FC_Port
		changes its operational state. For instance, the FC_Port
		goes from on-line to offline. The VarBind in the Trap Data
		Unit shall contain the corresponding instance of the
		FC_Port's operational status and index."
	--#TYPE		"A Fibre Channel Port changed its operational state."
	--#SUMMARY	"Port Index %d changed state to %d"
	--#ARGUMENTS	{ 1, 0 }
	--#SEVERITY	INFORMATIONAL
	--#TIMEINDEX	1
	--#STATE	OPERATIONAL
	::= 3

   swEventTrap           TRAP-TYPE
        ENTERPRISE      sw
        VARIABLES       { swEventIndex, swEventTimeInfo, swEventLevel,
                          swEventRepeatCount, swEventDescr }
        DESCRIPTION     "This trap is generated when an event whose
                level at or below swEventTrapLevel occurs."
	--#TYPE		"A firmware event has been logged"
	--#SUMMARY	"Event %d: %s (severity level %d) - %s"
	--#ARGUMENTS	{ 0, 1, 2, 4 }
	--#SEVERITY	INFORMATIONAL
	--#TIMEINDEX	1
	--#STATE	OPERATIONAL
	::= 4

  -- traps for Fabric Watch subsystem

  swFabricWatchTrap	TRAP-TYPE
	ENTERPRISE	sw
	VARIABLES	{	swFwClassAreaIndex,
					swFwThresholdIndex,
					swFwName,
					swFwLabel,
					swFwLastEventVal,
					swFwLastEventTime,
					swFwLastEvent,
					swFwLastState
					}
	DESCRIPTION	"trap to be sent by Fabric Watch to notify of an event"
	--#TYPE		"Fabric Watch has generated an event"
	--#SUMMARY	"Threshold %s in Class/Area %d at index %d has generated event %d with %d on %s. This event is %d"
	--#ARGUMENTS	{ 2, 0, 1, 6, 4, 5 , 7}
	--#SEVERITY	WARNING
	--#TIMEINDEX	1
	--#STATE	OPERATIONAL
	::= 5

  -- traps for track changes subsystem

  swTrackChangesTrap	TRAP-TYPE
	ENTERPRISE	sw
	VARIABLES	{	swTrackChangesInfo
					}
	DESCRIPTION	"trap to be sent for tracking login/logout/config changes"
	--#TYPE		"Track changes has generated a trap"
	--#SUMMARY	"%s"
	--#ARGUMENTS	{ 0 }
	--#SEVERITY	INFORMATIONAL
	--#TIMEINDEX	1
	--#STATE	OPERATIONAL
	::= 6

   -- end of Enterprise Specific Traps for Fibre Channel Switch (sw)
END
