--
--  IPSTOR MIB
--			     
--
--  Last edit date: Mar. 29, 2011
--
--

IPSTOR-MIB DEFINITIONS ::= BEGIN

IMPORTS
	mgmt, enterprises, IpAddress,
	OBJECT-TYPE, private,
	Integer32, Counter32, IpAddress,
	mib-2, Unsigned32, Counter64
		FROM SNMPv2-SMI
	DisplayString
		FROM RFC1213-MIB
	TRAP-TYPE
		FROM RFC-1215;
        
--      ipstor MODULE-IDENTITY
--      LAST-UPDATED "110329000Z"
--      ORGANIZATION "FalconStor Software, Inc."
--      CONTACT-INFO    
--      Primary Author: FalconStor Software, Inc.
--
--      US: 
--      postal:  2 Huntington Quadrangle
--		 Suite 2S01
--               Melville, NY 11747
--      phone:   631 777-3332
--
--      Asia:
--      postal:  6F-1,No.512, Section 1, 
--               Wunsin Road, 
--               Taichung, 
--               Taiwan, 403, R.O.C. 
--      phone:   +886-4-2258-6118
--
--      email:   support@falconstor.com"
--
--	DESCRIPTION
--	"This file defines the private IPStor MIB extensions."
--	::= { enterprises 7368 }
    
    ipstor OBJECT IDENTIFIER ::= { enterprises 7368 }

--------------------------------------------------------------------

	revisionNumber  OBJECT-TYPE
		SYNTAX  DisplayString (SIZE (4))
		ACCESS  read-only 
		STATUS  mandatory 
		DESCRIPTION
			"This is the revision number for this MIB. The format of the revision value is as follows
				(0) = high order major revision number
				(1) = low order major revision number
				(2) = high order minor revision number
				(3) = low order minor revision number
			The value will be stored as an ASCII value. The	following is the mandatory value of this object.
				(0) = '0'
				(1) = '1'
				(2) = '0'
				(3) = '0'
			This defines a revision of 01.00"
	::= { ipstor 1 }
        
	isServerOrClient	OBJECT-TYPE
		SYNTAX	DisplayString
		ACCESS	read-only
		STATUS	mandatory
		DESCRIPTION
			"It indicates the current running system is server or client version."
	::= { ipstor 2 }

	ipstorserver       OBJECT IDENTIFIER ::= { ipstor 3 }
	ipstorclient       OBJECT IDENTIFIER ::= { ipstor 4 }
--	ipstorsnmpagent    OBJECT IDENTIFIER ::= { ipstor 5 }
	ipstoroeminfo      OBJECT IDENTIFIER ::= { ipstor 10 }
	falconstorapplianceinfo	OBJECT IDENTIFIER ::= { ipstor 11 }

-- ***************************************************************
-- IPStor Server Group
-- ***************************************************************

--
-- Server Info
--
	serverInfo OBJECT IDENTIFIER ::= { ipstorserver 1 }

	serverName  OBJECT-TYPE
		SYNTAX  DisplayString
		ACCESS  read-only
		STATUS  mandatory
		DESCRIPTION
			"The hostname which the IPStor server is running."
	::= { serverInfo 1 }
	
	loginMachineName    OBJECT-TYPE
		SYNTAX  DisplayString
		ACCESS  read-only
		STATUS  mandatory
		DESCRIPTION
			"Identify which IPStor server you are login."
	::= { serverInfo 2 }

	serverVersion   OBJECT-TYPE
		SYNTAX  DisplayString
		ACCESS  read-only
		STATUS  mandatory
		DESCRIPTION
			"The IPStor server version and build number."
	::= { serverInfo 3 }

	osVersion   OBJECT-TYPE
		SYNTAX  DisplayString
		ACCESS  read-only
		STATUS  mandatory
		DESCRIPTION
			"The operation system version of the host the IPStor server is running."
	::= { serverInfo 4 }

	kernelVersion   OBJECT-TYPE
		SYNTAX  DisplayString
		ACCESS  read-only
		STATUS  mandatory
		DESCRIPTION
			"The kernel version of the host the IPStor server is running."
	::= { serverInfo 5 }

	processorTable  OBJECT-TYPE
		SYNTAX  SEQUENCE OF ProcessorEntry
		ACCESS	not-accessible
		STATUS  mandatory
		DESCRIPTION
			"A table containing the information of all processors in the host which the IPStor server is running."
	::= { serverInfo 6 }

	processorEntry  OBJECT-TYPE
		SYNTAX  ProcessorEntry
		ACCESS	not-accessible
		STATUS  mandatory
		DESCRIPTION
			"Information the specification of processor."
		INDEX { processorNo }
	::= { processorTable 1 }

	ProcessorEntry ::= SEQUENCE {
		processorNo	    INTEGER,
		processorInfo	DisplayString
	}

	processorNo OBJECT-TYPE
		SYNTAX  INTEGER
		ACCESS  read-only
		STATUS	mandatory
		DESCRIPTION
			"The sequential digit number as a index key of the processor table."
	::= { processorEntry 1 }

	processorInfo   OBJECT-TYPE
		SYNTAX  DisplayString
		ACCESS  read-only
		STATUS	mandatory
		DESCRIPTION
			"The specification of a processor type and power."
	::= { processorEntry 2 }

	memory  OBJECT-TYPE
		SYNTAX  DisplayString
		ACCESS  read-only
		STATUS  mandatory
		DESCRIPTION
			"The amount of memory which the IPStor server is running."
	::= { serverInfo 7 }

	swap    OBJECT-TYPE
		SYNTAX  DisplayString
		ACCESS  read-only
		STATUS  mandatory
		DESCRIPTION
			"The swap space of the host which the sIPStor erver is running."
	::= { serverInfo 8 }

	netInterfaceTable   OBJECT-TYPE
		SYNTAX  SEQUENCE OF NetInterface
		ACCESS	not-accessible
		STATUS  mandatory
		DESCRIPTION
			"A table containing the information of all network interfaces in the host which the IPStor server is running."
	::= { serverInfo 9 }

	netInterfaceEntry   OBJECT-TYPE
		SYNTAX  NetInterface
		ACCESS	not-accessible
		STATUS  mandatory
		DESCRIPTION
			"Information the specification of network interface."
		INDEX { netInterfaceNo }
	::= { netInterfaceTable 1 }

	NetInterface ::= SEQUENCE {
		netInterfaceNo		INTEGER,
		netInterfaceInfo	DisplayString
	}

	netInterfaceNo  OBJECT-TYPE
		SYNTAX  INTEGER
		ACCESS  read-only
		STATUS  mandatory
		DESCRIPTION
			"The sequential digit number as a index key of network interface table."
	::= { netInterfaceEntry 1 }	

	netInterfaceInfo    OBJECT-TYPE
		SYNTAX  DisplayString
		ACCESS  read-only
		STATUS  mandatory
		DESCRIPTION
			"The specification containing MAC, IP address and MTU of a network interface."
	::= { netInterfaceEntry 2 }	
	
	failoverInformationTable    OBJECT-TYPE
		SYNTAX  SEQUENCE OF FailoverInformation
		ACCESS	not-accessible
		STATUS  mandatory
		DESCRIPTION
			"A table containing the failover information which is currently configured of the IPStor server."
	::= { serverInfo 10 }

	failoverInformationEntry    OBJECT-TYPE
		SYNTAX  FailoverInformation
		ACCESS	not-accessible
		STATUS  mandatory
		DESCRIPTION
			"Information for the configured failover mode and state."
		INDEX { foIndex }
	::= { failoverInformationTable 1 }

	FailoverInformation ::= SEQUENCE {
		foIndex				INTEGER,
		foName				DisplayString,
		foValue				DisplayString,
		foConfType			DisplayString,
		foPartner			DisplayString,
		foPrimaryIPResource		DisplayString,
		foSecondaryIPResource		DisplayString,
		foCheckInterval			DisplayString,
--		foMemDumpMonitorIP		DisplayString,
		foHeartbeatInterval		DisplayString,
		foRecoverySetting		DisplayString,
		foState				DisplayString,
		foPrimaryStorageClusterInterlinkIP		DisplayString,
		foSecondaryStorageClusterInterlinkIP		DisplayString,
		foSuspended			DisplayString,
		foPowerControl			DisplayString,
		fofcWWPN			DisplayString
	}

	foIndex OBJECT-TYPE
		SYNTAX  INTEGER
		ACCESS  read-only
		STATUS  mandatory
		DESCRIPTION
			"The sequential digit number as a index key of failover table."
	::= { failoverInformationEntry 1 }	

	foName  OBJECT-TYPE
		SYNTAX  DisplayString
		ACCESS  read-only
		STATUS  mandatory
		DESCRIPTION
			"The property of a failover configuration."
	::= { failoverInformationEntry 2 }	

	foValue OBJECT-TYPE
		SYNTAX  DisplayString
		ACCESS  read-only
		STATUS  mandatory
		DESCRIPTION
			"The setting value of a failover configuration."
	::= { failoverInformationEntry 3 }

	foConfType OBJECT-TYPE
		SYNTAX  DisplayString
		ACCESS  read-only
		STATUS  mandatory
		DESCRIPTION
			"The Configuration Type of a failover configuration."
	::= { failoverInformationEntry 4 }

	foPartner OBJECT-TYPE
		SYNTAX  DisplayString
		ACCESS  read-only
		STATUS  mandatory
		DESCRIPTION
			"The Failover Partner of a failover configuration."
	::= { failoverInformationEntry 5 }

	foPrimaryIPResource OBJECT-TYPE
		SYNTAX  DisplayString
		ACCESS  read-only
		STATUS  mandatory
		DESCRIPTION
			"The IPStor Primary Server IP Resource of a failover configuration."
	::= { failoverInformationEntry 6 }

	foSecondaryIPResource OBJECT-TYPE
		SYNTAX  DisplayString
		ACCESS  read-only
		STATUS  mandatory
		DESCRIPTION
			"The IPStor Secondary Server IP Resource of a failover configuration."
	::= { failoverInformationEntry 7 }

	foCheckInterval OBJECT-TYPE
		SYNTAX  DisplayString
		ACCESS  read-only
		STATUS  mandatory
		DESCRIPTION
			"The Self Check Interval of a failover configuration."
	::= { failoverInformationEntry 8 }

--	foMemDumpMonitorIP OBJECT-TYPE
--		SYNTAX  DisplayString
--		ACCESS  read-only
--		STATUS  mandatory
--		DESCRIPTION
--			"The Memory Dump Monitoring IP Address of a failover configuration."
--	::= { failoverInformationEntry 9 }

	foHeartbeatInterval OBJECT-TYPE
		SYNTAX  DisplayString
		ACCESS  read-only
		STATUS  mandatory
		DESCRIPTION
			"The Heartbeat Interval of a failover configuration."
	::= { failoverInformationEntry 9 }

	foRecoverySetting OBJECT-TYPE
		SYNTAX  DisplayString
		ACCESS  read-only
		STATUS  mandatory
		DESCRIPTION
			"The Recovery Setting of a failover configuration."
	::= { failoverInformationEntry 10 }

	foState OBJECT-TYPE
		SYNTAX  DisplayString
		ACCESS  read-only
		STATUS  mandatory
		DESCRIPTION
			"The Failover State of a failover configuration."
	::= { failoverInformationEntry 11 }

	foPrimaryStorageClusterInterlinkIP OBJECT-TYPE
		SYNTAX  DisplayString
		ACCESS  read-only
		STATUS  mandatory
		DESCRIPTION
			"The primary internal link between two servers to mirror snapshot and SafeCache metadata between high-availability(HA) pairs."
	::= { failoverInformationEntry 12 }

	foSecondaryStorageClusterInterlinkIP OBJECT-TYPE
		SYNTAX  DisplayString
		ACCESS  read-only
		STATUS  mandatory
		DESCRIPTION
			"The secondary internal link between two servers to mirror snapshot and SafeCache metadata between high-availability(HA) pairs."
	::= { failoverInformationEntry 13 }

	foSuspended OBJECT-TYPE
		SYNTAX  DisplayString
		ACCESS  read-only
		STATUS  mandatory
		DESCRIPTION
			"The Suspended status of a failover configuration."
	::= { failoverInformationEntry 14 }

	foPowerControl OBJECT-TYPE
		SYNTAX  DisplayString
		ACCESS  read-only
		STATUS  mandatory
		DESCRIPTION
			"The Power Control of a failover configuration."
	::= { failoverInformationEntry 15 }

	fofcWWPN OBJECT-TYPE
		SYNTAX  DisplayString
		ACCESS  read-only
		STATUS  mandatory
		DESCRIPTION
			"The Fibre Channel  WWPN of a failover configuration."
	::= { failoverInformationEntry 16 }
	
	fcInfoTable OBJECT-TYPE
		SYNTAX  SEQUENCE OF FcInfoList
		ACCESS	not-accessible
		STATUS  mandatory
		DESCRIPTION
			"A table containing the information of all Fibre Channel HBAs of the IPStor server."
	::= { serverInfo 11 }

	fcInfoEntry OBJECT-TYPE
		SYNTAX  FcInfoList
		ACCESS	not-accessible
		STATUS  mandatory
		DESCRIPTION
			"Information the hardware specification and configured access mode."
		INDEX { fcIndex }
	::= { fcInfoTable 1 }

	FcInfoList ::= SEQUENCE {
		fcIndex	INTEGER,
		fcWWPN	DisplayString,
		fcMode	DisplayString,
		fcTargetWWPN	DisplayString
	}

	fcIndex OBJECT-TYPE
		SYNTAX  INTEGER
		ACCESS  read-only
		STATUS  mandatory
		DESCRIPTION
			"The sequential digit number as a index key of the fibre channel table."
	::= { fcInfoEntry 1 }

	fcWWPN  OBJECT-TYPE
		SYNTAX  DisplayString
		ACCESS  read-only
		STATUS  mandatory
		DESCRIPTION
			"This will display the WWPN (World Wide Port Name) information of a Fibre Channel HBA. 
			 This WWPN is a unique vendor assigned 64bit identifier which is assigned to each port within a FC HBA."
	::= { fcInfoEntry 2 }

	fcMode  OBJECT-TYPE
		SYNTAX  DisplayString
		ACCESS  read-only
		STATUS  mandatory
		DESCRIPTION
			"It indicates if the HBA is configured to an Initiator or Target mode of the IPStor server."
	::= { fcInfoEntry 3 }

	fcTargetWWPN  OBJECT-TYPE
		SYNTAX  DisplayString
		ACCESS  read-only
		STATUS  mandatory
		DESCRIPTION
			"This will display the Taget WWPN (World Wide Port Name) information of a Fibre Channel HBA when enables the HBA runs with dual mode.
			 This WWPN is a unique vendor assigned 64bit identifier which is assigned to each port within a FC HBA."
	::= { fcInfoEntry 4 }

	serverOption OBJECT IDENTIFIER ::= { serverInfo 12 }

	nasOption   OBJECT-TYPE
		SYNTAX  DisplayString
		ACCESS  read-only
		STATUS  mandatory
		DESCRIPTION
			"It indicates the status of NAS option is enable or disable of the IPStor server."
	::= { serverOption 1 }
	
	fibreChannelOption  OBJECT-TYPE
		SYNTAX  DisplayString
		ACCESS  read-only
		STATUS  mandatory
		DESCRIPTION
			"It indicates the status of Fibre Channel option is enable or disable of the IPStor server."
	::= { serverOption 2 }
	
	replicationOption  OBJECT-TYPE
		SYNTAX  DisplayString
		ACCESS  read-only
		STATUS  mandatory
		DESCRIPTION
			"It indicates the status of Replication option is enable or disable of the IPStor server."
	::= { serverOption 3 }

	syncMirroringOption   OBJECT-TYPE
		SYNTAX  DisplayString
		ACCESS  read-only
		STATUS  mandatory
		DESCRIPTION
			"It indicates the status of synchronized Mirroring option is enable or disable of the IPStor server."
	::= { serverOption 4 }
	
    timemarkOption  OBJECT-TYPE
        SYNTAX  DisplayString
        ACCESS  read-only
        STATUS  mandatory
        DESCRIPTION
            "It indicates the status of Timemark option is enable or disable of the IPStor server."
    ::= { serverOption 6 }
    
    zeroimpactOption    OBJECT-TYPE
        SYNTAX  DisplayString
        ACCESS  read-only
        STATUS  mandatory
        DESCRIPTION
            "It indicates the status of Zero Impact Backup option is enable or disable of the IPStor server."
    ::= { serverOption 7 }
	
	MTCPVersion  OBJECT-TYPE
		SYNTAX  INTEGER
		ACCESS  read-only
		STATUS  mandatory
		DESCRIPTION
			"The MTCP Version which the IPStor server uses."
	::= { serverInfo 13 }

	performanceTable  OBJECT-TYPE
		SYNTAX  SEQUENCE OF PerformanceEntry
		ACCESS	not-accessible
		STATUS  mandatory
		DESCRIPTION
			"A table containing the information of the performance in the host which the IPStor server is running."
	::= { serverInfo 14 }

	performanceEntry  OBJECT-TYPE
		SYNTAX  PerformanceEntry
		ACCESS	not-accessible
		STATUS  mandatory
		DESCRIPTION
			"Information the specification of performance."
		INDEX { performanceMirrorSyncTH }
	::= { performanceTable 1 }

	PerformanceEntry ::= SEQUENCE {
		performanceMirrorSyncTH		INTEGER,
		performanceSyncMirrorInterval	DisplayString,
		performanceSyncMirrorRetry	INTEGER,
		performanceSyncMirrorUpnum	Counter32,
		performanceInitialMirrorSync	DisplayString,
		performanceIncludeReplicaMirror DisplayString,
		performanceReplicationMicroscan	DisplayString
	}

	performanceMirrorSyncTH OBJECT-TYPE
		SYNTAX  INTEGER
		ACCESS  read-only
		STATUS	mandatory
		DESCRIPTION
			"The Mirror Synchronization Throttle of the performance table."
	::= { performanceEntry 1 }


	performanceSyncMirrorInterval OBJECT-TYPE
		SYNTAX  DisplayString
		ACCESS  read-only
		STATUS	mandatory
		DESCRIPTION
			"The Synchronize out-of-sync mirrors Interval of the performance table."
	::= { performanceEntry 2 }

	performanceSyncMirrorRetry OBJECT-TYPE
		SYNTAX  INTEGER
		ACCESS  read-only
		STATUS	mandatory
		DESCRIPTION
			"The Synchronize out-of-sync mirrors retry times of the performance table."
	::= { performanceEntry 3 }

	performanceSyncMirrorUpnum OBJECT-TYPE
		SYNTAX  Counter32
		ACCESS  read-only
		STATUS	mandatory
		DESCRIPTION
			"The Synchronize out-of-sync mirrors up numbers at each interval of the performance table."
	::= { performanceEntry 4 }

	performanceInitialMirrorSync OBJECT-TYPE
		SYNTAX  DisplayString
		ACCESS  read-only
		STATUS	mandatory
		DESCRIPTION
			"The option of starting initial synchronize when mirror is added of the performance table."
	::= { performanceEntry 5 }

	performanceIncludeReplicaMirror OBJECT-TYPE
		SYNTAX  DisplayString
		ACCESS  read-only
		STATUS	mandatory
		DESCRIPTION
			"The option of including replica mirror in the automatic synchronize process of the performance table."
	::= { performanceEntry 6 }

	performanceReplicationMicroscan   OBJECT-TYPE
		SYNTAX  DisplayString
		ACCESS  read-only
		STATUS  mandatory
		DESCRIPTION
			"It indicates the Microscan option of Replication is enable or disable of the IPStor server."
	::= { performanceEntry 7 }

	serverRole   OBJECT-TYPE
		SYNTAX  DisplayString
		ACCESS  read-only
		STATUS  mandatory
		DESCRIPTION
			"The IPStor server Role."
	::= { serverInfo 15 }

	smisoption   OBJECT-TYPE
		SYNTAX  DisplayString
		ACCESS  read-only
		STATUS  mandatory
		DESCRIPTION
			"The IPStor server SMI-S option."
	::= { serverInfo 16 }

	ServerIPaliasTable  OBJECT-TYPE
		SYNTAX  SEQUENCE OF ServerIPaliasEntry
		ACCESS	not-accessible
		STATUS  mandatory
		DESCRIPTION
			"A table containing the information of the IP alias in the host which the IPStor server is running."
	::= { serverInfo 17 }

	ServerIPaliasEntry  OBJECT-TYPE
		SYNTAX  ServerIPAliasEntry
		ACCESS	not-accessible
		STATUS  mandatory
		DESCRIPTION
			"Information the specification of server IP alias."
		INDEX { ServerIPaliasIP }
	::= { ServerIPaliasTable 1 }

	ServerIPAliasEntry ::= SEQUENCE {
		ServerIPaliasIP		DisplayString
	}

	ServerIPaliasIP   OBJECT-TYPE
		SYNTAX  DisplayString
		ACCESS  read-only
		STATUS  mandatory
		DESCRIPTION
			"The IPStor server IP Alias."
	::= { ServerIPaliasEntry 1 }

	iSCSIportal   OBJECT-TYPE
		SYNTAX  DisplayString
		ACCESS  read-only
		STATUS  mandatory
		DESCRIPTION
			"The IPStor server iSCSI default portal."
	::= { serverInfo 18 }

	DHCPTable  OBJECT-TYPE
		SYNTAX  SEQUENCE OF DHCPEntry
		ACCESS	not-accessible
		STATUS  mandatory
		DESCRIPTION
			"A table containing the information of the DHCP setting in the host which the IPStor server is running."
	::= { serverInfo 19 }

	DHCPEntry  OBJECT-TYPE
		SYNTAX  DHCPInfoEntry
		ACCESS	not-accessible
		STATUS  mandatory
		DESCRIPTION
			"Information the specification of DHCP."
		INDEX { DHCPOption }
	::= { DHCPTable 1 }

	DHCPInfoEntry ::= SEQUENCE {
		DHCPOption		DisplayString,
		DHCPNameServer		DisplayString,
		DHCPNetmask		DisplayString,
		DHCPGateway		DisplayString,
		DHCPIPrangeBegin	DisplayString,
		DHCPIPrangeEnd		DisplayString
	}

	DHCPOption OBJECT-TYPE
		SYNTAX  DisplayString
		ACCESS  read-only
		STATUS	mandatory
		DESCRIPTION
			"The option of the DHCP table."
	::= { DHCPEntry 1 }

	DHCPNameServer OBJECT-TYPE
		SYNTAX  DisplayString
		ACCESS  read-only
		STATUS	mandatory
		DESCRIPTION
			"The name server of the DHCP table."
	::= { DHCPEntry 2 }

	DHCPNetmask OBJECT-TYPE
		SYNTAX  DisplayString
		ACCESS  read-only
		STATUS	mandatory
		DESCRIPTION
			"The netmask of the DHCP table."
	::= { DHCPEntry 3 }

	DHCPGateway OBJECT-TYPE
		SYNTAX  DisplayString
		ACCESS  read-only
		STATUS	mandatory
		DESCRIPTION
			"The gateway of the DHCP table."
	::= { DHCPEntry 4 }

	DHCPIPrangeBegin OBJECT-TYPE
		SYNTAX  DisplayString
		ACCESS  read-only
		STATUS	mandatory
		DESCRIPTION
			"The begin IP range of the DHCP table."
	::= { DHCPEntry 5 }

	DHCPIPrangeEnd OBJECT-TYPE
		SYNTAX  DisplayString
		ACCESS  read-only
		STATUS	mandatory
		DESCRIPTION
			"The end IP range of the DHCP table."
	::= { DHCPEntry 6 }

	ActivityDBMaintenanceTable  OBJECT-TYPE
		SYNTAX  SEQUENCE OF ActivityDBMaintenanceEntry
		ACCESS	not-accessible
		STATUS  mandatory
		DESCRIPTION
			"A table containing the information of the Activity Database maintenanace of the IPStor server."
	::= { serverInfo 20 }

	ActivityDBMaintenanceEntry  OBJECT-TYPE
		SYNTAX  ActivityDBMaintenanceInfoEntry
		ACCESS	not-accessible
		STATUS  mandatory
		DESCRIPTION
			"Information the specification of activity database maintenance."
		INDEX { MAXActDBSize }
	::= { ActivityDBMaintenanceTable 1 }

	ActivityDBMaintenanceInfoEntry ::= SEQUENCE {
		MAXActDBSize		Counter32,
		NumofDaystoKeep		Counter32
	}

	MAXActDBSize OBJECT-TYPE
		SYNTAX  Counter32
		ACCESS  read-only
		STATUS	mandatory
		DESCRIPTION
			"The Maximum activity data file size(MB) of the Activity Database Maintenance table."
	::= { ActivityDBMaintenanceEntry 1 }

	NumofDaystoKeep OBJECT-TYPE
		SYNTAX  Counter32
		ACCESS  read-only
		STATUS	mandatory
		DESCRIPTION
			"The Number of days of activities to keep of the Activity Database Maintenance table."
	::= { ActivityDBMaintenanceEntry 2 }

	StatisticsLogsTable  OBJECT-TYPE
		SYNTAX  SEQUENCE OF StatisticsLogsEntry
		ACCESS	not-accessible
		STATUS  mandatory
		DESCRIPTION
			"A table containing the information of the Statistics Logs Option in the host which the IPStor server is running."
	::= { serverInfo 21 }

	StatisticsLogsEntry  OBJECT-TYPE
		SYNTAX  StatisticsLogsInfoEntry
		ACCESS	not-accessible
		STATUS  mandatory
		DESCRIPTION
			"Information the specification of Statistics Log option."
		INDEX { StatisticsLogsOption }
	::= { StatisticsLogsTable 1 }

	StatisticsLogsInfoEntry ::= SEQUENCE {
		StatisticsLogsOption		DisplayString,
		StatisticsLogsLogOption		DisplayString,
		StatisticsLogsStartTime		DisplayString,
		StatisticsLogsInterval		DisplayString,
		StatisticsLogsPurgeTime		DisplayString
	}

	StatisticsLogsOption OBJECT-TYPE
		SYNTAX  DisplayString
		ACCESS  read-only
		STATUS	mandatory
		DESCRIPTION
			"The option of the statistics logs table."
	::= { StatisticsLogsEntry 1 }

	StatisticsLogsLogOption OBJECT-TYPE
		SYNTAX  DisplayString
		ACCESS  read-only
		STATUS	mandatory
		DESCRIPTION
			"The log option of the statistics logs table."
	::= { StatisticsLogsEntry 2 }

	StatisticsLogsStartTime OBJECT-TYPE
		SYNTAX  DisplayString
		ACCESS  read-only
		STATUS	mandatory
		DESCRIPTION
			"The start time of the statistics logs table."
	::= { StatisticsLogsEntry 3 }

	StatisticsLogsInterval OBJECT-TYPE
		SYNTAX  DisplayString
		ACCESS  read-only
		STATUS	mandatory
		DESCRIPTION
			"The interval of the statistics logs table."
	::= { StatisticsLogsEntry 4 }

	StatisticsLogsPurgeTime OBJECT-TYPE
		SYNTAX  DisplayString
		ACCESS  read-only
		STATUS	mandatory
		DESCRIPTION
			"The purge time of the statistics logs table."
	::= { StatisticsLogsEntry 5 }

	AutoSaveConfigTable  OBJECT-TYPE
		SYNTAX  SEQUENCE OF AutoSaveConfigEntry
		ACCESS	not-accessible
		STATUS  mandatory
		DESCRIPTION
			"A table containing the information of the auto save configuration in the host which the IPStor server is running."
	::= { serverInfo 22 }

	AutoSaveConfigEntry  OBJECT-TYPE
		SYNTAX  AutoSaveConfigInfoEntry
		ACCESS	not-accessible
		STATUS  mandatory
		DESCRIPTION
			"Information the specification of auto save configuration."
		INDEX { AutoSaveConfigOption }
	::= { AutoSaveConfigTable 1 }

	AutoSaveConfigInfoEntry ::= SEQUENCE {
		AutoSaveConfigOption		DisplayString,
		AutoSaveConfigFtpServerName	DisplayString,
		AutoSaveConfigFtpPort		Counter32,
		AutoSaveConfigTargetDirectory	DisplayString,
		AutoSaveConfigInterval		DisplayString,
		AutoSaveConfigCopiesNumber	Counter32
	}

	AutoSaveConfigOption OBJECT-TYPE
		SYNTAX  DisplayString
		ACCESS  read-only
		STATUS	mandatory
		DESCRIPTION
			"The option of the auto save configuration table."
	::= { AutoSaveConfigEntry 1 }

	AutoSaveConfigFtpServerName OBJECT-TYPE
		SYNTAX  DisplayString
		ACCESS  read-only
		STATUS	mandatory
		DESCRIPTION
			"The ftp server name of the auto save configuration table."
	::= { AutoSaveConfigEntry 2 }

	AutoSaveConfigFtpPort OBJECT-TYPE
		SYNTAX  Counter32
		ACCESS  read-only
		STATUS	mandatory
		DESCRIPTION
			"The ftp port of the auto save configuration table."
	::= { AutoSaveConfigEntry 3 }

	AutoSaveConfigTargetDirectory OBJECT-TYPE
		SYNTAX  DisplayString
		ACCESS  read-only
		STATUS	mandatory
		DESCRIPTION
			"The target directory of the auto save configuration table."
	::= { AutoSaveConfigEntry 4 }

	AutoSaveConfigInterval OBJECT-TYPE
		SYNTAX  DisplayString
		ACCESS  read-only
		STATUS	mandatory
		DESCRIPTION
			"The interval of the auto save configuration table."
	::= { AutoSaveConfigEntry 5 }

	AutoSaveConfigCopiesNumber OBJECT-TYPE
		SYNTAX  Counter32
		ACCESS  read-only
		STATUS	mandatory
		DESCRIPTION
			"The number of copies of the auto save configuration table."
	::= { AutoSaveConfigEntry 6 }

	CDPPerformanceTable  OBJECT-TYPE
		SYNTAX  SEQUENCE OF CDPPerformanceEntry
		ACCESS	not-accessible
		STATUS  mandatory
		DESCRIPTION
			"A table containing the information of the auto save configuration in the host which the IPStor server is running."
	::= { serverInfo 23 }

	CDPPerformanceEntry  OBJECT-TYPE
		SYNTAX  CDPPerformanceInfoEntry
		ACCESS	not-accessible
		STATUS  mandatory
		DESCRIPTION
			"Information the specification of auto save configuration."
		INDEX { CDPPerformanceAggressiveThreshold }
	::= { CDPPerformanceTable 1 }

	CDPPerformanceInfoEntry ::= SEQUENCE {
		CDPPerformanceAggressiveThreshold		Counter32,
		CDPPerformanceAggressiveDataFlushSpeed		Counter32,
		CDPPerformanceAggressiveInactDataFlsuhSpeed	Counter32,
		CDPPerformanceModerateThreshold			Counter32,
		CDPPerformanceModerateDataFlushSpeed		Counter32,
		CDPPerformanceModerateInactDataFlsuhSpeed	Counter32
	}

	CDPPerformanceAggressiveThreshold OBJECT-TYPE
		SYNTAX  Counter32
		ACCESS  read-only
		STATUS	mandatory
		DESCRIPTION
			"The aggressive threshold of the CDP performance table."
	::= { CDPPerformanceEntry 1 }

	CDPPerformanceAggressiveDataFlushSpeed OBJECT-TYPE
		SYNTAX  Counter32
		ACCESS  read-only
		STATUS	mandatory
		DESCRIPTION
			"The aggressive data flush speed of the CDP performance table."
	::= { CDPPerformanceEntry 2 }

	CDPPerformanceAggressiveInactDataFlsuhSpeed OBJECT-TYPE
		SYNTAX  Counter32
		ACCESS  read-only
		STATUS	mandatory
		DESCRIPTION
			"The aggressive data flush speed during inactivity of the CDP performance table."
	::= { CDPPerformanceEntry 3 }

	CDPPerformanceModerateThreshold OBJECT-TYPE
		SYNTAX  Counter32
		ACCESS  read-only
		STATUS	mandatory
		DESCRIPTION
			"The moderate threshold of the CDP performance table."
	::= { CDPPerformanceEntry 4 }

	CDPPerformanceModerateDataFlushSpeed OBJECT-TYPE
		SYNTAX  Counter32
		ACCESS  read-only
		STATUS	mandatory
		DESCRIPTION
			"The moderate data flush speed of the CDP performance table."
	::= { CDPPerformanceEntry 5 }

	CDPPerformanceModerateInactDataFlsuhSpeed OBJECT-TYPE
		SYNTAX  Counter32
		ACCESS  read-only
		STATUS	mandatory
		DESCRIPTION
			"The moderate data flush speed during inactivity of the CDP performance table."
	::= { CDPPerformanceEntry 6 }

	StatisticsNASTable  OBJECT-TYPE
		SYNTAX  SEQUENCE OF StatisticsNASEntry
		ACCESS	not-accessible
		STATUS  mandatory
		DESCRIPTION
			"A table containing the information of the Statistics gathering for NAS of the IPStor server."
	::= { serverInfo 24 }

	StatisticsNASEntry  OBJECT-TYPE
		SYNTAX  StatisticsNASInfoEntry
		ACCESS	not-accessible
		STATUS  mandatory
		DESCRIPTION
			"Information the specification of statistics gathering for NAS."
		INDEX { StatisticsNASOption }
	::= { StatisticsNASTable 1 }

	StatisticsNASInfoEntry ::= SEQUENCE {
		StatisticsNASOption		DisplayString,
		StatisticsNASInterval		Counter32
	}

	StatisticsNASOption OBJECT-TYPE
		SYNTAX  DisplayString
		ACCESS  read-only
		STATUS	mandatory
		DESCRIPTION
			"The option of the statistics gathering for NAS table."
	::= { StatisticsNASEntry 1 }

	StatisticsNASInterval OBJECT-TYPE
		SYNTAX  Counter32
		ACCESS  read-only
		STATUS	mandatory
		DESCRIPTION
			"The interval of the statistics gathering for NAS table."
	::= { StatisticsNASEntry 2 }

	SNMPMaintenanceTable  OBJECT-TYPE
		SYNTAX  SEQUENCE OF SNMPMaintenanceEntry
		ACCESS	not-accessible
		STATUS  mandatory
		DESCRIPTION
			"A table containing the information of the SNMP maintenance in the host which the IPStor server is running."
	::= { serverInfo 25 }

	SNMPMaintenanceEntry  OBJECT-TYPE
		SYNTAX  SNMPMaintenanceInfoEntry
		ACCESS	not-accessible
		STATUS  mandatory
		DESCRIPTION
			"Information the specification of SNMP maintenance."
		INDEX { SNMPMaintenanceTrapLevel }
	::= { SNMPMaintenanceTable 1 }

	SNMPMaintenanceInfoEntry ::= SEQUENCE {
		SNMPMaintenanceTrapLevel		DisplayString,
		SNMPMaintenanceServer			DisplayString,
		SNMPMaintenanceCommunity		DisplayString
	}

	SNMPMaintenanceTrapLevel OBJECT-TYPE
		SYNTAX  DisplayString
		ACCESS  read-only
		STATUS	mandatory
		DESCRIPTION
			"The trap level of the SNMP maintenance table."
	::= { SNMPMaintenanceEntry 1 }

	SNMPMaintenanceServer OBJECT-TYPE
		SYNTAX  DisplayString
		ACCESS  read-only
		STATUS	mandatory
		DESCRIPTION
			"The trap receive server of the SNMP maintenance table."
	::= { SNMPMaintenanceEntry 2 }

	SNMPMaintenanceCommunity OBJECT-TYPE
		SYNTAX  DisplayString
		ACCESS  read-only
		STATUS	mandatory
		DESCRIPTION
			"The trap send community of the SNMP maintenance table."
	::= { SNMPMaintenanceEntry 3 }

	TimeMarkMaintenanceTable  OBJECT-TYPE
		SYNTAX  SEQUENCE OF TimeMarkMaintenanceEntry
		ACCESS	not-accessible
		STATUS  mandatory
		DESCRIPTION
			"A table containing the information of the TimeMark maintenance in the host which the IPStor server is running."
	::= { serverInfo 26 }

	TimeMarkMaintenanceEntry  OBJECT-TYPE
		SYNTAX  TimeMarkMaintenanceInfoEntry
		ACCESS	not-accessible
		STATUS  mandatory
		DESCRIPTION
			"Information the specification of TimeMark maintenance."
		INDEX { TimeMarkMaintenanceSchedule }
	::= { TimeMarkMaintenanceTable 1 }

	TimeMarkMaintenanceInfoEntry ::= SEQUENCE {
		TimeMarkMaintenanceSchedule			DisplayString,
		TimeMarkMaintenanceReclamOption			DisplayString,
		TimeMarkMaintenanceReclamThreshold		DisplayString,
		TimeMarkMaintenanceReclamStartTime		DisplayString,
		TimeMarkMaintenanceReclamRepeatTime		DisplayString,
		TimeMarkMaintenanceReclamMaxProcessingTime	DisplayString
	}

	TimeMarkMaintenanceSchedule OBJECT-TYPE
		SYNTAX  DisplayString
		ACCESS  read-only
		STATUS	mandatory
		DESCRIPTION
			"The schedule to start timemark maintenance."
	::= { TimeMarkMaintenanceEntry 1 }

	TimeMarkMaintenanceReclamOption OBJECT-TYPE
		SYNTAX  DisplayString
		ACCESS  read-only
		STATUS	mandatory
		DESCRIPTION
			"The option of reclamation in TimeMark maintenance."
	::= { TimeMarkMaintenanceEntry 2 }

	TimeMarkMaintenanceReclamThreshold OBJECT-TYPE
		SYNTAX  DisplayString
		ACCESS  read-only
		STATUS	mandatory
		DESCRIPTION
			"The threshold for minimum amount of space that can be reclamed per TimeMark."
	::= { TimeMarkMaintenanceEntry 3 }

	TimeMarkMaintenanceReclamStartTime OBJECT-TYPE
		SYNTAX  DisplayString
		ACCESS  read-only
		STATUS	mandatory
		DESCRIPTION
			"The start schedule time of reclamation in TimeMark maintenance."
	::= { TimeMarkMaintenanceEntry 4 }

	TimeMarkMaintenanceReclamRepeatTime OBJECT-TYPE
		SYNTAX  DisplayString
		ACCESS  read-only
		STATUS	mandatory
		DESCRIPTION
			"The repeat schedule interval of reclamation in TimeMark maintenance."
	::= { TimeMarkMaintenanceEntry 5 }

	TimeMarkMaintenanceReclamMaxProcessingTime OBJECT-TYPE
		SYNTAX  DisplayString
		ACCESS  read-only
		STATUS	mandatory
		DESCRIPTION
			"The maximum time for the reclamation process in TimeMark maintenance."
	::= { TimeMarkMaintenanceEntry 6 }

	LocationTable  OBJECT-TYPE
		SYNTAX  SEQUENCE OF LocationEntry
		ACCESS	not-accessible
		STATUS  mandatory
		DESCRIPTION
			"A table containing the information of the location setting in the host which the IPStor server is running."
	::= { serverInfo 27 }

	LocationEntry  OBJECT-TYPE
		SYNTAX  LocationInfoEntry
		ACCESS	not-accessible
		STATUS  mandatory
		DESCRIPTION
			"Information the specification of Location."
		INDEX { LCLocation }
	::= { LocationTable 1 }

	LocationInfoEntry ::= SEQUENCE {
		LCLocation	DisplayString,
		LCRoom		DisplayString,
		LCFloor		DisplayString,
		LCBuilding	DisplayString,
		LCAddress	DisplayString,
		LCCity		DisplayString,
		LCState		DisplayString,
		LCZipCode	DisplayString,
		LCCountry	DisplayString,
		LCOwner		DisplayString,
		LCOwnersPhone	DisplayString,
		LCOwnersEmail	DisplayString,
		LCOwnersIM	DisplayString,
		LCDescription	DisplayString,
		LCImagepath	DisplayString
	}

	LCLocation OBJECT-TYPE
		SYNTAX  DisplayString
		ACCESS  read-only
		STATUS	mandatory
		DESCRIPTION
			"The location field of location setting table."
	::= { LocationEntry 1 }

	LCRoom OBJECT-TYPE
		SYNTAX  DisplayString
		ACCESS  read-only
		STATUS	mandatory
		DESCRIPTION
			"The room field of location setting table."
	::= { LocationEntry 2 }

	LCFloor OBJECT-TYPE
		SYNTAX  DisplayString
		ACCESS  read-only
		STATUS	mandatory
		DESCRIPTION
			"The floor field of location setting table."
	::= { LocationEntry 3 }

	LCBuilding OBJECT-TYPE
		SYNTAX  DisplayString
		ACCESS  read-only
		STATUS	mandatory
		DESCRIPTION
			"The building field of location setting table."
	::= { LocationEntry 4 }

	LCAddress OBJECT-TYPE
		SYNTAX  DisplayString
		ACCESS  read-only
		STATUS	mandatory
		DESCRIPTION
			"The address field of location setting table."
	::= { LocationEntry 5 }

	LCCity OBJECT-TYPE
		SYNTAX  DisplayString
		ACCESS  read-only
		STATUS	mandatory
		DESCRIPTION
			"The city field of location setting table."
	::= { LocationEntry 6 }

	LCState OBJECT-TYPE
		SYNTAX  DisplayString
		ACCESS  read-only
		STATUS	mandatory
		DESCRIPTION
			"The state field of location setting table."
	::= { LocationEntry 7 }

	LCZipCode OBJECT-TYPE
		SYNTAX  DisplayString
		ACCESS  read-only
		STATUS	mandatory
		DESCRIPTION
			"The zip code field of location setting table."
	::= { LocationEntry 8 }

	LCCountry OBJECT-TYPE
		SYNTAX  DisplayString
		ACCESS  read-only
		STATUS	mandatory
		DESCRIPTION
			"The country field of location setting table."
	::= { LocationEntry 9 }

	LCOwner OBJECT-TYPE
		SYNTAX  DisplayString
		ACCESS  read-only
		STATUS	mandatory
		DESCRIPTION
			"The owner field of location setting table."
	::= { LocationEntry 10 }

	LCOwnersPhone OBJECT-TYPE
		SYNTAX  DisplayString
		ACCESS  read-only
		STATUS	mandatory
		DESCRIPTION
			"The owner's phone field of location setting table."
	::= { LocationEntry 11 }

	LCOwnersEmail OBJECT-TYPE
		SYNTAX  DisplayString
		ACCESS  read-only
		STATUS	mandatory
		DESCRIPTION
			"The owner's e-mail field of location setting table."
	::= { LocationEntry 12 }

	LCOwnersIM OBJECT-TYPE
		SYNTAX  DisplayString
		ACCESS  read-only
		STATUS	mandatory
		DESCRIPTION
			"The owner's IM field of location setting table."
	::= { LocationEntry 13 }

	LCDescription OBJECT-TYPE
		SYNTAX  DisplayString
		ACCESS  read-only
		STATUS	mandatory
		DESCRIPTION
			"The description field of location setting table."
	::= { LocationEntry 14 }

	LCImagepath OBJECT-TYPE
		SYNTAX  DisplayString
		ACCESS  read-only
		STATUS	mandatory
		DESCRIPTION
			"The image path field of location setting table."
	::= { LocationEntry 15 }


--
-- Physical Resources
--
	physicalResources OBJECT IDENTIFIER ::= { ipstorserver 2 }

	numOfAdapters   OBJECT-TYPE
		SYNTAX  INTEGER
		ACCESS  read-only
		STATUS  mandatory
		DESCRIPTION
			"The amount of physical adapters configured by the IPStor server."
	::= { physicalResources 1 }

	numOfDevices    OBJECT-TYPE
		SYNTAX  INTEGER
		ACCESS  read-only
		STATUS  mandatory
		DESCRIPTION
			"The amount of physical devices configured by the IPStor server."
	::= { physicalResources 2 }

	scsiAdapterTable    OBJECT-TYPE
		SYNTAX  SEQUENCE OF ScsiAdapter
		ACCESS	not-accessible
		STATUS  mandatory
		DESCRIPTION
			"A table containing the information of all the installed SCSI adapters of the IPStor server."
	::= { physicalResources 3 }

	scsiAdapterEntry    OBJECT-TYPE
		SYNTAX ScsiAdapter
		ACCESS	not-accessible
		STATUS  mandatory
		DESCRIPTION
			"Information about the hardware and vendor specification."
		INDEX { adapterIndex }
	::= { scsiAdapterTable 1 }
	
	ScsiAdapter ::= SEQUENCE {
	    adapterIndex	INTEGER,
	    adapterNumber	INTEGER,
	    adapterInfo		DisplayString
	}

	adapterIndex    OBJECT-TYPE
		SYNTAX  INTEGER
		ACCESS	read-only
		STATUS	mandatory
		DESCRIPTION
			"The sequential digit number as a index key of adapter table."
	::= { scsiAdapterEntry 1 }

	adapterNumber   OBJECT-TYPE
		SYNTAX  INTEGER
		ACCESS	read-only
		STATUS	mandatory
		DESCRIPTION
			"The SCSI adapter number."
	::= { scsiAdapterEntry 2 }

	adapterInfo OBJECT-TYPE
		SYNTAX  DisplayString
		ACCESS	read-only
		STATUS	mandatory
		DESCRIPTION
			"The model name of the SCSI adapter."
	::= { scsiAdapterEntry 3 }

	scsiDeviceTable OBJECT-TYPE
		SYNTAX  SEQUENCE OF ScsiDevice
		ACCESS	not-accessible
		STATUS	mandatory
		DESCRIPTION
			"A table containing all the SCSI devices of the IPStor server."
	::= { physicalResources 4 }

	scsiDeviceEntry OBJECT-TYPE
		SYNTAX	ScsiDevice
		ACCESS	not-accessible
		STATUS	mandatory
		DESCRIPTION
			"Information about the hardware specification and characteristic of the device."
		INDEX { deviceNo }
	::= { scsiDeviceTable 1 }
	
	ScsiDevice ::= SEQUENCE {
		deviceNo	    INTEGER,
		deviceType	    DisplayString,
		vendorID	    DisplayString,
		productID	    DisplayString,
		firmwareRev	    DisplayString,
		adapterNo	    INTEGER,
		channelNo	    INTEGER,
		scsiID		    INTEGER,
		lun		    INTEGER,
		totalSectors        Counter32,
		sectorSize          INTEGER,
		totalSize           Counter32,
		configStatus        DisplayString,
		totalSizeQuantity   Counter32,
		totalSizeUnit       INTEGER,
		totalSectors64	    Counter64,
		totalSize64	    Counter64
	}

	deviceNo    OBJECT-TYPE
		SYNTAX  INTEGER
		ACCESS	read-only
		STATUS	mandatory
		DESCRIPTION
			"The sequential digit number as a index key of the device table."
	::= { scsiDeviceEntry 1 }

	deviceType  OBJECT-TYPE
		SYNTAX  DisplayString
		ACCESS	read-only
		STATUS	mandatory
		DESCRIPTION
			"It represents the access type that the device attached to the IPStor server."
	::= { scsiDeviceEntry 2 }

	vendorID    OBJECT-TYPE
		SYNTAX  DisplayString
		ACCESS	read-only
		STATUS	mandatory
		DESCRIPTION
			"The product vendor ID."
	::= { scsiDeviceEntry 3 }

	productID   OBJECT-TYPE
		SYNTAX  DisplayString
		ACCESS	read-only
		STATUS	mandatory
		DESCRIPTION
			"The product model name."
	::= { scsiDeviceEntry 4 }

	firmwareRev OBJECT-TYPE
		SYNTAX  DisplayString
		ACCESS	read-only
		STATUS	mandatory
		DESCRIPTION
			"The firmware version of the device."
	::= { scsiDeviceEntry 5 }

	adapterNo   OBJECT-TYPE
		SYNTAX  INTEGER
		ACCESS	read-only
		STATUS	mandatory
		DESCRIPTION
			"The configured SCSI adapter number."
	::= { scsiDeviceEntry 6 }

	channelNo   OBJECT-TYPE
		SYNTAX  INTEGER
		ACCESS	read-only
		STATUS	mandatory
		DESCRIPTION
			"The configured SCSI channel number."
	::= { scsiDeviceEntry 7 }

	scsiID  OBJECT-TYPE
		SYNTAX  INTEGER
		ACCESS	read-only
		STATUS	mandatory
		DESCRIPTION
			"The configured SCSI ID."
	::= { scsiDeviceEntry 8 }

	lun OBJECT-TYPE
		SYNTAX  INTEGER
		ACCESS	read-only
		STATUS	mandatory
		DESCRIPTION
			"The configured SCSI LUN number."
	::= { scsiDeviceEntry 9 }

	totalSectors    OBJECT-TYPE
		SYNTAX  Counter32
		ACCESS	read-only
		STATUS	mandatory
		DESCRIPTION
			"The amount of sectors or blocks of the device."
	::= { scsiDeviceEntry 10 }

	sectorSize  OBJECT-TYPE
		SYNTAX  INTEGER
		ACCESS	read-only
		STATUS	mandatory
		DESCRIPTION
			"The size of bytes for each sector or block."
	::= { scsiDeviceEntry 11 }

	totalSize   OBJECT-TYPE
		SYNTAX  Counter32
		ACCESS	read-only
		STATUS	mandatory
		DESCRIPTION
			"The amount size of the device which represents with megabyte unit."
	::= { scsiDeviceEntry 12 }

	configStatus    OBJECT-TYPE
		SYNTAX  DisplayString
		ACCESS	read-only
		STATUS	mandatory
		DESCRIPTION
			"It represents the attaching status of the device."
	::= { scsiDeviceEntry 13 }

	totalSizeQuantity   OBJECT-TYPE
		SYNTAX  Counter32
		ACCESS	read-only
		STATUS	mandatory
		DESCRIPTION
			"The quantity size of the device."
	::= { scsiDeviceEntry 14 }

	totalSizeUnit   OBJECT-TYPE
		SYNTAX  INTEGER
		ACCESS	read-only
		STATUS	mandatory
		DESCRIPTION
			"The size unit of the device. 0 presents KB. 1 presents MB. 2 presents GB. 3 presents TB."
	::= { scsiDeviceEntry 15 }

	totalSectors64  OBJECT-TYPE
		SYNTAX  Counter64
		ACCESS	read-only
		STATUS	mandatory
		DESCRIPTION
			"The amount of sectors or blocks of the device."
	::= { scsiDeviceEntry 16 }

	totalSize64     OBJECT-TYPE
		SYNTAX  Counter64
		ACCESS	read-only
		STATUS	mandatory
		DESCRIPTION
			"The amount size of the device which represents with megabyte unit."
	::= { scsiDeviceEntry 17 }

	StoragePoolTable    OBJECT-TYPE
		SYNTAX  SEQUENCE OF StoragePool
		ACCESS	not-accessible
		STATUS  mandatory
		DESCRIPTION
			"A table containing the information of Storage Pool of the IPStor server."
	::= { physicalResources 5 }

	StoragePoolEntry    OBJECT-TYPE
		SYNTAX	StoragePool
		ACCESS	not-accessible
		STATUS  mandatory
		DESCRIPTION
			"Information about Storage Pool settings."
		INDEX { PoolName }
	::= { StoragePoolTable 1 }
	
	StoragePool ::= SEQUENCE {
	    PoolName			DisplayString,
	    PoolID			INTEGER,
	    PoolType			DisplayString,
	    DeviceCount			INTEGER,
	    PoolCount			INTEGER,
	    PoolTotalSize		Counter32,
	    PoolUsedSize		Counter32,
	    PoolAvailableSize		Counter32,
	    PoolTotalSizeQuantity	Counter32,
	    PoolTotalSizeUnit		INTEGER,
	    PoolUsedSizeQuantity	Counter32,
	    PoolUsedSizeUnit		INTEGER,
	    PoolAvailableSizeQuantity	Counter32,
	    PoolAvailableSizeUnit	INTEGER,
	    PoolTotalSize64		Counter64,
	    PoolUsedSize64		Counter64,
	    PoolAvailableSize64		Counter64
	}

	PoolName    OBJECT-TYPE
		SYNTAX  DisplayString
		ACCESS	read-only
		STATUS	mandatory
		DESCRIPTION
			"The Pool Name of the Storage Pool."
	::= { StoragePoolEntry 1 }

	PoolID    OBJECT-TYPE
		SYNTAX  INTEGER
		ACCESS	read-only
		STATUS	mandatory
		DESCRIPTION
			"The Pool ID of the Storage Pool."
	::= { StoragePoolEntry 2 }

	PoolType    OBJECT-TYPE
		SYNTAX  DisplayString
		ACCESS	read-only
		STATUS	mandatory
		DESCRIPTION
			"The Pool Type of the Storage Pool."
	::= { StoragePoolEntry 3 }

	DeviceCount    OBJECT-TYPE
		SYNTAX  INTEGER
		ACCESS	read-only
		STATUS	mandatory
		DESCRIPTION
			"The device Count in the Storage Pool."
	::= { StoragePoolEntry 4 }

	PoolCount    OBJECT-TYPE
		SYNTAX  INTEGER
		ACCESS	read-only
		STATUS	mandatory
		DESCRIPTION
			"The Storage Pool counts."
	::= { StoragePoolEntry 5 }

	PoolTotalSize    OBJECT-TYPE
		SYNTAX  Counter32
		ACCESS	read-only
		STATUS	mandatory
		DESCRIPTION
			"The total Size of the Storage Pool."
	::= { StoragePoolEntry 6 }

	PoolUsedSize    OBJECT-TYPE
		SYNTAX  Counter32
		ACCESS	read-only
		STATUS	mandatory
		DESCRIPTION
			"The used Size of the Storage Pool."
	::= { StoragePoolEntry 7 }

	PoolAvailableSize    OBJECT-TYPE
		SYNTAX  Counter32
		ACCESS	read-only
		STATUS	mandatory
		DESCRIPTION
			"The available Size of the Storage Pool."
	::= { StoragePoolEntry 8 }

	PoolTotalSizeQuantity    OBJECT-TYPE
		SYNTAX  Counter32
		ACCESS	read-only
		STATUS	mandatory
		DESCRIPTION
			"The total Size quantity of the Storage Pool."
	::= { StoragePoolEntry 9 }

	PoolTotalSizeUnit    OBJECT-TYPE
		SYNTAX  INTEGER
		ACCESS	read-only
		STATUS	mandatory
		DESCRIPTION
			"The total Size unit of the Storage Pool. 0 presents KB. 1 presents MB. 2 presents GB. 3 presents TB."
	::= { StoragePoolEntry 10 }

	PoolUsedSizeQuantity    OBJECT-TYPE
		SYNTAX  Counter32
		ACCESS	read-only
		STATUS	mandatory
		DESCRIPTION
			"The used Size quantity of the Storage Pool."
	::= { StoragePoolEntry 11 }

	PoolUsedSizeUnit    OBJECT-TYPE
		SYNTAX  INTEGER
		ACCESS	read-only
		STATUS	mandatory
		DESCRIPTION
			"The used Size unit of the Storage Pool. 0 presents KB. 1 presents MB. 2 presents GB. 3 presents TB."
	::= { StoragePoolEntry 12 }

	PoolAvailableSizeQuantity    OBJECT-TYPE
		SYNTAX  Counter32
		ACCESS	read-only
		STATUS	mandatory
		DESCRIPTION
			"The available Size quantity of the Storage Pool."
	::= { StoragePoolEntry 13 }

	PoolAvailableSizeUnit    OBJECT-TYPE
		SYNTAX  INTEGER
		ACCESS	read-only
		STATUS	mandatory
		DESCRIPTION
			"The available Size unit of the Storage Pool. 0 presents KB. 1 presents MB. 2 presents GB. 3 presents TB."
	::= { StoragePoolEntry 14 }

	PoolTotalSize64 OBJECT-TYPE
		SYNTAX  Counter64
		ACCESS	read-only
		STATUS	mandatory
		DESCRIPTION
			"The total Size of the Storage Pool."
	::= { StoragePoolEntry 15 }

	PoolUsedSize64  OBJECT-TYPE
		SYNTAX  Counter64
		ACCESS	read-only
		STATUS	mandatory
		DESCRIPTION
			"The used Size of the Storage Pool."
	::= { StoragePoolEntry 16 }

	PoolAvailableSize64    OBJECT-TYPE
		SYNTAX  Counter64
		ACCESS	read-only
		STATUS	mandatory
		DESCRIPTION
			"The available Size of the Storage Pool."
	::= { StoragePoolEntry 17 }
--
-- Logical Resources
--

	logicalResources OBJECT IDENTIFIER ::= { ipstorserver 3 }
	
	numOfLogicalResources   OBJECT-TYPE
		SYNTAX	INTEGER
		ACCESS	read-only
		STATUS	mandatory
		DESCRIPTION
			"The amount of logical resources which including the SAN, NAS, and Replica devices are available in the IPStor server."
	::= { logicalResources 1}

	snapshotReservedArea OBJECT IDENTIFIER ::= { logicalResources 2 }

	numOfSnapshotReserved   OBJECT-TYPE
		SYNTAX  INTEGER
		ACCESS  read-only
		STATUS  obsolete
		DESCRIPTION
			"The amount of the shareable snapshot reserved areas."
	::= { snapshotReservedArea 1 }

	snapshotReservedTable OBJECT-TYPE
		SYNTAX  SEQUENCE OF SnapShotReserved
		ACCESS	not-accessible
		STATUS	obsolete
		DESCRIPTION
			"A table containing the snapshot reserved areas information."
	::= { snapshotReservedArea 2 }

	snapShotReservedEntry OBJECT-TYPE
		SYNTAX	SnapShotReserved
		ACCESS	not-accessible
		STATUS	obsolete
		DESCRIPTION
			"Information about the allocated resource."
		INDEX { ssrIndex }
	::= { snapshotReservedTable 1 }
	
	SnapShotReserved ::= SEQUENCE {
	ssrIndex	    INTEGER,
        ssrName 	    DisplayString,
        ssrDeviceName	DisplayString,
        ssrSCSIAddress	DisplayString,
        ssrFirstSector	Counter32,
        ssrLastSector	Counter32,
	ssrTotalSectors Counter32,
	ssrSize		Counter32,
	ssrSizeQuantity Counter32,
	ssrSizeUnit	INTEGER,
        ssrFirstSector64	Counter64,
        ssrLastSector64		Counter64,
	ssrTotalSectors64	Counter64,
	ssrSize64		Counter64
	}

	ssrIndex    OBJECT-TYPE
		SYNTAX	INTEGER
		ACCESS	read-only
		STATUS	obsolete
		DESCRIPTION
			"The sequential digit number as a index key of the snapshot reserved table."
	::= { snapShotReservedEntry 1 }

	ssrName OBJECT-TYPE
		SYNTAX	DisplayString
		ACCESS	read-only
		STATUS	obsolete
		DESCRIPTION
			"The name of the snapshot reserved area."
	::= { snapShotReservedEntry 2 }

	ssrDeviceName   OBJECT-TYPE
		SYNTAX	DisplayString
		ACCESS	read-only
		STATUS	obsolete
		DESCRIPTION
			"The physical device name of the snapshot reserved area."
	::= { snapShotReservedEntry 3 }

	ssrSCSIAddress  OBJECT-TYPE
		SYNTAX	DisplayString
		ACCESS	read-only
		STATUS	obsolete
		DESCRIPTION
			"The SCSI address of the physical device which the snapshot reserved area created."
	::= { snapShotReservedEntry 4 }

	ssrFirstSector  OBJECT-TYPE
		SYNTAX	Counter32
		ACCESS	read-only
		STATUS	obsolete
		DESCRIPTION
			"The first sector of the snapshot reserved area."
	::= { snapShotReservedEntry 5 }
	
	ssrLastSector   OBJECT-TYPE
		SYNTAX	Counter32
		ACCESS	read-only
		STATUS	obsolete
		DESCRIPTION
			"The last sector of the snapshot reserved area."
	::= { snapShotReservedEntry 6 }

	ssrTotalSectors OBJECT-TYPE
		SYNTAX	Counter32
		ACCESS	read-only
		STATUS	obsolete
		DESCRIPTION
			"The amount of sectors that the snapshot reserved area created."
	::= { snapShotReservedEntry 7 }

	ssrSize OBJECT-TYPE
		SYNTAX  Counter32
		ACCESS	read-only
		STATUS	obsolete
		DESCRIPTION
			"The amount of resource size which is representing with megabyte unit of the snapshot reserved area."
	::= { snapShotReservedEntry 8 }

	ssrSizeQuantity OBJECT-TYPE
		SYNTAX  Counter32
		ACCESS	read-only
		STATUS	obsolete
		DESCRIPTION
			"The amount quantity of resource size of the snapshot reserved area."
	::= { snapShotReservedEntry 9 }

	ssrSizeUnit OBJECT-TYPE
		SYNTAX  INTEGER
		ACCESS	read-only
		STATUS	obsolete
		DESCRIPTION
			"The resource size unit of the snapshot reserved area. The size unit of the device. 0 presents KB. 1 presents MB. 2 presents GB. 3 presents TB."
	::= { snapShotReservedEntry 10 }

	ssrFirstSector64  OBJECT-TYPE
		SYNTAX	Counter64
		ACCESS	read-only
		STATUS	obsolete
		DESCRIPTION
			"The first sector of the snapshot reserved area."
	::= { snapShotReservedEntry 11 }
	
	ssrLastSector64   OBJECT-TYPE
		SYNTAX	Counter64
		ACCESS	read-only
		STATUS	obsolete
		DESCRIPTION
			"The last sector of the snapshot reserved area."
	::= { snapShotReservedEntry 12 }

	ssrTotalSectors64 OBJECT-TYPE
		SYNTAX	Counter64
		ACCESS	read-only
		STATUS	obsolete
		DESCRIPTION
			"The amount of sectors that the snapshot reserved area created."
	::= { snapShotReservedEntry 13 }

	ssrSize64 OBJECT-TYPE
		SYNTAX  Counter64
		ACCESS	read-only
		STATUS	obsolete
		DESCRIPTION
			"The amount of resource size which is representing with megabyte unit of the snapshot reserved area."
	::= { snapShotReservedEntry 14 }

	sanResources OBJECT IDENTIFIER ::= { logicalResources 3 }

	numOfSANResources   OBJECT-TYPE
		SYNTAX  INTEGER
		ACCESS  read-only
		STATUS  mandatory
		DESCRIPTION
			"The amount of SAN resources are available by the IPStor server."
	::= { sanResources 1 }

	sanResourceTable OBJECT-TYPE
		SYNTAX  SEQUENCE OF SANResource
		ACCESS	not-accessible
		STATUS	mandatory
		DESCRIPTION
			"A table containing the SAN resources information."
	::= { sanResources 2 }

	sanResourceEntry OBJECT-TYPE
		SYNTAX	SANResource
		ACCESS	not-accessible
		STATUS	mandatory
		DESCRIPTION
			"Information about the configurations and properties of the logical SAN resources."
		INDEX { sanResourceID }
	::= { sanResourceTable 1 }

	SANResource ::= SEQUENCE {
		sanResourceID			    INTEGER,
		sanResourceName 		DisplayString,
		srAllocationType		DisplayString,
		srTotalSectors			Counter32,
		srTotalSize			Counter32,
		srConfigStatus			DisplayString,
		srMirrorSyncStatus		DisplayString,
		srReplicaDevice		        DisplayString,
		srReplicatingSchedule		DisplayString,
		srSnapshotCopyStatus		DisplayString,
--		srClientInfoTable          	OBJECT IDENTIFIER,
--		srTimeMarkTable			OBJECT IDENTIFIER,
	        srWriteCacheProperty		DisplayString,
		srTotalSizeQuantity		Counter32,
		srTotalSizeUnit			INTEGER,
		srTotalSectors64		Counter64,
		srTotalSize64			Counter64
	}

	sanResourceID   OBJECT-TYPE
		SYNTAX	INTEGER
		ACCESS	read-only
		STATUS	mandatory
		DESCRIPTION
			"The SAN resource ID assigned by the IPStor server."
	::= { sanResourceEntry 1 }
	
	sanResourceName OBJECT-TYPE
		SYNTAX	DisplayString
		ACCESS	read-only
		STATUS	mandatory
		DESCRIPTION
			"The SAN resource name created by the user."
	::= { sanResourceEntry 2 }    

	srAllocationType    OBJECT-TYPE
		SYNTAX	DisplayString
		ACCESS	read-only
		STATUS	mandatory
		DESCRIPTION
			"It represents the resource type when user allocating the SAN device."
	::= { sanResourceEntry 3 }

	srTotalSectors  OBJECT-TYPE
		SYNTAX	Counter32
		ACCESS	read-only
		STATUS	mandatory
		DESCRIPTION
			"The amount of sectors allocated by the SAN resource."
	::= { sanResourceEntry 4 }
	
	srTotalSize OBJECT-TYPE
		SYNTAX	Counter32
		ACCESS	read-only
		STATUS	mandatory
		DESCRIPTION
			"The amount of device size which is representing with megabyte unit of the SAN resource."
	::= { sanResourceEntry 5 }

	srConfigStatus  OBJECT-TYPE
		SYNTAX	DisplayString
		ACCESS	read-only
		STATUS	mandatory
		DESCRIPTION
			"It represents the attaching status of the SAN resource."
	::= { sanResourceEntry 6 }
	
	srMirrorSyncStatus  OBJECT-TYPE
		SYNTAX	DisplayString
		ACCESS	read-only
		STATUS	mandatory
		DESCRIPTION
			"It represents the mirror synchronization status of the SAN resource."
	::= { sanResourceEntry 7 }

	srReplicaDevice OBJECT-TYPE
		SYNTAX	DisplayString
		ACCESS	read-only
		STATUS	mandatory
		DESCRIPTION
			"It represents the target replica server and device as the format <hostname of target>:<virtual device id>,
			 if the replication option is enabled of the SAN resource."
	::= { sanResourceEntry 8 }
	
	srReplicatingSchedule   OBJECT-TYPE
		SYNTAX	DisplayString
		ACCESS	read-only
		STATUS	mandatory
		DESCRIPTION
			"It represents the current status of the replicating schedule(On-schedule, Suspended, or N/A) set for the SAN resource."
	::= { sanResourceEntry 9 }
	
	srSnapshotCopyStatus    OBJECT-TYPE
		SYNTAX	DisplayString
		ACCESS	read-only
		STATUS	mandatory
		DESCRIPTION
			"The snapshot copy status of the SAN resource."
	::= { sanResourceEntry 10 }

	srPhysicalAllocLayoutTable OBJECT IDENTIFIER ::= { sanResourceEntry 11 }

	physicalAllocLayoutEntry    OBJECT-TYPE
		SYNTAX PhysicalAllocLayout
		ACCESS	not-accessible
		STATUS	mandatory
		DESCRIPTION
			"Information about the physical devices which are reserved and created by logical SAN resource."
		INDEX { physicalAllocLayoutIndex }
	::= { srPhysicalAllocLayoutTable 1 }

	PhysicalAllocLayout ::= SEQUENCE {
		physicalAllocLayoutIndex    		INTEGER,
		srpaSANResourceName 			DisplayString,
		srpaSANResourceID   			INTEGER,
		srpaName			        DisplayString,
		srpaType  			        DisplayString,
		srpaAdapterNo			    	INTEGER,
		srpaChannelNo			    	INTEGER,
		srpaScsiID			        INTEGER,
		srpaLun				        INTEGER,
		srpaFirstSector			    	Counter32,
		srpaLastSector			    	Counter32,
		srpaSize			        Counter32,
		srpaSizeQuantity		        Counter32,
		srpaSizeUnit			        INTEGER,
		srpaFirstSector64			Counter64,
		srpaLastSector64			Counter64,
		srpaSize64				Counter64
	}

	physicalAllocLayoutIndex    OBJECT-TYPE
		SYNTAX	INTEGER
		ACCESS	read-only
		STATUS	mandatory
		DESCRIPTION
			"The sequential digit number as a index key of the physical allocation layout table."
	::= { physicalAllocLayoutEntry 1 }

	srpaSANResourceName OBJECT-TYPE
		SYNTAX	DisplayString
		ACCESS	read-only
		STATUS	mandatory
		DESCRIPTION
			"The SAN resource name created by the user."
	::= { physicalAllocLayoutEntry 2 }

	srpaSANResourceID   OBJECT-TYPE
		SYNTAX  INTEGER
		ACCESS	read-only
		STATUS	mandatory
		DESCRIPTION
			"The SAN resource ID assigned by the IPStor server."
	::= { physicalAllocLayoutEntry 3 }

	srpaName    OBJECT-TYPE
		SYNTAX	DisplayString
		ACCESS	read-only
		STATUS	mandatory
		DESCRIPTION
			"The physical device name."
	::= { physicalAllocLayoutEntry 4 }
	
	srpaType OBJECT-TYPE
		SYNTAX	DisplayString
		ACCESS	read-only
		STATUS	mandatory
		DESCRIPTION
			"It represents the type(Primary, or Mirror) of the physical layout."
	::= { physicalAllocLayoutEntry 5 }

	srpaAdapterNo OBJECT-TYPE
		SYNTAX  INTEGER
		ACCESS	read-only
		STATUS	mandatory
		DESCRIPTION
			"The SCSI adapter number of the physical device."
	::= { physicalAllocLayoutEntry 6 }

	srpaChannelNo OBJECT-TYPE
		SYNTAX  INTEGER
		ACCESS	read-only
		STATUS	mandatory
		DESCRIPTION
			"The SCSI channel number of the physical device."
	::= { physicalAllocLayoutEntry 7 }

	srpaScsiID OBJECT-TYPE
		SYNTAX  INTEGER
		ACCESS	read-only
		STATUS	mandatory
		DESCRIPTION
			"The SCSI ID of the physical device."
	::= { physicalAllocLayoutEntry 8 }

	srpaLun OBJECT-TYPE
		SYNTAX  INTEGER
		ACCESS	read-only
		STATUS	mandatory
		DESCRIPTION
			"The SCSI LUN number of the physical device."
	::= { physicalAllocLayoutEntry 9 }

	srpaFirstSector OBJECT-TYPE
		SYNTAX  Counter32
		ACCESS	read-only
		STATUS	mandatory
		DESCRIPTION
			"The first sector of the physical device which is allocated by the SAN resource."
	::= { physicalAllocLayoutEntry 10 }

	srpaLastSector  OBJECT-TYPE
		SYNTAX  Counter32
		ACCESS	read-only
		STATUS	mandatory
		DESCRIPTION
			"The last sector of the physical device which is allocated by the SAN resource."
	::= { physicalAllocLayoutEntry 11 }
		
	srpaSize    OBJECT-TYPE
		SYNTAX  Counter32
		ACCESS	read-only
		STATUS	mandatory
		DESCRIPTION
			"The amount of the allocated size which is representing with megabyte unit within a physical device."
	::= { physicalAllocLayoutEntry 12 }
		
	srpaSizeQuantity    OBJECT-TYPE
		SYNTAX  Counter32
		ACCESS	read-only
		STATUS	mandatory
		DESCRIPTION
			"The amount of the allocated size quantity within a physical device."
	::= { physicalAllocLayoutEntry 13 }
		
	srpaSizeUnit    OBJECT-TYPE
		SYNTAX  INTEGER
		ACCESS	read-only
		STATUS	mandatory
		DESCRIPTION
			"The amount of the allocated size unit within a physical device. The size unit of the device. 0 presents KB. 1 presents MB. 2 presents GB. 3 presents TB."
	::= { physicalAllocLayoutEntry 14 }

	srpaFirstSector64 OBJECT-TYPE
		SYNTAX  Counter64
		ACCESS	read-only
		STATUS	mandatory
		DESCRIPTION
			"The first sector of the physical device which is allocated by the SAN resource."
	::= { physicalAllocLayoutEntry 15 }

	srpaLastSector64  OBJECT-TYPE
		SYNTAX  Counter64
		ACCESS	read-only
		STATUS	mandatory
		DESCRIPTION
			"The last sector of the physical device which is allocated by the SAN resource."
	::= { physicalAllocLayoutEntry 16 }
		
	srpaSize64    OBJECT-TYPE
		SYNTAX  Counter64
		ACCESS	read-only
		STATUS	mandatory
		DESCRIPTION
			"The amount of the allocated size which is representing with megabyte unit within a physical device."
	::= { physicalAllocLayoutEntry 17 }

	srClientInfoTable   OBJECT-TYPE
		SYNTAX SEQUENCE OF SRClientInfo
		ACCESS	not-accessible
		STATUS	mandatory
		DESCRIPTION
			"A table containing the SAN clients information."
	::= { sanResourceEntry 12 }

	srClientInfoEntry   OBJECT-TYPE
		SYNTAX  SRClientInfo
		ACCESS	not-accessible
		STATUS	mandatory
		DESCRIPTION
			"Information about the SAN clients if the SAN resources have been assigned."
		INDEX { srClientNo }
	::= { srClientInfoTable 1 }

	SRClientInfo ::= SEQUENCE {
		srClientNo          INTEGER,
		srcName			    DisplayString,
		srcSANResourceID	INTEGER,
		srcSANResourceName	DisplayString,
		srcAdapterNo		INTEGER,
		srcChannelNo		INTEGER,
		srcScsiID		    INTEGER,
		srcLun			    INTEGER,
		srcAccess		    DisplayString,
		srcConnAccess		DisplayString
	}

	srClientNo  OBJECT-TYPE
		SYNTAX	INTEGER
		ACCESS	read-only
		STATUS	mandatory
		DESCRIPTION
			"The SAN client ID assigned by the IPStor server."
	::= { srClientInfoEntry 1 }

	srcName OBJECT-TYPE
		SYNTAX	DisplayString
		ACCESS	read-only
		STATUS	mandatory
		DESCRIPTION
			"The SAN client name assigned by the IPStor server."
	::= { srClientInfoEntry 2 }

	srcSANResourceID    OBJECT-TYPE
		SYNTAX	INTEGER
		ACCESS	read-only
		STATUS	mandatory
		DESCRIPTION
			"The SAN resource ID assigned by the IPStor server."
	::= { srClientInfoEntry 3 }

	srcSANResourceName  OBJECT-TYPE
		SYNTAX	DisplayString
		ACCESS	read-only
		STATUS	mandatory
		DESCRIPTION
			"The SAN resource name created by the user."
	::= { srClientInfoEntry 4 }

	srcAdapterNo    OBJECT-TYPE
		SYNTAX  INTEGER
		ACCESS	read-only
		STATUS	mandatory
		DESCRIPTION
			"The adapter number of the SAN client."
	::= { srClientInfoEntry 5 }

	srcChannelNo    OBJECT-TYPE
		SYNTAX  INTEGER
		ACCESS	read-only
		STATUS	mandatory
		DESCRIPTION
			"The channel number of the SAN client."
	::= { srClientInfoEntry 6 }

	srcScsiID   OBJECT-TYPE
		SYNTAX  INTEGER
		ACCESS	read-only
		STATUS	mandatory
		DESCRIPTION
			"The SCSI ID of the SAN client."
	::= { srClientInfoEntry 7 }

	srcLun  OBJECT-TYPE
		SYNTAX  INTEGER
		ACCESS	read-only
		STATUS	mandatory
		DESCRIPTION
			"The SCSI LUN number of the SAN client."
	::= { srClientInfoEntry 8 }

	srcAccess   OBJECT-TYPE
		SYNTAX  DisplayString
		ACCESS	read-only
		STATUS	mandatory
		DESCRIPTION
			"The SAN resource accessing mode assigned to the SAN client."
	::= { srClientInfoEntry 9 }

	srcConnAccess   OBJECT-TYPE
		SYNTAX  DisplayString
		ACCESS	read-only
		STATUS	mandatory
		DESCRIPTION
			"Identify the connecting and accessing status with a resource of the SAN client."
	::= { srClientInfoEntry 10 }

    srFCClientInfoTable OBJECT IDENTIFIER ::= { sanResourceEntry 13 }

    srFCClientInfoEntry OBJECT-TYPE
        SYNTAX  SRFCClientInfo
        ACCESS  not-accessible
        STATUS  mandatory
        DESCRIPTION
            "Information about the Fibre Channel clients if the SAN resources have been assigned."
        INDEX { srFCClientNo }
    ::= { srFCClientInfoTable 1 }

    SRFCClientInfo ::= SEQUENCE {
        srFCClientNo        INTEGER,
        srFCName            DisplayString,
        srFCSANResourceID   INTEGER,
        srFCSANResourceName DisplayString,
        srFCInitatorWWPN    DisplayString,
        srFCTargetWWPN      DisplayString,
        srFCLun             INTEGER,
        srFCAccess          DisplayString,
        srFCConnAccess      DisplayString
    }

    srFCClientNo OBJECT-TYPE
        SYNTAX  INTEGER
        ACCESS  read-only
        STATUS  mandatory
        DESCRIPTION
            "The Fibre Channel client ID assigned by the IPStor server."
    ::= { srFCClientInfoEntry 1 }

    srFCName    OBJECT-TYPE
        SYNTAX  DisplayString
        ACCESS  read-only
        STATUS  mandatory
        DESCRIPTION
            "The Fibre Channel client name assigned by the IPStor server."
    ::= { srFCClientInfoEntry 2 }

    srFCSANResourceID   OBJECT-TYPE
        SYNTAX  INTEGER
        ACCESS  read-only
        STATUS  mandatory
        DESCRIPTION
            "The SAN resource ID assigned by the IPStor server."
    ::= { srFCClientInfoEntry 3 }

    srFCSANResourceName OBJECT-TYPE 
        SYNTAX  DisplayString
        ACCESS  read-only
        STATUS  mandatory
        DESCRIPTION
            "The SAN resource name created by the user."
    ::= { srFCClientInfoEntry 4 }

    srFCInitatorWWPN    OBJECT-TYPE
        SYNTAX  DisplayString
        ACCESS  read-only
        STATUS  mandatory
        DESCRIPTION
            "The world wide port name(WWPN) of the Fibre Channel client's initator HBA."
    ::= { srFCClientInfoEntry 5 }
    
    srFCTargetWWPN  OBJECT-TYPE
        SYNTAX  DisplayString
        ACCESS  read-only
        STATUS  mandatory
        DESCRIPTION
            "The world wide port name(WWPN) of the Fibre Channel client's target HBA."
    ::= { srFCClientInfoEntry 6 }
    
    srFCLun OBJECT-TYPE
        SYNTAX  INTEGER
        ACCESS  read-only
        STATUS  mandatory
        DESCRIPTION
            "The SCSI LUN number of the Fibre Channel client."
    ::= { srFCClientInfoEntry 7 }
    
    srFCAccess OBJECT-TYPE
        SYNTAX  DisplayString
        ACCESS  read-only
        STATUS  mandatory
        DESCRIPTION
            "The SAN resource accessing mode assigned to the Fibre Channel client."
    ::= { srFCClientInfoEntry 8 }
   
    srFCConnAccess OBJECT-TYPE
        SYNTAX  DisplayString
        ACCESS  read-only
        STATUS  mandatory
        DESCRIPTION
            "Identify the connecting and accessing status with a resource of the Fibre Channel client."
    ::= { srFCClientInfoEntry 9 } 

    srSnapShotTable OBJECT IDENTIFIER ::= { sanResourceEntry 14 }
    
    srSnapShotInfoEntry OBJECT-TYPE
        SYNTAX  SRSnapShotInfo
        ACCESS  not-accessible
        STATUS  mandatory
        DESCRIPTION
            "Information about the policy and configuration of the snapshot function."
        INDEX { srSnapShotResourceID }
    ::= { srSnapShotTable 1 }

    SRSnapShotInfo ::= SEQUENCE {
        srSnapShotResourceID		INTEGER,
        srSnapShotResourceName		DisplayString,
        srSnapShotOption		DisplayString,
        srSnapShotSize			Counter32,
        srSnapShotThreshold		INTEGER,
        srSnapShotReachTH		DisplayString,
        srSnapShotIncSize		DisplayString,
        srSnapShotMaxSize		DisplayString,
        srSnapShotResourceFull		DisplayString,
        srSnapShotUsedSize		Counter32,
        srSnapShotFreeSize		Counter32,
        srSnapShotUsedPercent		INTEGER,
        srSnapShotMicroscan		DisplayString,
        srSnapShotSizeQuantity		Counter32,
        srSnapShotSizeUnit		INTEGER,
        srSnapShotUsedSizeQuantity	Counter32,
        srSnapShotUsedSizeUnit		INTEGER,
        srSnapShotFreeSizeQuantity	Counter32,
        srSnapShotFreeSizeUnit		INTEGER,
        srSnapShotIncSizeQuantity	Counter32,
        srSnapShotIncSizeUnit		INTEGER,
        srSnapShotMaxSizeQuantity	Counter32,
        srSnapShotMaxSizeUnit		INTEGER,
        srSnapShotOwnResourceID		INTEGER,
        srSnapShotSize64		Counter64,
        srSnapShotIncSize64		Counter64,
        srSnapShotMaxSize64		Counter64,
        srSnapShotUsedSize64		Counter64,
        srSnapShotFreeSize64		Counter64,
        srSnapShotReclaimPolicy		DisplayString,
        srSnapShotReclaimTime		DisplayString,
        srSnapShotReclaimInterval	DisplayString,
        srSnapShotReclaimWaterMark	DisplayString,
        srSnapShotReclaimMaxTime	DisplayString,
        srSnapShotShrinkPolicy		DisplayString,
        srSnapShotShrinkThreshold	DisplayString,
        srSnapShotShrinkMinSize		DisplayString,
        srSnapShotShrinkMinSizeQuantity	Counter32,
        srSnapShotShrinkMinSizeUnit	INTEGER,
        srSnapShotShrinkMinSize64	Counter64,
        srSnapShotResourceStatus	DisplayString
    }

    srSnapShotResourceID    OBJECT-TYPE
        SYNTAX  INTEGER
        ACCESS  read-only
        STATUS  mandatory
        DESCRIPTION
            "The SAN resource ID assigned by the IPStor server."
    ::= { srSnapShotInfoEntry 1 }

    srSnapShotResourceName  OBJECT-TYPE
        SYNTAX  DisplayString
        ACCESS  read-only
        STATUS  mandatory
        DESCRIPTION
            "The SAN resource name created by the user."
    ::= { srSnapShotInfoEntry 2 }
    
    srSnapShotOption    OBJECT-TYPE
        SYNTAX  DisplayString
        ACCESS  read-only
        STATUS  mandatory
        DESCRIPTION
            "The status represents the snapshot option is enable or disable of the SAN resource."
    ::= { srSnapShotInfoEntry 3 }

    srSnapShotSize  OBJECT-TYPE
        SYNTAX  Counter32
        ACCESS  read-only
        STATUS  mandatory
        DESCRIPTION
            "The allocated size when creating the SAN resource at first time."
    ::= { srSnapShotInfoEntry 4 }
    
    srSnapShotThreshold OBJECT-TYPE
        SYNTAX  INTEGER
        ACCESS  read-only
        STATUS  mandatory
        DESCRIPTION
            "The value represents the threshold setting which is in percentage(%) format of the SAN resource."
    ::= { srSnapShotInfoEntry 5 }

    srSnapShotReachTH   OBJECT-TYPE
        SYNTAX  DisplayString
        ACCESS  read-only
        STATUS  mandatory
        DESCRIPTION
            "The policy is setting for expanding resource automatically or manually while reaching the threshold."
    ::= { srSnapShotInfoEntry 6 }

    srSnapShotIncSize   OBJECT-TYPE
        SYNTAX  DisplayString
        ACCESS  read-only
        STATUS  mandatory
        DESCRIPTION
            "The incremental size for each time when is running out the resource.  This is meaningful when expanding
             resource is automatically."
    ::= { srSnapShotInfoEntry 7 }

    srSnapShotMaxSize   OBJECT-TYPE
        SYNTAX  DisplayString
        ACCESS  read-only
        STATUS  mandatory
        DESCRIPTION
            "The maximum resource size which is represented in megabyte unit is allowed for allocating."
    ::= { srSnapShotInfoEntry 8 }
    
    srSnapShotResourceFull  OBJECT-TYPE
        SYNTAX  DisplayString
        ACCESS  read-only
        STATUS  mandatory
        DESCRIPTION
            "The policy sets to delete previous timemarks or stop to creating new timemarks when using the maximum resource size."
    ::= { srSnapShotInfoEntry 9 }

    srSnapShotUsedSize  OBJECT-TYPE
        SYNTAX  Counter32
        ACCESS  read-only
        STATUS  mandatory
        DESCRIPTION
            "The resource size which is representing in kilobyte unit have been used."
    ::= { srSnapShotInfoEntry 10 }
    
    srSnapShotFreeSize  OBJECT-TYPE
        SYNTAX  Counter32
        ACCESS  read-only
        STATUS  mandatory
        DESCRIPTION
            "The free resource size which is representing in megabyte unit before reaching the threshold."
    ::= { srSnapShotInfoEntry 11 }

    srSnapShotUsedPercent   OBJECT-TYPE
        SYNTAX  INTEGER
        ACCESS  read-only
        STATUS  mandatory
        DESCRIPTION
            "The percentage of the used resource size."
    ::= { srSnapShotInfoEntry 12 }
    
    srSnapShotMicroscan    OBJECT-TYPE
        SYNTAX  DisplayString
        ACCESS  read-only
        STATUS  mandatory
        DESCRIPTION
            "The status represents the snapshot Microscan option is enabled or disabled of the SAN resource."
    ::= { srSnapShotInfoEntry 13 }

    srSnapShotSizeQuantity  OBJECT-TYPE
        SYNTAX  Counter32
        ACCESS  read-only
        STATUS  mandatory
        DESCRIPTION
            "The allocated size quantity when creating the SAN resource at first time."
    ::= { srSnapShotInfoEntry 14 }

    srSnapShotSizeUnit  OBJECT-TYPE
        SYNTAX  INTEGER
        ACCESS  read-only
        STATUS  mandatory
        DESCRIPTION
            "The allocated size unit when creating the SAN resource at first time. 0 presents KB. 1 presents MB. 2 presents GB. 3 presents TB."
    ::= { srSnapShotInfoEntry 15 }

    srSnapShotUsedSizeQuantity  OBJECT-TYPE
        SYNTAX  Counter32
        ACCESS  read-only
        STATUS  mandatory
        DESCRIPTION
            "The resource size quantity which have been used."
    ::= { srSnapShotInfoEntry 16 }

    srSnapShotUsedSizeUnit  OBJECT-TYPE
        SYNTAX  INTEGER
        ACCESS  read-only
        STATUS  mandatory
        DESCRIPTION
            "The resource size unit which have been used. 0 presents KB. 1
presents MB. 2 presents GB. 3 presents TB."
    ::= { srSnapShotInfoEntry 17 }
    
    srSnapShotFreeSizeQuantity  OBJECT-TYPE
        SYNTAX  Counter32
        ACCESS  read-only
        STATUS  mandatory
        DESCRIPTION
            "The free resource size quantity before reaching the threshold."
    ::= { srSnapShotInfoEntry 18 }
    
    srSnapShotFreeSizeUnit  OBJECT-TYPE
        SYNTAX  INTEGER
        ACCESS  read-only
        STATUS  mandatory
        DESCRIPTION
            "The free resource size unit before reaching the threshold. 0 presents KB. 1 presents MB. 2 presents GB. 3 presents TB."
    ::= { srSnapShotInfoEntry 19 }

    srSnapShotIncSizeQuantity  OBJECT-TYPE
        SYNTAX  Counter32
        ACCESS  read-only
        STATUS  mandatory
        DESCRIPTION
            "The incremental size quantity which has been used for each time when is running out the resource"
    ::= { srSnapShotInfoEntry 20 }

    srSnapShotIncSizeUnit  OBJECT-TYPE
        SYNTAX  INTEGER
        ACCESS  read-only
        STATUS  mandatory
        DESCRIPTION
            "The incremental size unit which has been used for each time when is running out the resource. 0 presents KB. 1 presents MB. 2 presents GB. 3 presents TB."
    ::= { srSnapShotInfoEntry 21 }

    srSnapShotMaxSizeQuantity  OBJECT-TYPE
        SYNTAX  Counter32
        ACCESS  read-only
        STATUS  mandatory
        DESCRIPTION
            "The maximum resource size quantity which have been used."
    ::= { srSnapShotInfoEntry 22 }

    srSnapShotMaxSizeUnit  OBJECT-TYPE
        SYNTAX  INTEGER
        ACCESS  read-only
        STATUS  mandatory
        DESCRIPTION
            "The maximum resource size unit which have been used. 0 presents KB. 1 presents MB. 2 presents GB. 3 presents TB."
    ::= { srSnapShotInfoEntry 23 }

    srSnapShotOwnResourceID    OBJECT-TYPE
        SYNTAX  INTEGER
        ACCESS  read-only
        STATUS  mandatory
        DESCRIPTION
            "The SnapShot resource ID assigned by the IPStor server."
    ::= { srSnapShotInfoEntry 24 }

    srSnapShotSize64  OBJECT-TYPE
        SYNTAX  Counter64
        ACCESS  read-only
        STATUS  mandatory
        DESCRIPTION
            "The allocated size when creating the SAN resource at first time."
    ::= { srSnapShotInfoEntry 25 }

    srSnapShotIncSize64   OBJECT-TYPE
        SYNTAX  Counter64
        ACCESS  read-only
        STATUS  mandatory
        DESCRIPTION
            "The incremental size for each time when is running out the resource.  This is meaningful when expanding
             resource is automatically."
    ::= { srSnapShotInfoEntry 26 }

    srSnapShotMaxSize64   OBJECT-TYPE
        SYNTAX  Counter64
        ACCESS  read-only
        STATUS  mandatory
        DESCRIPTION
            "The maximum resource size which is represented in megabyte unit is allowed for allocating."
    ::= { srSnapShotInfoEntry 27 }

    srSnapShotUsedSize64  OBJECT-TYPE
        SYNTAX  Counter64
        ACCESS  read-only
        STATUS  mandatory
        DESCRIPTION
            "The resource size which is representing in kilobyte unit have been used."
    ::= { srSnapShotInfoEntry 28 }
    
    srSnapShotFreeSize64  OBJECT-TYPE
        SYNTAX  Counter64
        ACCESS  read-only
        STATUS  mandatory
        DESCRIPTION
            "The free resource size which is representing in megabyte unit before reaching the threshold."
    ::= { srSnapShotInfoEntry 29 }
    
    srSnapShotReclaimPolicy    OBJECT-TYPE
        SYNTAX  DisplayString
        ACCESS  read-only
        STATUS  mandatory
        DESCRIPTION
            "The status represents the snapshot Reclaim option is enabled or disabled of the SAN resource."
    ::= { srSnapShotInfoEntry 30 }
    
    srSnapShotReclaimTime    OBJECT-TYPE
        SYNTAX  DisplayString
        ACCESS  read-only
        STATUS  mandatory
        DESCRIPTION
            "The initial time when the snapshot Reclaim option is enabled of the SAN resource."
    ::= { srSnapShotInfoEntry 31 }
    
    srSnapShotReclaimInterval    OBJECT-TYPE
        SYNTAX  DisplayString
        ACCESS  read-only
        STATUS  mandatory
        DESCRIPTION
            "The schedule interval to start the snapshot Reclaim of the SAN resource."
    ::= { srSnapShotInfoEntry 32 }
    
    srSnapShotReclaimWaterMark    OBJECT-TYPE
        SYNTAX  DisplayString
        ACCESS  read-only
        STATUS  mandatory
        DESCRIPTION
            "The threshold for the minimum amount of space that can be reclaimed per TimeMark of the SAN resource."
    ::= { srSnapShotInfoEntry 33 }
    
    srSnapShotReclaimMaxTime    OBJECT-TYPE
        SYNTAX  DisplayString
        ACCESS  read-only
        STATUS  mandatory
        DESCRIPTION
            "The maximum time for the reclaim process of the SAN resource."
    ::= { srSnapShotInfoEntry 34 }
    
    srSnapShotShrinkPolicy    OBJECT-TYPE
        SYNTAX  DisplayString
        ACCESS  read-only
        STATUS  mandatory
        DESCRIPTION
            "The status represents the snapshot Shrink option is enabled or disabled of the SAN resource."
    ::= { srSnapShotInfoEntry 35 }
    
    srSnapShotShrinkThreshold    OBJECT-TYPE
        SYNTAX  DisplayString
        ACCESS  read-only
        STATUS  mandatory
        DESCRIPTION
            "The minimum disk space to shrink the snapshot resource of the SAN resource."
    ::= { srSnapShotInfoEntry 36 }
    
    srSnapShotShrinkMinSize    OBJECT-TYPE
        SYNTAX  DisplayString
        ACCESS  read-only
        STATUS  mandatory
        DESCRIPTION
            "The minimum size for the snapshot resource to shrink."
    ::= { srSnapShotInfoEntry 37 }

    srSnapShotShrinkMinSizeQuantity  OBJECT-TYPE
        SYNTAX  Counter32
        ACCESS  read-only
        STATUS  mandatory
        DESCRIPTION
            "The minimum size quantity for the snapshot resource to shrink."
    ::= { srSnapShotInfoEntry 38 }

    srSnapShotShrinkMinSizeUnit  OBJECT-TYPE
        SYNTAX  INTEGER
        ACCESS  read-only
        STATUS  mandatory
        DESCRIPTION
            "The minimum size unit for the snapshot resource to shrink. 0 presents KB. 1 presents MB. 2 presents GB. 3 presents TB."
    ::= { srSnapShotInfoEntry 39 }
    
    srSnapShotShrinkMinSize64    OBJECT-TYPE
        SYNTAX  Counter64
        ACCESS  read-only
        STATUS  mandatory
        DESCRIPTION
            "The minimum size for the snapshot resource to shrink."
    ::= { srSnapShotInfoEntry 40 }

    srSnapShotResourceStatus   OBJECT-TYPE
        SYNTAX  DisplayString
        ACCESS  read-only
        STATUS  mandatory
        DESCRIPTION
            "The snapshot resource status of the SAN resouce."
    ::= { srSnapShotInfoEntry 41 }

    srTimeMarkTable OBJECT IDENTIFIER ::= { sanResourceEntry 15 }
    
    srTimeMarkInfoEntry OBJECT-TYPE
        SYNTAX  SRTimeMarkInfo
        ACCESS  not-accessible
        STATUS  mandatory
        DESCRIPTION
            "Information about the policy and configuration of the timemark function."
        INDEX { srTimeMarkResourceID }
    ::= { srTimeMarkTable 1 }

    SRTimeMarkInfo ::= SEQUENCE {
        srTimeMarkResourceID    INTEGER,
        srTimeMarkResourceName  DisplayString,
        srTimeMarkOption        DisplayString,
        srTimeMarkCounts        INTEGER,
        srTimeMarkSchedule      DisplayString,
        srTimeMarkLastTimeStamp DisplayString,
        srTimeMarkSnapshotImage DisplayString,
	srTimeMarkSnapshotNotificationOption	DisplayString,
	srTimeMarkReplicationOption		DisplayString
    }

    srTimeMarkResourceID    OBJECT-TYPE
        SYNTAX  INTEGER
        ACCESS  read-only
        STATUS  mandatory
        DESCRIPTION
            "The SAN resource ID assigned by the IPStor server."
    ::= { srTimeMarkInfoEntry 1 }

    srTimeMarkResourceName  OBJECT-TYPE
        SYNTAX  DisplayString
        ACCESS  read-only
        STATUS  mandatory
        DESCRIPTION
            "The SAN resource name created by the user."
    ::= { srTimeMarkInfoEntry 2 }
    
    srTimeMarkOption    OBJECT-TYPE
        SYNTAX  DisplayString
        ACCESS  read-only
        STATUS  mandatory
        DESCRIPTION
            "The status represents the timemark option is enable or disable of the SAN resource."
    ::= { srTimeMarkInfoEntry 3 }

    srTimeMarkCounts    OBJECT-TYPE
        SYNTAX  INTEGER
        ACCESS  read-only
        STATUS  mandatory
        DESCRIPTION
            "The maximum timemarks that is allowed to create of the SAN resource."
    ::= { srTimeMarkInfoEntry 4 }
    
    srTimeMarkSchedule  OBJECT-TYPE
        SYNTAX  DisplayString
        ACCESS  read-only
        STATUS  mandatory
        DESCRIPTION
            "The time interval creates one new timemark."
    ::= { srTimeMarkInfoEntry 5 }

    srTimeMarkLastTimeStamp OBJECT-TYPE
        SYNTAX  DisplayString
        ACCESS  read-only
        STATUS  mandatory
        DESCRIPTION
            "The lately timestamp creates timemark."
    ::= { srTimeMarkInfoEntry 6 }

    srTimeMarkSnapshotImage OBJECT-TYPE
        SYNTAX  DisplayString
        ACCESS  read-only
        STATUS  mandatory
        DESCRIPTION
            "The time of each day creates snapshot-image automatically."
    ::= { srTimeMarkInfoEntry 7 }

    srTimeMarkSnapshotNotificationOption OBJECT-TYPE
        SYNTAX  DisplayString
        ACCESS  read-only
        STATUS  mandatory
        DESCRIPTION
            "The option of triggering snapshot notification schedule."
    ::= { srTimeMarkInfoEntry 8 }

    srTimeMarkReplicationOption OBJECT-TYPE
        SYNTAX  DisplayString
        ACCESS  read-only
        STATUS  mandatory
        DESCRIPTION
            "The replication option after the timemark is taken."
    ::= { srTimeMarkInfoEntry 9 }

    srBackupTable OBJECT IDENTIFIER ::= { sanResourceEntry 16 }
    
    srBackupInfoEntry OBJECT-TYPE
        SYNTAX  SRBackupInfo
        ACCESS  not-accessible
        STATUS  mandatory
        DESCRIPTION
            "Information about the policy and configuration of the backup function."
        INDEX { srBackupResourceID }
    ::= { srBackupTable 1 }

    SRBackupInfo ::= SEQUENCE {
        srBackupResourceID      INTEGER,
        srBackupResourceName    DisplayString,
        srBackupOption          DisplayString,
        srBackupWindow          DisplayString,
        srBackupSessionLen      DisplayString,
        srBackupRelativeTime    DisplayString,
        srBackupWaitTime        INTEGER,
        srBackupSelectCriteria  DisplayString,
        srBackupRawDeviceName   DisplayString
    }

    srBackupResourceID  OBJECT-TYPE
        SYNTAX  INTEGER
        ACCESS  read-only
        STATUS  mandatory
        DESCRIPTION
            "The SAN resource ID assigned by the IPStor server."
    ::= { srBackupInfoEntry 1 }

    srBackupResourceName    OBJECT-TYPE
        SYNTAX  DisplayString
        ACCESS  read-only
        STATUS  mandatory
        DESCRIPTION
            "The SAN resource name created by the user."
    ::= { srBackupInfoEntry 2 }
    
    srBackupOption  OBJECT-TYPE
        SYNTAX  DisplayString
        ACCESS  read-only
        STATUS  mandatory
        DESCRIPTION
            "The status represents the backup option is enable or disable of the SAN resource."
    ::= { srBackupInfoEntry 3 }

    srBackupWindow  OBJECT-TYPE
        SYNTAX  DisplayString
        ACCESS  read-only
        STATUS  mandatory
        DESCRIPTION
            "The daytime allows for opening one backup sesion."
    ::= { srBackupInfoEntry 4 }
    
    srBackupSessionLen  OBJECT-TYPE
        SYNTAX  DisplayString
        ACCESS  read-only
        STATUS  mandatory
        DESCRIPTION
            "The time interval allows for one backup session in each time."
    ::= { srBackupInfoEntry 5 }

    srBackupRelativeTime    OBJECT-TYPE
        SYNTAX  DisplayString
        ACCESS  read-only
        STATUS  mandatory
        DESCRIPTION
            "The time interval waits before closing the backup session which is in inactivity status."
    ::= { srBackupInfoEntry 6 }
    
    srBackupWaitTime    OBJECT-TYPE
        SYNTAX  INTEGER
        ACCESS  read-only
        STATUS  mandatory
        DESCRIPTION
            "The time interval which is represnting in minute unit waits before closing the backup session after completion."
    ::= { srBackupInfoEntry 7 }

    srBackupSelectCriteria  OBJECT-TYPE
        SYNTAX  DisplayString
        ACCESS  read-only
        STATUS  mandatory
        DESCRIPTION
            "The snapshot image selection criteria that could be new or latest for the backup session.
             New represents that it always creates new snapshot image for backup, and 
             Latest represents that it uses the last created snapshot image for backup."
    ::= { srBackupInfoEntry 8 }

    srBackupRawDeviceName    OBJECT-TYPE
        SYNTAX  DisplayString
        ACCESS  read-only
        STATUS  mandatory
        DESCRIPTION
            "The SAN Backup Resource Raw Device Name created by the user."
    ::= { srBackupInfoEntry 9 }

    srReplicationTable OBJECT IDENTIFIER ::= { sanResourceEntry 17 }
    
    srReplicaInfoEntry OBJECT-TYPE
        SYNTAX  SRReplicationInfo
        ACCESS  not-accessible
        STATUS  mandatory
        DESCRIPTION
            "Information about the policy and configuration of the replication function."
        INDEX { srReplicationResourceID }
    ::= { srReplicationTable 1 }

    SRReplicationInfo ::= SEQUENCE {
        srReplicationResourceID			INTEGER,
        srReplicationResourceName		DisplayString,
        srReplicationOption			DisplayString,
        srReplicaServer				DisplayString,
        srReplicaDeviceID			INTEGER,
        srReplicaSchedule			DisplayString,
        srReplicaWatermark			DisplayString,
        srReplicaWatermarkRetry			INTEGER,
        srReplicaTime				DisplayString,
        srReplicaInterval			DisplayString,
        srReplicationContinuousMode		DisplayString,
        srReplicationCreatePrimaryTimeMark	DisplayString,
        srReplicaSyncTimeMark			DisplayString,
        srReplicationProtocol			DisplayString,
        srReplicationCompression		DisplayString,
        srReplicationEncryption			DisplayString,
        srReplicationMicroscan			DisplayString,
        srReplicationSyncPriority		INTEGER,
        srReplicationStatus			DisplayString,
        srReplicationMode			DisplayString,
        srReplicationContinuousResourceID	INTEGER,
        srReplicationContinuousResourceUsage	DisplayString,
        srReplicationDeltaData			DisplayString,
        srReplicationUseExistTM			DisplayString,
        srReplicationPreserveTM			DisplayString,
        srReplicaLastSuccessfulSyncTime		DisplayString,
	srReplicaAverageThroughput		Counter32,
	srReplicaAverageThroughputQuantity	Counter32,
	srReplicaAverageThroughputUnit		INTEGER
    }

    srReplicationResourceID OBJECT-TYPE
        SYNTAX  INTEGER
        ACCESS  read-only
        STATUS  mandatory
        DESCRIPTION
            "The SAN resource ID assigned by the IPStor server."
    ::= { srReplicaInfoEntry 1 }

    srReplicationResourceName   OBJECT-TYPE
        SYNTAX  DisplayString
        ACCESS  read-only
        STATUS  mandatory
        DESCRIPTION
            "The SAN resource name created by the user."
    ::= { srReplicaInfoEntry 2 }
    
    srReplicationOption OBJECT-TYPE
        SYNTAX  DisplayString
        ACCESS  read-only
        STATUS  mandatory
        DESCRIPTION
            "The status represents the replication option is enable or disable of the SAN resource."
    ::= { srReplicaInfoEntry 3 }

    srReplicaServer OBJECT-TYPE
        SYNTAX  DisplayString
        ACCESS  read-only
        STATUS  mandatory
        DESCRIPTION
            "The target replia server name."
    ::= { srReplicaInfoEntry 4 }
    
    srReplicaDeviceID   OBJECT-TYPE
        SYNTAX  INTEGER
        ACCESS  read-only
        STATUS  mandatory
        DESCRIPTION
            "The target replica device ID."
    ::= { srReplicaInfoEntry 5 }

    srReplicaSchedule   OBJECT-TYPE
        SYNTAX  DisplayString
        ACCESS  read-only
        STATUS  mandatory
        DESCRIPTION
            "It represents the current status of the replicating schedule(On-schedule, Suspended, or N/A) set for the SAN resource."
    ::= { srReplicaInfoEntry 6 }
    
    srReplicaWatermark  OBJECT-TYPE
        SYNTAX  DisplayString
        ACCESS  read-only
        STATUS  mandatory
        DESCRIPTION
            "The watermark sets to generate one new replication automatically."
    ::= { srReplicaInfoEntry 7 }

    srReplicaWatermarkRetry OBJECT-TYPE
        SYNTAX  INTEGER
        ACCESS  read-only
        STATUS  mandatory
        DESCRIPTION
            "The retry interval which is representing in minute unit if the replication failed."
    ::= { srReplicaInfoEntry 8 }
    
    srReplicaTime   OBJECT-TYPE
        SYNTAX  DisplayString
        ACCESS  read-only
        STATUS  mandatory
        DESCRIPTION
            "The daytime of each day creates one new replication."
    ::= { srReplicaInfoEntry 9 }
    
    srReplicaInterval   OBJECT-TYPE
        SYNTAX  DisplayString
        ACCESS  read-only
        STATUS  mandatory
        DESCRIPTION
            "The time interval creates one new replication."
    ::= { srReplicaInfoEntry 10 }

    srReplicationContinuousMode   OBJECT-TYPE
        SYNTAX  DisplayString
        ACCESS  read-only
        STATUS  mandatory
        DESCRIPTION
            "The status represents the Continuous Mode of Replication is enable or disable."
    ::= { srReplicaInfoEntry 11 }

    srReplicationCreatePrimaryTimeMark    OBJECT-TYPE
        SYNTAX  DisplayString
        ACCESS  read-only
        STATUS  mandatory
        DESCRIPTION
            "This option allows to create the primary TimeMark when a replica TimeMark is created."
    ::= { srReplicaInfoEntry 12 }

    srReplicaSyncTimeMark    OBJECT-TYPE
        SYNTAX  DisplayString
        ACCESS  read-only
        STATUS  mandatory
        DESCRIPTION
            "This option allows to synchronize the replica TimeMark when a primary TimeMark is created."
    ::= { srReplicaInfoEntry 13 }

    srReplicationProtocol    OBJECT-TYPE
        SYNTAX  DisplayString
        ACCESS  read-only
        STATUS  mandatory
        DESCRIPTION
            "It states the Protocol which Replication uses."
    ::= { srReplicaInfoEntry 14 }

    srReplicationCompression    OBJECT-TYPE
        SYNTAX  DisplayString
        ACCESS  read-only
        STATUS  mandatory
        DESCRIPTION
            "The status represents the Compression option is enable or disable of Replication."
    ::= { srReplicaInfoEntry 15 }

    srReplicationEncryption    OBJECT-TYPE
        SYNTAX  DisplayString
        ACCESS  read-only
        STATUS  mandatory
        DESCRIPTION
            "The status represents the Encryption option is enable or disable of Replication."
    ::= { srReplicaInfoEntry 16 }

    srReplicationMicroscan    OBJECT-TYPE
        SYNTAX  DisplayString
        ACCESS  read-only
        STATUS  mandatory
        DESCRIPTION
            "The status represents the Microscan option is enable or disable of Replication."
    ::= { srReplicaInfoEntry 17 }

    srReplicationSyncPriority    OBJECT-TYPE
        SYNTAX  INTEGER
        ACCESS  read-only
        STATUS  mandatory
        DESCRIPTION
            "The Priority setting when Replication Synchronize of the SAN resource."
    ::= { srReplicaInfoEntry 18 }

    srReplicationStatus    OBJECT-TYPE
        SYNTAX  DisplayString
        ACCESS  read-only
        STATUS  mandatory
        DESCRIPTION
            "The Replication status of the SAN resource."
    ::= { srReplicaInfoEntry 19 }

    srReplicationMode    OBJECT-TYPE
        SYNTAX  DisplayString
        ACCESS  read-only
        STATUS  mandatory
        DESCRIPTION
            "The Replication mode of the SAN resource."
    ::= { srReplicaInfoEntry 20 }

    srReplicationContinuousResourceID    OBJECT-TYPE
        SYNTAX  INTEGER
        ACCESS  read-only
        STATUS  mandatory
        DESCRIPTION
            "The Continuous Replication Resource ID of the SAN resource."
    ::= { srReplicaInfoEntry 21 }

    srReplicationContinuousResourceUsage    OBJECT-TYPE
        SYNTAX  DisplayString
        ACCESS  read-only
        STATUS  mandatory
        DESCRIPTION
            "The Continuous Replication Resource Usage of the SAN resource."
    ::= { srReplicaInfoEntry 22 }

    srReplicationDeltaData    OBJECT-TYPE
        SYNTAX  DisplayString
        ACCESS  read-only
        STATUS  mandatory
        DESCRIPTION
            "The Accumulated Delta Data of replication of the SAN resource."
    ::= { srReplicaInfoEntry 23 }

    srReplicationUseExistTM    OBJECT-TYPE
        SYNTAX  DisplayString
        ACCESS  read-only
        STATUS  mandatory
        DESCRIPTION
            "When Continuous Mode is disabled, the option about using existing TimeMark of the replication."
    ::= { srReplicaInfoEntry 24 }

    srReplicationPreserveTM    OBJECT-TYPE
        SYNTAX  DisplayString
        ACCESS  read-only
        STATUS  mandatory
        DESCRIPTION
            "When Continuous Mode is disabled, the option about perserving TimeMark of the replication."
    ::= { srReplicaInfoEntry 25 }
    
    srReplicaLastSuccessfulSyncTime   OBJECT-TYPE
        SYNTAX  DisplayString
        ACCESS  read-only
        STATUS  mandatory
        DESCRIPTION
            "The last successful synchronize time of the replication."
    ::= { srReplicaInfoEntry 26 }
    
    srReplicaAverageThroughput   OBJECT-TYPE
        SYNTAX  Counter32
        ACCESS  read-only
        STATUS  mandatory
        DESCRIPTION
            "The average throughput (MB/s) of the replication."
    ::= { srReplicaInfoEntry 27 }

    srReplicaAverageThroughputQuantity  OBJECT-TYPE
        SYNTAX  Counter32
        ACCESS  read-only
        STATUS  mandatory
        DESCRIPTION
            "The average throughput quantity of the replication."
    ::= { srReplicaInfoEntry 28 }

    srReplicaAverageThroughputUnit  OBJECT-TYPE
        SYNTAX  INTEGER
        ACCESS  read-only
        STATUS  mandatory
        DESCRIPTION
            "The average throughput unit of the replication. 0 presents KB. 1 presents MB. 2 presents GB. 3 presents TB."
    ::= { srReplicaInfoEntry 29 }

    srCacheTable OBJECT IDENTIFIER ::= { sanResourceEntry 18 }
    
    srCacheInfoEntry    OBJECT-TYPE
        SYNTAX  SRCacheInfo
        ACCESS  not-accessible
        STATUS  mandatory
        DESCRIPTION
            "Information about the configuration and usage of the cache resource."
        INDEX { srCacheResourceID }
    ::= { srCacheTable 1 }

    SRCacheInfo ::= SEQUENCE {
        srCacheResourceID		INTEGER,
        srCacheResourceName		DisplayString,
        srCacheOption			DisplayString,
        srCacheSuspend			DisplayString,
        srCacheTotalSize		Counter32,
        srCacheFreeSize			Counter32,
        srCacheUsage			INTEGER,
        srCacheThreshold		INTEGER,
        srCacheFlushTime		INTEGER,
        srCacheFlushCommand		INTEGER,
        srCacheSkipWriteCommands	DisplayString,
        srCacheFlushSpeed		INTEGER,
        srCacheTotalSizeQuantity	Counter32,
        srCacheTotalSizeUnit		INTEGER,
        srCacheFreeSizeQuantity		Counter32,
        srCacheFreeSizeUnit		INTEGER,
        srCacheOwnResourceID		INTEGER,
        srCacheTotalSize64		Counter64,
        srCacheFreeSize64		Counter64,
	srCacheStatus			DisplayString
    }

    srCacheResourceID   OBJECT-TYPE
        SYNTAX  INTEGER
        ACCESS  read-only
        STATUS  mandatory
        DESCRIPTION
            "The SAN resource ID assigned by the IPStor server."
    ::= { srCacheInfoEntry 1 }

    srCacheResourceName OBJECT-TYPE
        SYNTAX  DisplayString
        ACCESS  read-only
        STATUS  mandatory
        DESCRIPTION
            "The SAN resource name created by the user."
    ::= { srCacheInfoEntry 2 }
    
    srCacheOption   OBJECT-TYPE
        SYNTAX  DisplayString
        ACCESS  read-only
        STATUS  mandatory
        DESCRIPTION
            "The status represents the cache option is enable or disable of the SAN resource."
    ::= { srCacheInfoEntry 3 }
    
    srCacheSuspend  OBJECT-TYPE
        SYNTAX  DisplayString
        ACCESS  read-only
        STATUS  mandatory
        DESCRIPTION
            "The cache resource is currently suspended or not."
    ::= { srCacheInfoEntry 4 }
    
    srCacheTotalSize    OBJECT-TYPE
        SYNTAX  Counter32
        ACCESS  read-only
        STATUS  mandatory
        DESCRIPTION
            "The allocated size when creating the cache resource."
    ::= { srCacheInfoEntry 5 }
    
    srCacheFreeSize OBJECT-TYPE
        SYNTAX  Counter32
        ACCESS  read-only
        STATUS  mandatory
        DESCRIPTION
            "The free resource size which is representing in megabyte unit before reaching the maximum resource size."
    ::= { srCacheInfoEntry 6 }

    srCacheUsage    OBJECT-TYPE
        SYNTAX  INTEGER
        ACCESS  read-only
        STATUS  mandatory
        DESCRIPTION
            "The percentage of the used resource size."
    ::= { srCacheInfoEntry 7 }
    
    srCacheThreshold    OBJECT-TYPE
        SYNTAX  INTEGER
        ACCESS  read-only
        STATUS  mandatory
        DESCRIPTION
            "The data needs to be in the cache before beginning flushing the cache."
    ::= { srCacheInfoEntry 8 }
    
    srCacheFlushTime    OBJECT-TYPE
        SYNTAX  INTEGER
        ACCESS  read-only
        STATUS  mandatory
        DESCRIPTION
            "The number of milliseconds before cache begins to flush when below the data threshold level."
    ::= { srCacheInfoEntry 9 }
    
    srCacheFlushCommand OBJECT-TYPE
        SYNTAX  INTEGER
        ACCESS  read-only
        STATUS  mandatory
        DESCRIPTION
            "The outstanding commands will be sent at one time during the flush process."
    ::= { srCacheInfoEntry 10 }
    
    srCacheSkipWriteCommands    OBJECT-TYPE
        SYNTAX  DisplayString
        ACCESS  read-only
        STATUS  mandatory
        DESCRIPTION
            "This option allows the system to skip multiple pending write commands targeted for the same block."
    ::= { srCacheInfoEntry 11 }

    srCacheFlushSpeed OBJECT-TYPE
        SYNTAX  INTEGER
        ACCESS  read-only
        STATUS  mandatory
        DESCRIPTION
            "The flush speed will be sent at one time during the flush process."
    ::= { srCacheInfoEntry 12 }
    
    srCacheTotalSizeQuantity    OBJECT-TYPE
        SYNTAX  Counter32
        ACCESS  read-only
        STATUS  mandatory
        DESCRIPTION
            "The allocated size quantity when creating the cache resource."
    ::= { srCacheInfoEntry 13 }
    
    srCacheTotalSizeUnit    OBJECT-TYPE
        SYNTAX  INTEGER
        ACCESS  read-only
        STATUS  mandatory
        DESCRIPTION
            "The allocated size unit when creating the cache resource. 0
presents KB. 1 presents MB. 2 presents GB. 3 presents TB."
    ::= { srCacheInfoEntry 14 }
    
    srCacheFreeSizeQuantity OBJECT-TYPE
        SYNTAX  Counter32
        ACCESS  read-only
        STATUS  mandatory
        DESCRIPTION
            "The free resource size quantity before reaching the maximum resource size."
    ::= { srCacheInfoEntry 15 }
    
    srCacheFreeSizeUnit OBJECT-TYPE
        SYNTAX  INTEGER
        ACCESS  read-only
        STATUS  mandatory
        DESCRIPTION
            "The free resource size unit before reaching the maximum resource size. 0 presents KB. 1 presents MB. 2 presents GB. 3 presents TB."
    ::= { srCacheInfoEntry 16 }

    srCacheOwnResourceID   OBJECT-TYPE
        SYNTAX  INTEGER
        ACCESS  read-only
        STATUS  mandatory
        DESCRIPTION
            "The Cache resource ID assigned by the IPStor server."
    ::= { srCacheInfoEntry 17 }
    
    srCacheTotalSize64    OBJECT-TYPE
        SYNTAX  Counter64
        ACCESS  read-only
        STATUS  mandatory
        DESCRIPTION
            "The allocated size when creating the cache resource."
    ::= { srCacheInfoEntry 18 }
    
    srCacheFreeSize64 OBJECT-TYPE
        SYNTAX  Counter64
        ACCESS  read-only
        STATUS  mandatory
        DESCRIPTION
            "The free resource size which is representing in megabyte unit before reaching the maximum resource size."
    ::= { srCacheInfoEntry 19 }
    
    srCacheStatus    OBJECT-TYPE
        SYNTAX  DisplayString
        ACCESS  read-only
        STATUS  mandatory
        DESCRIPTION
            "The current safecache device's status of the SAN resource."
    ::= { srCacheInfoEntry 20 }

    srWriteCacheProperty    OBJECT-TYPE
	SYNTAX  DisplayString
	ACCESS  read-only
	STATUS  mandatory
	DESCRIPTION
      	    "The property represents the write cache is enabled or disabled of the SAN resource."
    ::= { sanResourceEntry 19 }

    srMirrorTable OBJECT IDENTIFIER ::= { sanResourceEntry 20 }
    
    srMirrorInfoEntry    OBJECT-TYPE
        SYNTAX  SRMirrorInfo
        ACCESS  not-accessible
        STATUS  mandatory
        DESCRIPTION
            "Information about the configuration and usage of the mirror."
        INDEX { srMirrorResourceID }
    ::= { srMirrorTable 1 }

    SRMirrorInfo ::= SEQUENCE {
        srMirrorResourceID			INTEGER,
        srMirrorType				DisplayString,
        srMirrorSyncPriority			INTEGER,
        srMirrorSuspended			DisplayString,
        srMirrorThrottle			INTEGER,
        srMirrorHealthMonitoringOption		DisplayString,
        srMirrorHealthCheckInterval		INTEGER,
        srMirrorMaxLagTime			INTEGER,
        srMirrorSuspendThPercent		INTEGER,
        srMirrorSuspendThIOnum			INTEGER,
        srMirrorSyncRetryPolicy			DisplayString,
        srMirrorSyncRetryInterval		DisplayString,
        srMirrorSyncRetryActivity		DisplayString,
        srMirrorSyncRetryTimes			INTEGER,
--        srMirrorThroughputControlOption		DisplayString,
--        srMirrorThroughputCheckTime		DisplayString,
--        srMirrorThroughputCheckInterval		DisplayString,
--        srMirrorThroughputResumeSyncflow	DisplayString,
--        srMirrorThroughputResumeSyncIO		INTEGER,
--        srMirrorThroughputCheckRetry		INTEGER,
	srMirrorSynchronizationStatus		DisplayString,
	srMirrorAlterReadMirror			DisplayString,
	srMirrorAverageThroughput		Counter32,
	srMirrorAverageThroughputQuantity	Counter32,
	srMirrorAverageThroughputUnit		INTEGER,
	srMirrorSANResourceName			DisplayString
    }

    srMirrorResourceID   OBJECT-TYPE
        SYNTAX  INTEGER
        ACCESS  read-only
        STATUS  mandatory
        DESCRIPTION
            "The SAN resource ID that enables the mirror property."
    ::= { srMirrorInfoEntry 1 }

    srMirrorType   OBJECT-TYPE
        SYNTAX  DisplayString
        ACCESS  read-only
        STATUS  mandatory
        DESCRIPTION
            "The mirror type when a SAN resource enable the mirror property."
    ::= { srMirrorInfoEntry 2 }

    srMirrorSyncPriority   OBJECT-TYPE
        SYNTAX  INTEGER
        ACCESS  read-only
        STATUS  mandatory
        DESCRIPTION
            "The mirror synchronization priority when a SAN resource enable the mirror property."
    ::= { srMirrorInfoEntry 3 }

    srMirrorSuspended   OBJECT-TYPE
        SYNTAX  DisplayString
        ACCESS  read-only
        STATUS  mandatory
        DESCRIPTION
            "Whether the mirror is suspended."
    ::= { srMirrorInfoEntry 4 }

    srMirrorThrottle   OBJECT-TYPE
        SYNTAX  INTEGER
        ACCESS  read-only
        STATUS  mandatory
        DESCRIPTION
            "The mirror throttle value for SAN resource."
    ::= { srMirrorInfoEntry 5 }

    srMirrorHealthMonitoringOption   OBJECT-TYPE
        SYNTAX  DisplayString
        ACCESS  read-only
        STATUS  mandatory
        DESCRIPTION
            "The status represents the mirror health monitoring option is enable or disable."
    ::= { srMirrorInfoEntry 6 }

    srMirrorHealthCheckInterval   OBJECT-TYPE
        SYNTAX  INTEGER
        ACCESS  read-only
        STATUS  mandatory
        DESCRIPTION
            "The Interval to Check and report mirror health status."
    ::= { srMirrorInfoEntry 7 }

    srMirrorMaxLagTime   OBJECT-TYPE
        SYNTAX  INTEGER
        ACCESS  read-only
        STATUS  mandatory
        DESCRIPTION
            "The Maximum acceptable lagging time for the mirror I/O's."
    ::= { srMirrorInfoEntry 8 }

    srMirrorSuspendThPercent   OBJECT-TYPE
        SYNTAX  INTEGER
        ACCESS  read-only
        STATUS  mandatory
        DESCRIPTION
            "Suspended mirroring when the threshold of failure reaches the percentage of the failure conditions."
    ::= { srMirrorInfoEntry 9 }

    srMirrorSuspendThIOnum   OBJECT-TYPE
        SYNTAX  INTEGER
        ACCESS  read-only
        STATUS  mandatory
        DESCRIPTION
            "Suspended mirroring when the outstanding IOs is greater than or equals to."
    ::= { srMirrorInfoEntry 10 }

    srMirrorSyncRetryPolicy   OBJECT-TYPE
        SYNTAX  DisplayString
        ACCESS  read-only
        STATUS  mandatory
        DESCRIPTION
            "The status represents the mirror synchronization retry policy is enable or not."
    ::= { srMirrorInfoEntry 11 }

    srMirrorSyncRetryInterval   OBJECT-TYPE
        SYNTAX  DisplayString
        ACCESS  read-only
        STATUS  mandatory
        DESCRIPTION
            "The mirror synchronization retry at specified interval."
    ::= { srMirrorInfoEntry 12 }

    srMirrorSyncRetryActivity   OBJECT-TYPE
        SYNTAX  DisplayString
        ACCESS  read-only
        STATUS  mandatory
        DESCRIPTION
            "The mirror synchronization retry when I/O activity is below or at."
    ::= { srMirrorInfoEntry 13 }

    srMirrorSyncRetryTimes   OBJECT-TYPE
        SYNTAX  INTEGER
        ACCESS  read-only
        STATUS  mandatory
        DESCRIPTION
            "The maximum mirror synchronization retry times."
    ::= { srMirrorInfoEntry 14 }

--    srMirrorThroughputControlOption   OBJECT-TYPE
--        SYNTAX  DisplayString
--        ACCESS  read-only
--        STATUS  mandatory
--        DESCRIPTION
--            "The status represents the mirror throughput control option is enable or not."
--    ::= { srMirrorInfoEntry 15 }

--    srMirrorThroughputCheckTime   OBJECT-TYPE
--        SYNTAX  DisplayString
--        ACCESS  read-only
--        STATUS  mandatory
--        DESCRIPTION
--            "The time to check mirror resource throughput after synchronization in progress."
--    ::= { srMirrorInfoEntry 16 }

--    srMirrorThroughputCheckInterval   OBJECT-TYPE
--        SYNTAX  DisplayString
--        ACCESS  read-only
--        STATUS  mandatory
--        DESCRIPTION
--            "Check mirror resource throughput at the specified interval."
--    ::= { srMirrorInfoEntry 17 }

--    srMirrorThroughputResumeSyncflow   OBJECT-TYPE
--        SYNTAX  DisplayString
--        ACCESS  read-only
--        STATUS  mandatory
--        DESCRIPTION
--            "Resume synchronization when I/Os per second activity is less than or equal to."
--    ::= { srMirrorInfoEntry 18 }

--    srMirrorThroughputResumeSyncIO   OBJECT-TYPE
--        SYNTAX  INTEGER
--        ACCESS  read-only
--        STATUS  mandatory
--        DESCRIPTION
--            "Resume synchronization when numbers of I/Os activity is less than or equal to."
--    ::= { srMirrorInfoEntry 19 }

--    srMirrorThroughputCheckRetry   OBJECT-TYPE
--        SYNTAX  INTEGER
--        ACCESS  read-only
--        STATUS  mandatory
--        DESCRIPTION
--            "Number of checking attempts before resuming synchronization."
--    ::= { srMirrorInfoEntry 20 }
	
    srMirrorSynchronizationStatus  OBJECT-TYPE
	SYNTAX	DisplayString
	ACCESS	read-only
	STATUS	mandatory
	DESCRIPTION
		"It represents the mirror synchronization status of the SAN resource."
    ::= { srMirrorInfoEntry 21 }
	
    srMirrorAlterReadMirror  OBJECT-TYPE
	SYNTAX	DisplayString
	ACCESS	read-only
	STATUS	mandatory
	DESCRIPTION
		"It represents the alternative read mirror option of the SAN resource."
    ::= { srMirrorInfoEntry 22 }
    
    srMirrorAverageThroughput   OBJECT-TYPE
        SYNTAX  Counter32
        ACCESS  read-only
        STATUS  mandatory
        DESCRIPTION
            "The average throughput (MB/s) of the mirror synchronization operation."
    ::= { srMirrorInfoEntry 23 }

    srMirrorAverageThroughputQuantity  OBJECT-TYPE
        SYNTAX  Counter32
        ACCESS  read-only
        STATUS  mandatory
        DESCRIPTION
            "The average throughput quantity of the mirror synchronization operation."
    ::= { srMirrorInfoEntry 24 }

    srMirrorAverageThroughputUnit  OBJECT-TYPE
        SYNTAX  INTEGER
        ACCESS  read-only
        STATUS  mandatory
        DESCRIPTION
            "The average throughput unit of the mirror synchronization operation. 0 presents KB. 1 presents MB. 2 presents GB. 3 presents TB."
    ::= { srMirrorInfoEntry 25 }

    srMirrorSANResourceName   OBJECT-TYPE
        SYNTAX  DisplayString
        ACCESS  read-only
        STATUS  mandatory
        DESCRIPTION
            "The SAN resource Name that enables the mirror property."
    ::= { srMirrorInfoEntry 26 }

    srThinProvisionTable OBJECT IDENTIFIER ::= { sanResourceEntry 21 }
    
    srThinProvisionInfoEntry    OBJECT-TYPE
        SYNTAX  SRThinProvisionInfo
        ACCESS  not-accessible
        STATUS  mandatory
        DESCRIPTION
            "Information about the usage of the Thin Provision resource."
        INDEX { srThinProvisionOption }
    ::= { srThinProvisionTable 1 }

    SRThinProvisionInfo ::= SEQUENCE {
        srThinProvisionOption			DisplayString,
        srThinProvisionCurrAllocSize		Counter32,
        srThinProvisionUsageSize		Counter32,
        srThinProvisionUsagePercentage		DisplayString,
        srThinProvisionCurrAllocSizeQuantity	Counter32,
        srThinProvisionCurrAllocSizeUnit	INTEGER,
        srThinProvisionUsageSizeQuantity	Counter32,
        srThinProvisionUsageSizeUnit		INTEGER,
        srThinProvisionCurrAllocSize64		Counter64,
        srThinProvisionUsageSize64		Counter64,
        srThinProvisionSANResourceID		INTEGER,
        srThinProvisionSANResourceName		DisplayString
    }

    srThinProvisionOption   OBJECT-TYPE
        SYNTAX  DisplayString
        ACCESS  read-only
        STATUS  mandatory
        DESCRIPTION
            "It represents the thin provisioning option is enable or disable of the resource."
    ::= { srThinProvisionInfoEntry 1 }

    srThinProvisionCurrAllocSize   OBJECT-TYPE
        SYNTAX  Counter32
        ACCESS  read-only
        STATUS  mandatory
        DESCRIPTION
            "The current Allocated Size of the Thin Provision resource on the IPStor server."
    ::= { srThinProvisionInfoEntry 2 }

    srThinProvisionUsageSize   OBJECT-TYPE
        SYNTAX  Counter32
        ACCESS  read-only
        STATUS  mandatory
        DESCRIPTION
            "The current usage size of the Thin Provision resource."
    ::= { srThinProvisionInfoEntry 3 }

    srThinProvisionUsagePercentage   OBJECT-TYPE
        SYNTAX  DisplayString
        ACCESS  read-only
        STATUS  mandatory
        DESCRIPTION
            "The current usage percentage of the Thin Provision resource."
    ::= { srThinProvisionInfoEntry 4 }

    srThinProvisionCurrAllocSizeQuantity   OBJECT-TYPE
        SYNTAX  Counter32
        ACCESS  read-only
        STATUS  mandatory
        DESCRIPTION
            "The current Allocated Size quantity of the Thin Provision resource on the IPStor server."
    ::= { srThinProvisionInfoEntry 5 }

    srThinProvisionCurrAllocSizeUnit   OBJECT-TYPE
        SYNTAX  INTEGER
        ACCESS  read-only
        STATUS  mandatory
        DESCRIPTION
            "The current Allocated Size unit of the Thin Provision resource on the IPStor server. 0 presents KB. 1 presents MB. 2 presents GB. 3 presents TB."
    ::= { srThinProvisionInfoEntry 6 }

    srThinProvisionUsageSizeQuantity   OBJECT-TYPE
        SYNTAX  Counter32
        ACCESS  read-only
        STATUS  mandatory
        DESCRIPTION
            "The current usage size quantity of the Thin Provision resource."
    ::= { srThinProvisionInfoEntry 7 }

    srThinProvisionUsageSizeUnit   OBJECT-TYPE
        SYNTAX  INTEGER
        ACCESS  read-only
        STATUS  mandatory
        DESCRIPTION
            "The current usage size unit of the Thin Provision resource. 0 presents KB. 1 presents MB. 2 presents GB. 3 presents TB."
    ::= { srThinProvisionInfoEntry 8 }

    srThinProvisionCurrAllocSize64   OBJECT-TYPE
        SYNTAX  Counter64
        ACCESS  read-only
        STATUS  mandatory
        DESCRIPTION
            "The current Allocated Size of the Thin Provision resource on the IPStor server."
    ::= { srThinProvisionInfoEntry 9 }

    srThinProvisionUsageSize64   OBJECT-TYPE
        SYNTAX  Counter64
        ACCESS  read-only
        STATUS  mandatory
        DESCRIPTION
            "The current usage size of the Thin Provision resource."
    ::= { srThinProvisionInfoEntry 10 }

    srThinProvisionSANResourceID   OBJECT-TYPE
        SYNTAX  INTEGER
        ACCESS  read-only
        STATUS  mandatory
        DESCRIPTION
            "The SAN resource ID that enables the ThinProvision option."
    ::= { srThinProvisionInfoEntry 11 }

    srThinProvisionSANResourceName   OBJECT-TYPE
        SYNTAX  DisplayString
        ACCESS  read-only
        STATUS  mandatory
        DESCRIPTION
            "The SAN resource Name that enables the ThinProvision option."
    ::= { srThinProvisionInfoEntry 12 }

    srCDPJournalTable OBJECT IDENTIFIER ::= { sanResourceEntry 22 }
    
    srCDPJournalInfoEntry OBJECT-TYPE
        SYNTAX  SRCDPJournalInfo
        ACCESS  not-accessible
        STATUS  mandatory
        DESCRIPTION
            "Information about the policy and configuration of the CDP Journal function."
        INDEX { srCDPJournalResourceID }
    ::= { srCDPJournalTable 1 }

    SRCDPJournalInfo ::= SEQUENCE {
        srCDPJournalResourceID			INTEGER,
        srCDPJournalSANResourceID		INTEGER,
        srCDPJournalOption			DisplayString,
        srCDPJournalTotalSize			Counter32,
        srCDPJournalStatus			DisplayString,
        srCDPJournalPerformanceLevel		DisplayString,
--        srCDPJournalPolicy			DisplayString,
--        srCDPJournalCoveragePeriod		DisplayString,
--        srCDPJournalExpansionTH			INTEGER,
--        srCDPJournalExpansionAllocPercent	INTEGER,
--        srCDPJournalExpansionAllocMB		INTEGER,
--        srCDPJournalMaxSize			Counter32,
        srCDPJournalTotalSizeQuantity		Counter32,
        srCDPJournalTotalSizeUnit		INTEGER,
--        srCDPJournalMaxSizeQuantity		Counter32,
--        srCDPJournalMaxSizeUnit			INTEGER,
--        srCDPJournalExpansionAllocMBQuantity	Counter32,
--        srCDPJournalExpansionAllocMBUnit	INTEGER,
        srCDPJournalTotalSize64			Counter64,
--        srCDPJournalMaxSize64			Counter64,
--        srCDPJournalExpansionAllocMB64		Counter64,
	srCDPJournalAvailableTimerange		DisplayString,
	srCDPJournalUsageSize			Counter32,
	srCDPJournalUsagePercentage		Counter32,
        srCDPJournalUsageSizeQuantity		Counter32,
        srCDPJournalUsageSizeUnit		INTEGER,
        srCDPJournalUsageSize64			Counter64,
        srCDPJournalSANResourceName		DisplayString
    }

    srCDPJournalResourceID    OBJECT-TYPE
        SYNTAX  INTEGER
        ACCESS  read-only
        STATUS  mandatory
        DESCRIPTION
            "The CDP Journal ID assigned by the IPStor server."
    ::= { srCDPJournalInfoEntry 1 }

    srCDPJournalSANResourceID    OBJECT-TYPE
        SYNTAX  INTEGER
        ACCESS  read-only
        STATUS  mandatory
        DESCRIPTION
            "The CDP Journal SAN resource ID assigned by the IPStor server."
    ::= { srCDPJournalInfoEntry 2 }

    srCDPJournalOption    OBJECT-TYPE
        SYNTAX  DisplayString
        ACCESS  read-only
        STATUS  mandatory
        DESCRIPTION
            "The status represents the CDP Journal option is enable or disable of the SAN resource."
    ::= { srCDPJournalInfoEntry 3 }

    srCDPJournalTotalSize    OBJECT-TYPE
        SYNTAX  Counter32
        ACCESS  read-only
        STATUS  mandatory
        DESCRIPTION
            "The CDP Journal Total size of the SAN resource."
    ::= { srCDPJournalInfoEntry 4 }

    srCDPJournalStatus    OBJECT-TYPE
        SYNTAX  DisplayString
        ACCESS  read-only
        STATUS  mandatory
        DESCRIPTION
            "The status represents current CDP Journal of the SAN resource."
    ::= { srCDPJournalInfoEntry 5 }

    srCDPJournalPerformanceLevel    OBJECT-TYPE
        SYNTAX  DisplayString
        ACCESS  read-only
        STATUS  mandatory
        DESCRIPTION
            "The setting Performance level for the CDP Journal of the SAN resource."
    ::= { srCDPJournalInfoEntry 6 }

--    srCDPJournalPolicy    OBJECT-TYPE
--        SYNTAX  DisplayString
--        ACCESS  read-only
--        STATUS  mandatory
--        DESCRIPTION
--            "The CDP Journal Storage Policy when threshold reached and continuous coverage period not exceeded."
--    ::= { srCDPJournalInfoEntry 7 }

--    srCDPJournalCoveragePeriod    OBJECT-TYPE
--        SYNTAX  DisplayString
--        ACCESS  read-only
--        STATUS  mandatory
--        DESCRIPTION
--            "Minimun period of continuous coverage to be maintained when journal storage is available or can be allocated."
--    ::= { srCDPJournalInfoEntry 8 }

--    srCDPJournalExpansionTH    OBJECT-TYPE
--        SYNTAX  INTEGER
--        ACCESS  read-only
--        STATUS  mandatory
--        DESCRIPTION
--            "The threshold to expand the journal storage when usage reaches."
--    ::= { srCDPJournalInfoEntry 9 }

--    srCDPJournalExpansionAllocate    OBJECT-TYPE
--        SYNTAX  INTEGER
--        ACCESS  read-only
--        STATUS  mandatory
--        DESCRIPTION
--            "Amount to allocate when expansion is triggered of the CDP Journal Storage."
--    ::= { srCDPJournalInfoEntry 10 }

--    srCDPJournalExpansionAllocMB    OBJECT-TYPE
--        SYNTAX  INTEGER
--        ACCESS  read-only
--        STATUS  mandatory
--        DESCRIPTION
--            "Amount to allocate when expansion is triggered of the CDP Journal Storage."
--    ::= { srCDPJournalInfoEntry 11 }

--    srCDPJournalMaxSize    OBJECT-TYPE
--        SYNTAX  Counter32
--        ACCESS  read-only
--        STATUS  mandatory
--        DESCRIPTION
--            "The CDP Journal Storage Maximum size of the SAN resource."
--    ::= { srCDPJournalInfoEntry 12 }

    srCDPJournalTotalSizeQuantity    OBJECT-TYPE
        SYNTAX  Counter32
        ACCESS  read-only
        STATUS  mandatory
        DESCRIPTION
            "The CDP Journal Total size quantity of the SAN resource."
    ::= { srCDPJournalInfoEntry 13 }

    srCDPJournalTotalSizeUnit    OBJECT-TYPE
        SYNTAX  INTEGER
        ACCESS  read-only
        STATUS  mandatory
        DESCRIPTION
            "The CDP Journal Total size unit of the SAN resource. The size unit of the device. 0 presents KB. 1 presents MB. 2 presents GB. 3 presents TB."
    ::= { srCDPJournalInfoEntry 14 }

--    srCDPJournalMaxSizeQuantity    OBJECT-TYPE
--        SYNTAX  Counter32
--        ACCESS  read-only
--        STATUS  mandatory
--        DESCRIPTION
--            "The CDP Journal Storage Maximum size quantity of the SAN resource."
--    ::= { srCDPJournalInfoEntry 15 }

--    srCDPJournalMaxSizeUnit    OBJECT-TYPE
--        SYNTAX  INTEGER
--        ACCESS  read-only
--        STATUS  mandatory
--        DESCRIPTION
--            "The CDP Journal Storage Maximum size unit of the SAN resource. The size unit of the device. 0 presents KB. 1 presents MB. 2 presents GB. 3 presents TB."
--    ::= { srCDPJournalInfoEntry 16 }

--    srCDPJournalExpansionAllocMBQuantity    OBJECT-TYPE
--        SYNTAX  Counter32
--        ACCESS  read-only
--        STATUS  mandatory
--        DESCRIPTION
--            "The Amount quantity to allocate when expansion is triggered of the CDP Journal Storage."
--    ::= { srCDPJournalInfoEntry 17 }

--    srCDPJournalExpansionAllocMBUnit    OBJECT-TYPE
--        SYNTAX  INTEGER
--        ACCESS  read-only
--        STATUS  mandatory
--        DESCRIPTION
--            "The Amount unit to allocate when expansion is triggered of the CDP Journal Storage. The size unit of the device. 0 presents KB. 1 presents MB. 2 presents GB. 3 presents TB."
--    ::= { srCDPJournalInfoEntry 18 }

    srCDPJournalTotalSize64    OBJECT-TYPE
        SYNTAX  Counter64
        ACCESS  read-only
        STATUS  mandatory
        DESCRIPTION
            "The CDP Journal Total size of the SAN resource."
    ::= { srCDPJournalInfoEntry 19 }

--    srCDPJournalMaxSize64    OBJECT-TYPE
--        SYNTAX  Counter64
--        ACCESS  read-only
--        STATUS  mandatory
--        DESCRIPTION
--            "The CDP Journal Storage Maximum size of the SAN resource."
--    ::= { srCDPJournalInfoEntry 20 }

--    srCDPJournalExpansionAllocMB64    OBJECT-TYPE
--        SYNTAX  Counter64
--        ACCESS  read-only
--        STATUS  mandatory
--        DESCRIPTION
--            "The Amount to allocate when expansion is triggered of the CDP Journal Storage."
--    ::= { srCDPJournalInfoEntry 21 }

    srCDPJournalAvailableTimerange    OBJECT-TYPE
        SYNTAX  DisplayString
        ACCESS  read-only
        STATUS  mandatory
        DESCRIPTION
            "The CDP Journal available time range of the SAN resource."
    ::= { srCDPJournalInfoEntry 22 }

    srCDPJournalUsageSize    OBJECT-TYPE
        SYNTAX  Counter32
        ACCESS  read-only
        STATUS  mandatory
        DESCRIPTION
            "The CDP Journal usage size(MB) of the SAN resource."
    ::= { srCDPJournalInfoEntry 23 }

    srCDPJournalUsagePercentage    OBJECT-TYPE
        SYNTAX  Counter32
        ACCESS  read-only
        STATUS  mandatory
        DESCRIPTION
            "The CDP Journal usage percentage of the SAN resource."
    ::= { srCDPJournalInfoEntry 24 }

    srCDPJournalUsageSizeQuantity    OBJECT-TYPE
        SYNTAX  Counter32
        ACCESS  read-only
        STATUS  mandatory
        DESCRIPTION
            "The CDP Journal Usage size quantity of the SAN resource."
    ::= { srCDPJournalInfoEntry 25 }

    srCDPJournalUsageSizeUnit    OBJECT-TYPE
        SYNTAX  INTEGER
        ACCESS  read-only
        STATUS  mandatory
        DESCRIPTION
            "The CDP Journal Usage size unit of the SAN resource. The size unit of the device. 0 presents KB. 1 presents MB. 2 presents GB. 3 presents TB."
    ::= { srCDPJournalInfoEntry 26 }

    srCDPJournalUsageSize64    OBJECT-TYPE
        SYNTAX  Counter64
        ACCESS  read-only
        STATUS  mandatory
        DESCRIPTION
            "The CDP Journal Usage size of the SAN resource."
    ::= { srCDPJournalInfoEntry 27 }

    srCDPJournalSANResourceName    OBJECT-TYPE
        SYNTAX  DisplayString
        ACCESS  read-only
        STATUS  mandatory
        DESCRIPTION
            "The CDP Journal SAN resource Name assigned by the IPStor server."
    ::= { srCDPJournalInfoEntry 28 }
	
    srNearLineMirrorTable OBJECT IDENTIFIER ::= { sanResourceEntry 23 }
    
    srNearLineMirrorInfoEntry    OBJECT-TYPE
        SYNTAX  SRNearLineMirrorInfo
        ACCESS  not-accessible
        STATUS  mandatory
        DESCRIPTION
            "Information about the configuration of the Near-Line Mirror resource."
        INDEX { srNearLineMirrorRemoteServerName }
    ::= { srNearLineMirrorTable 1 }

    SRNearLineMirrorInfo ::= SEQUENCE {
        srNearLineMirrorRemoteServerName	DisplayString,
        srNearLineMirrorRemoteServerAlias	DisplayString,
        srNearLineMirrorRemoteID		INTEGER,
        srNearLineMirrorRemoteGUID		DisplayString,
        srNearLineMirrorRemoteSN		DisplayString,
        srNearLineMirrorSANResourceID		INTEGER,
        srNearLineMirrorSANResourceName		DisplayString
    }

    srNearLineMirrorRemoteServerName   OBJECT-TYPE
        SYNTAX  DisplayString
        ACCESS  read-only
        STATUS  mandatory
        DESCRIPTION
            "The remote server name of Near-Line mirror resource sets on the IPStor server."
    ::= { srNearLineMirrorInfoEntry 1 }

    srNearLineMirrorRemoteServerAlias   OBJECT-TYPE
        SYNTAX  DisplayString
        ACCESS  read-only
        STATUS  mandatory
        DESCRIPTION
            "The remote server Alias of Near-Line mirror resource sets on the IPStor server."
    ::= { srNearLineMirrorInfoEntry 2 }

    srNearLineMirrorRemoteID   OBJECT-TYPE
        SYNTAX  INTEGER
        ACCESS  read-only
        STATUS  mandatory
        DESCRIPTION
            "The remote resource ID of Near-Line mirror resource sets on the IPStor server."
    ::= { srNearLineMirrorInfoEntry 3 }

    srNearLineMirrorRemoteGUID   OBJECT-TYPE
        SYNTAX  DisplayString
        ACCESS  read-only
        STATUS  mandatory
        DESCRIPTION
            "The remote resource GUID of Near-Line mirror resource sets on the IPStor server."
    ::= { srNearLineMirrorInfoEntry 4 }

    srNearLineMirrorRemoteSN   OBJECT-TYPE
        SYNTAX  DisplayString
        ACCESS  read-only
        STATUS  mandatory
        DESCRIPTION
            "The remote resource serial number of Near-Line mirror resource sets on the IPStor server."
    ::= { srNearLineMirrorInfoEntry 5 }

    srNearLineMirrorSANResourceID    OBJECT-TYPE
        SYNTAX  INTEGER
        ACCESS  read-only
        STATUS  mandatory
        DESCRIPTION
            "The Near-Line mirror SAN resource ID assigned by the IPStor server."
    ::= { srNearLineMirrorInfoEntry 6 }

    srNearLineMirrorSANResourceName    OBJECT-TYPE
        SYNTAX  INTEGER
        ACCESS  read-only
        STATUS  mandatory
        DESCRIPTION
            "The Near-Line mirror SAN resource Name assigned by the IPStor server."
    ::= { srNearLineMirrorInfoEntry 7 }
	
	srTotalSizeQuantity OBJECT-TYPE
		SYNTAX	Counter32
		ACCESS	read-only
		STATUS	mandatory
		DESCRIPTION
			"The amount of device size quantity of the SAN resource."
	::= { sanResourceEntry 24 }
	
	srTotalSizeUnit OBJECT-TYPE
		SYNTAX	INTEGER
		ACCESS	read-only
		STATUS	mandatory
		DESCRIPTION
			"The amount of device size unit of the SAN resource. The size unit of the device. 0 presents KB. 1 presents MB. 2 presents GB. 3 presents TB."
	::= { sanResourceEntry 25 }

	srTotalSectors64  OBJECT-TYPE
		SYNTAX	Counter64
		ACCESS	read-only
		STATUS	mandatory
		DESCRIPTION
			"The amount of sectors allocated by the SAN resource."
	::= { sanResourceEntry 26 }
	
	srTotalSize64 OBJECT-TYPE
		SYNTAX	Counter64
		ACCESS	read-only
		STATUS	mandatory
		DESCRIPTION
			"The amount of device size which is representing with megabyte unit of the SAN resource."
	::= { sanResourceEntry 27 }

	srISCSIClientInfoTable OBJECT IDENTIFIER ::= { sanResourceEntry 28 }

	srISCSIClientInfoEntry OBJECT-TYPE
		SYNTAX  SRISCSIClientInfo
		ACCESS  not-accessible
		STATUS  mandatory
		DESCRIPTION
			"Information about the iSCSI clients if the SAN resources have been assigned."
		INDEX { srISCSIClientNo }
	::= { srISCSIClientInfoTable 1 }

	SRISCSIClientInfo ::= SEQUENCE {
		srISCSIClientNo		INTEGER,
		srISCSIName		DisplayString,
		srISCSISANResourceID	INTEGER,
		srISCSISANResourceName	DisplayString,
		srISCSIAccessType	DisplayString,
		srISCSIConnectAccess	DisplayString
	}

	srISCSIClientNo OBJECT-TYPE
		SYNTAX  INTEGER
		ACCESS  read-only
		STATUS  mandatory
		DESCRIPTION
			"The iSCSI client ID assigned by the IPStor server."
	::= { srISCSIClientInfoEntry 1 }

	srISCSIName    OBJECT-TYPE
		SYNTAX  DisplayString
		ACCESS  read-only
		STATUS  mandatory
		DESCRIPTION
			"The iSCSI client name assigned by the IPStor server."
	::= { srISCSIClientInfoEntry 2 }

	srISCSISANResourceID   OBJECT-TYPE
		SYNTAX  INTEGER
		ACCESS  read-only
		STATUS  mandatory
		DESCRIPTION
			"The SAN resource ID assigned by the IPStor server."
	::= { srISCSIClientInfoEntry 3 }

	srISCSISANResourceName OBJECT-TYPE 
		SYNTAX  DisplayString
		ACCESS  read-only
		STATUS  mandatory
		DESCRIPTION
			"The SAN resource name created by the user."
	::= { srISCSIClientInfoEntry 4 }

	srISCSIAccessType    OBJECT-TYPE
		SYNTAX  DisplayString
		ACCESS  read-only
		STATUS  mandatory
		DESCRIPTION
			"The resource access type of the iSCSI client."
	::= { srISCSIClientInfoEntry 5 }
   
	srISCSIConnectAccess OBJECT-TYPE
		SYNTAX  DisplayString
		ACCESS  read-only
		STATUS  mandatory
		DESCRIPTION
			"Identify the connecting and accessing status with a resource of the iSCSI client."
	::= { srISCSIClientInfoEntry 6 }

	srPhysicalTotalAllocLayoutTable OBJECT IDENTIFIER ::= { sanResourceEntry 29 }

	srPhysicalTotalAllocLayoutEntry OBJECT-TYPE
		SYNTAX  SRPhysicalTotalAllocLayout
		ACCESS  not-accessible
		STATUS  mandatory
		DESCRIPTION
			"Information about the physical devices which are reserved and created by logical SAN resource."
		INDEX { srpaAllocSANResourceName }
	::= { srPhysicalTotalAllocLayoutTable 1 }

	SRPhysicalTotalAllocLayout ::= SEQUENCE {
		srpaAllocSANResourceName		DisplayString,
		srpaAllocName			        DisplayString,
		srpaAllocType  			        DisplayString,
		srpaAllocAdapterNo		    	INTEGER,
		srpaAllocChannelNo		    	INTEGER,
		srpaAllocScsiID			        INTEGER,
		srpaAllocLun			        INTEGER,
		srpaAllocFirstSector		    	Counter32,
		srpaAllocLastSector			Counter32,
		srpaAllocFirstSector64			Counter64,
		srpaAllocLastSector64			Counter64,
		srpaAllocSize			        Counter32,
		srpaAllocSizeQuantity		        Counter32,
		srpaAllocSizeUnit			INTEGER,
		srpaAllocSize64				Counter64
	}

	srpaAllocSANResourceName    OBJECT-TYPE
		SYNTAX	DisplayString
		ACCESS	read-only
		STATUS	mandatory
		DESCRIPTION
			"The SAN resource name created by the user."
	::= { srPhysicalTotalAllocLayoutEntry 1 }

	srpaAllocName    OBJECT-TYPE
		SYNTAX	DisplayString
		ACCESS	read-only
		STATUS	mandatory
		DESCRIPTION
			"The physical device name."
	::= { srPhysicalTotalAllocLayoutEntry 2 }
	
	srpaAllocType OBJECT-TYPE
		SYNTAX	DisplayString
		ACCESS	read-only
		STATUS	mandatory
		DESCRIPTION
			"It represents the type(Primary, or Mirror) of the physical layout."
	::= { srPhysicalTotalAllocLayoutEntry 3 }

	srpaAllocAdapterNo OBJECT-TYPE
		SYNTAX  INTEGER
		ACCESS	read-only
		STATUS	mandatory
		DESCRIPTION
			"The SCSI adapter number of the physical device."
	::= { srPhysicalTotalAllocLayoutEntry 4 }

	srpaAllocChannelNo OBJECT-TYPE
		SYNTAX  INTEGER
		ACCESS	read-only
		STATUS	mandatory
		DESCRIPTION
			"The SCSI channel number of the physical device."
	::= { srPhysicalTotalAllocLayoutEntry 5 }

	srpaAllocScsiID OBJECT-TYPE
		SYNTAX  INTEGER
		ACCESS	read-only
		STATUS	mandatory
		DESCRIPTION
			"The SCSI ID of the physical device."
	::= { srPhysicalTotalAllocLayoutEntry 6 }

	srpaAllocLun OBJECT-TYPE
		SYNTAX  INTEGER
		ACCESS	read-only
		STATUS	mandatory
		DESCRIPTION
			"The SCSI LUN number of the physical device."
	::= { srPhysicalTotalAllocLayoutEntry 7 }

	srpaAllocFirstSector OBJECT-TYPE
		SYNTAX  Counter32
		ACCESS	read-only
		STATUS	mandatory
		DESCRIPTION
			"The first sector of the physical device which is allocated by the SAN resource."
	::= { srPhysicalTotalAllocLayoutEntry 8 }

	srpaAllocLastSector  OBJECT-TYPE
		SYNTAX  Counter32
		ACCESS	read-only
		STATUS	mandatory
		DESCRIPTION
			"The last sector of the physical device which is allocated by the SAN resource."
	::= { srPhysicalTotalAllocLayoutEntry 9 }

	srpaAllocFirstSector64 OBJECT-TYPE
		SYNTAX  Counter64
		ACCESS	read-only
		STATUS	mandatory
		DESCRIPTION
			"The first sector of the physical device which is allocated by the SAN resource."
	::= { srPhysicalTotalAllocLayoutEntry 10 }

	srpaAllocLastSector64  OBJECT-TYPE
		SYNTAX  Counter64
		ACCESS	read-only
		STATUS	mandatory
		DESCRIPTION
			"The last sector of the physical device which is allocated by the SAN resource."
	::= { srPhysicalTotalAllocLayoutEntry 11 }
		
	srpaAllocSize    OBJECT-TYPE
		SYNTAX  Counter32
		ACCESS	read-only
		STATUS	mandatory
		DESCRIPTION
			"The amount of the allocated size which is representing with megabyte unit within a physical device."
	::= { srPhysicalTotalAllocLayoutEntry 12 }
		
	srpaAllocSizeQuantity    OBJECT-TYPE
		SYNTAX  Counter32
		ACCESS	read-only
		STATUS	mandatory
		DESCRIPTION
			"The amount of the allocated size quantity within a physical device."
	::= { srPhysicalTotalAllocLayoutEntry 13 }
		
	srpaAllocSizeUnit    OBJECT-TYPE
		SYNTAX  INTEGER
		ACCESS	read-only
		STATUS	mandatory
		DESCRIPTION
			"The amount of the allocated size unit within a physical device. The size unit of the device. 0 presents KB. 1 presents MB. 2 presents GB. 3 presents TB."
	::= { srPhysicalTotalAllocLayoutEntry 14 }
		
	srpaAllocSize64    OBJECT-TYPE
		SYNTAX  Counter64
		ACCESS	read-only
		STATUS	mandatory
		DESCRIPTION
			"The amount of the allocated size which is representing with megabyte unit within a physical device."
	::= { srPhysicalTotalAllocLayoutEntry 15 }

	srHotZonePrefetchInfoTable OBJECT IDENTIFIER ::= { sanResourceEntry 30 }

	srHotZonePrefetchInfoEntry OBJECT-TYPE
		SYNTAX  SRHotZonePrefetchInfo
		ACCESS  not-accessible
		STATUS  mandatory
		DESCRIPTION
			"Information about the HotZone Prefetch if the SAN resources have enabled."
		INDEX { srHotZonePrefetchSANResourceID }
	::= { srHotZonePrefetchInfoTable 1 }

	SRHotZonePrefetchInfo ::= SEQUENCE {
		srHotZonePrefetchSANResourceID		INTEGER,
		srHotZonePrefetchMaximumChains		INTEGER,
		srHotZonePrefetchMaximumReadAhead	INTEGER,
		srHotZonePrefetchReadAhead		INTEGER,
		srHotZonePrefetchChainTimeout		DisplayString,
		srHotZonePrefetchSANResourceName	DisplayString
	}

	srHotZonePrefetchSANResourceID OBJECT-TYPE
		SYNTAX  INTEGER
		ACCESS  read-only
		STATUS  mandatory
		DESCRIPTION
			"The SAN Resource ID that assigned by IPStor server."
	::= { srHotZonePrefetchInfoEntry 1 }

	srHotZonePrefetchMaximumChains OBJECT-TYPE
		SYNTAX  INTEGER
		ACCESS  read-only
		STATUS  mandatory
		DESCRIPTION
			"The maximum number of sequential read chains to detect."
	::= { srHotZonePrefetchInfoEntry 2 }

	srHotZonePrefetchMaximumReadAhead OBJECT-TYPE
		SYNTAX  INTEGER
		ACCESS  read-only
		STATUS  mandatory
		DESCRIPTION
			"The maximum size to read ahead representing with KB."
	::= { srHotZonePrefetchInfoEntry 3 }

	srHotZonePrefetchReadAhead OBJECT-TYPE
		SYNTAX  INTEGER
		ACCESS  read-only
		STATUS  mandatory
		DESCRIPTION
			"The size of read the read command issued when reading ahead representing with KB."
	::= { srHotZonePrefetchInfoEntry 4 }

	srHotZonePrefetchChainTimeout OBJECT-TYPE
		SYNTAX  DisplayString
		ACCESS  read-only
		STATUS  mandatory
		DESCRIPTION
			"The time before the chain is removed and the readahead buffers are freed."
	::= { srHotZonePrefetchInfoEntry 5 }

	srHotZonePrefetchSANResourceName OBJECT-TYPE
		SYNTAX  DisplayString
		ACCESS  read-only
		STATUS  mandatory
		DESCRIPTION
			"The SAN Resource Name that assigned by IPStor server enables the HotZone Prefetch."
	::= { srHotZonePrefetchInfoEntry 6 }

	srHotZoneReadCacheInfoTable OBJECT IDENTIFIER ::= { sanResourceEntry 31 }

	srHotZoneReadCacheInfoEntry OBJECT-TYPE
		SYNTAX  SRHotZoneReadCacheInfo
		ACCESS  not-accessible
		STATUS  mandatory
		DESCRIPTION
			"Information about the HotZone Read Cache if the SAN resources have enabled."
		INDEX { srHotZoneReadCacheResourceID }
	::= { srHotZoneReadCacheInfoTable 1 }

	SRHotZoneReadCacheInfo ::= SEQUENCE {
		srHotZoneReadCacheResourceID		INTEGER,
		srHotZoneReadCacheSANResourceID		INTEGER,
		srHotZoneReadCacheTotalSize		Counter32,
		srHotZoneReadCacheStatus		DisplayString,
		srHotZoneReadCacheSuspended		DisplayString,
		srHotZoneReadCacheAccessType		DisplayString,
		srHotZoneReadCacheAccessIntensity	DisplayString,
		srHotZoneReadCacheMinimumStayTime	DisplayString,
		srHotZoneReadCacheEachZoneSize		DisplayString,
		srHotZoneReadCacheTotalZones		Counter32,
		srHotZoneReadCacheUsedZones		Counter32,
		srHotZoneReadCacheHitRatio		DisplayString,
		srHotZoneReadCacheTotalSizeQuantity	Counter32,
		srHotZoneReadCacheTotalSizeUnit		INTEGER,
		srHotZoneReadCacheTotalSize64		Counter64,
		srHotZoneReadCacheSANResourceID		DisplayString
	}

	srHotZoneReadCacheResourceID OBJECT-TYPE
		SYNTAX  INTEGER
		ACCESS  read-only
		STATUS  mandatory
		DESCRIPTION
			"The Resource ID that assigned by IPStor server."
	::= { srHotZoneReadCacheInfoEntry 1 }

	srHotZoneReadCacheSANResourceID OBJECT-TYPE
		SYNTAX  INTEGER
		ACCESS  read-only
		STATUS  mandatory
		DESCRIPTION
			"The SANResource ID that assigned by IPStor server."
	::= { srHotZoneReadCacheInfoEntry 2 }

	srHotZoneReadCacheTotalSize OBJECT-TYPE
		SYNTAX  Counter32
		ACCESS  read-only
		STATUS  mandatory
		DESCRIPTION
			"The amount of device size which is representing with megabyte unit of the HotZone read cache resource."
	::= { srHotZoneReadCacheInfoEntry 3 }

	srHotZoneReadCacheStatus OBJECT-TYPE
		SYNTAX  DisplayString
		ACCESS  read-only
		STATUS  mandatory
		DESCRIPTION
			"The status represents current HotZone read cache of the SAN resource."
	::= { srHotZoneReadCacheInfoEntry 4 }

	srHotZoneReadCacheSuspended OBJECT-TYPE
		SYNTAX  DisplayString
		ACCESS  read-only
		STATUS  mandatory
		DESCRIPTION
			"The Suspended status represents current HotZone read cache of the SAN resource."
	::= { srHotZoneReadCacheInfoEntry 5 }

	srHotZoneReadCacheAccessType OBJECT-TYPE
		SYNTAX  DisplayString
		ACCESS  read-only
		STATUS  mandatory
		DESCRIPTION
			"The zone's access type policy of the SAN resource."
	::= { srHotZoneReadCacheInfoEntry 6 }

	srHotZoneReadCacheAccessIntensity OBJECT-TYPE
		SYNTAX  DisplayString
		ACCESS  read-only
		STATUS  mandatory
		DESCRIPTION
			"The access intensity to determine how the zone is accessed."
	::= { srHotZoneReadCacheInfoEntry 7 }

	srHotZoneReadCacheMinimumStayTime OBJECT-TYPE
		SYNTAX  DisplayString
		ACCESS  read-only
		STATUS  mandatory
		DESCRIPTION
			"The minimum time that how long a zone can stay at least in the HotZone before it is swapped out."
	::= { srHotZoneReadCacheInfoEntry 8 }

	srHotZoneReadCacheEachZoneSize OBJECT-TYPE
		SYNTAX  DisplayString
		ACCESS  read-only
		STATUS  mandatory
		DESCRIPTION
			"The size of each zone setting."
	::= { srHotZoneReadCacheInfoEntry 9 }

	srHotZoneReadCacheTotalZones OBJECT-TYPE
		SYNTAX  Counter32
		ACCESS  read-only
		STATUS  mandatory
		DESCRIPTION
			"The total zones that is allocated of the SAN resource."
	::= { srHotZoneReadCacheInfoEntry 10 }

	srHotZoneReadCacheUsedZones OBJECT-TYPE
		SYNTAX  Counter32
		ACCESS  read-only
		STATUS  mandatory
		DESCRIPTION
			"The current used zones of the SAN resource."
	::= { srHotZoneReadCacheInfoEntry 11 }

	srHotZoneReadCacheHitRatio OBJECT-TYPE
		SYNTAX  DisplayString
		ACCESS  read-only
		STATUS  mandatory
		DESCRIPTION
			"The hit ratio represents current HotZone read cache of the SAN resource."
	::= { srHotZoneReadCacheInfoEntry 12 }

	srHotZoneReadCacheTotalSizeQuantity OBJECT-TYPE
		SYNTAX  Counter32
		ACCESS  read-only
		STATUS  mandatory
		DESCRIPTION
			"The amount of device size quantity which is representing with megabyte unit of the HotZone read cache resource."
	::= { srHotZoneReadCacheInfoEntry 13 }

	srHotZoneReadCacheTotalSizeUnit OBJECT-TYPE
		SYNTAX  INTEGER
		ACCESS  read-only
		STATUS  mandatory
		DESCRIPTION
			"The amount of device size unit of the HotZone read cache resource. The size unit of the device. 0 presents KB. 1 presents MB. 2 presents GB. 3 presents TB."
	::= { srHotZoneReadCacheInfoEntry 14 }

	srHotZoneReadCacheTotalSize64 OBJECT-TYPE
		SYNTAX  Counter64
		ACCESS  read-only
		STATUS  mandatory
		DESCRIPTION
			"The amount of device size which is representing with megabyte unit of the HotZone read cache resource."
	::= { srHotZoneReadCacheInfoEntry 15 }

	srHotZoneReadCacheSANResourceName OBJECT-TYPE
		SYNTAX  DisplayString
		ACCESS  read-only
		STATUS  mandatory
		DESCRIPTION
			"The SANResource Name that assigned by IPStor server enables the HotZone ReadCache."
	::= { srHotZoneReadCacheInfoEntry 16 }



            
	nasResources OBJECT IDENTIFIER ::= { logicalResources 4 }

	numOfNASResources   OBJECT-TYPE
		SYNTAX  INTEGER
		ACCESS  read-only
		STATUS  mandatory
		DESCRIPTION
			"The amount of NAS resources are available by the IPStor server."
	::= { nasResources 1 }

	nasResourceTable    OBJECT-TYPE
		SYNTAX  SEQUENCE OF NASResource
		ACCESS	not-accessible
		STATUS	mandatory
		DESCRIPTION
			"A table containing the NAS resources information."
	::= { nasResources 2 }

	nasResourceEntry    OBJECT-TYPE
		SYNTAX	NASResource
		ACCESS	not-accessible
		STATUS	mandatory
		DESCRIPTION
			"Information about the configurations and properties of the logical NAS resources."
		INDEX { nasResourceID }
	::= { nasResourceTable 1 }

	NASResource ::= SEQUENCE {
		nasResourceID		        INTEGER,
	        nasResourceName 	        DisplayString,
		nrAllocationType	        DisplayString,
		nrTotalSectors			Counter32,
		nrTotalSize			Counter32,
--		nrCategory			DisplayString,
		nrConfigStatus			DisplayString,
		nrMountPath			DisplayString,
		nrStatus			DisplayString,
		nrMirrorSyncStatus		DisplayString,
		nrReplicaDevice			DisplayString,
		nrSnapshotCopyStatus		DisplayString,
--		nrPhysicalAllocLayoutTable	OBJECT IDENTIFIER,
--		nrShareInfoTable         	OBJECT IDENTIFIER,
--      nrSnapShotTable				OBJECT IDENTIFIER,
--      nrTimeMarkTable				OBJECT IDENTIFIER,
--      nrBackupTable				OBJECT IDENTIFIER,
--      nrReplicationTable			OBJECT IDENTIFIER,
--      nrCacheTable				OBJECT IDENTIFIER,
		nrWriteCacheProperty		DisplayString,
--                nrThinProvisionTable            OBJECT IDENTIFIER,
		nrTotalSizeQuantity		Counter32,
		nrTotalSizeUnit			INTEGER,
		nrTotalSectors64	        Counter64,
		nrTotalSize64                 	Counter64
	}

	nasResourceID   OBJECT-TYPE
		SYNTAX	INTEGER
		ACCESS	read-only
		STATUS	mandatory
		DESCRIPTION
			"The NAS resource ID assigned by the IPStor server."
	::= { nasResourceEntry 1 }
	
	nasResourceName OBJECT-TYPE
		SYNTAX	DisplayString
		ACCESS	read-only
		STATUS	mandatory
		DESCRIPTION
			"The NAS resource name created by the user."
	::= { nasResourceEntry 2 }    

	nrAllocationType    OBJECT-TYPE
		SYNTAX	DisplayString
		ACCESS	read-only
		STATUS	mandatory
		DESCRIPTION
			"It represents the resource type when user allocating the NAS device."
	::= { nasResourceEntry 3 }

	nrTotalSectors  OBJECT-TYPE
		SYNTAX	Counter32
		ACCESS	read-only
		STATUS	mandatory
		DESCRIPTION
			"The amount of sectors allocated by the NAS resource."
	::= { nasResourceEntry 4 }
	
	nrTotalSize OBJECT-TYPE
		SYNTAX	Counter32
		ACCESS	read-only
		STATUS	mandatory
		DESCRIPTION
			"The amount of device size which is representing with megabyte unit of the NAS resource."
	::= { nasResourceEntry 5 }

--	nrCategory  OBJECT-TYPE
--		SYNTAX	DisplayString
--		ACCESS	read-only
--		STATUS	mandatory
--		DESCRIPTION
--			"The category of NAS resource"
--	::= { nasResourceEntry 6 }

	nrConfigStatus  OBJECT-TYPE
		SYNTAX	DisplayString
		ACCESS	read-only
		STATUS	mandatory
		DESCRIPTION
			"It represents the attaching status of the NAS resource."
	::= { nasResourceEntry 6 }
	
	nrMountPath OBJECT-TYPE
		SYNTAX	DisplayString
		ACCESS	read-only
		STATUS	mandatory
		DESCRIPTION
			"The mounted path of the NAS resource."
	::= { nasResourceEntry 7 }

	nrStatus    OBJECT-TYPE
		SYNTAX	DisplayString
		ACCESS	read-only
		STATUS	mandatory
		DESCRIPTION
			"The status(attached and mounted) of the NAS resource."
	::= { nasResourceEntry 8 }
	
	nrMirrorSyncStatus  OBJECT-TYPE
		SYNTAX	DisplayString
		ACCESS	read-only
		STATUS	mandatory
		DESCRIPTION
			"It represents the mirror synchronization status of the NAS resource."
	::= { nasResourceEntry 9 }

	nrReplicaDevice OBJECT-TYPE
		SYNTAX	DisplayString
		ACCESS	read-only
		STATUS	mandatory
		DESCRIPTION
			"It represents the target replica server and device as the format <hostname of target>:<virtual device id>,
			 if the replication option is enabled of the NAS resource."
	::= { nasResourceEntry 10 }

	nrSnapshotCopyStatus    OBJECT-TYPE
		SYNTAX	DisplayString
		ACCESS	read-only
		STATUS	mandatory
		DESCRIPTION
			"The snapshot copy status of the NAS resource."
	::= { nasResourceEntry 11 }

	nrPhysicalAllocLayoutTable  OBJECT-TYPE
		SYNTAX  SEQUENCE OF NRPhysicalAllocLayout
		ACCESS	not-accessible
		STATUS	mandatory
		DESCRIPTION
			"A table containging the physical layout information for the NAS resources."
	::= { nasResourceEntry 12 }

	nrphysicalAllocLayoutEntry  OBJECT-TYPE
		SYNTAX  NRPhysicalAllocLayout
		ACCESS	not-accessible
		STATUS	mandatory
		DESCRIPTION
			"Information about the physical devices which are reserved and created by logical NAS resource."
		INDEX { nrpaNASResourceID }
	::= { nrPhysicalAllocLayoutTable 1 }

	NRPhysicalAllocLayout ::= SEQUENCE {
		nrpaNASResourceID   	INTEGER,
		nrpaNASResourceName	DisplayString,
		nrpaName		DisplayString,
		nrpaType 		DisplayString,
		nrpaAdapterNo		INTEGER,
		nrpaChannelNo		INTEGER,
		nrpaScsiID		INTEGER,
		nrpaLun			INTEGER,
		nrpaFirstSector		Counter32,
		nrpaLastSector		Counter32,
		nrpaSize		Counter32,
		nrpaSizeQuantity	Counter32,
		nrpaSizeUnit		INTEGER,
		nrpaFirstSector64	Counter64,
		nrpaLastSector64	Counter64,
		nrpaSize64		Counter64
	}

	nrpaNASResourceID   OBJECT-TYPE
		SYNTAX  INTEGER
		ACCESS	read-only
		STATUS	mandatory
		DESCRIPTION
			"The NAS resource ID assigned by the IPStor server."
	::= { nrphysicalAllocLayoutEntry 1 }

	nrpaNASResourceName OBJECT-TYPE
		SYNTAX	DisplayString
		ACCESS	read-only
		STATUS	mandatory
		DESCRIPTION
			"The NAS resource name created by the user."
	::= { nrphysicalAllocLayoutEntry 2 }

	nrpaName    OBJECT-TYPE
		SYNTAX	DisplayString
		ACCESS	read-only
		STATUS	mandatory
		DESCRIPTION
			"The physical device name."
	::= { nrphysicalAllocLayoutEntry 3 }
	
	nrpaType    OBJECT-TYPE
		SYNTAX	DisplayString
		ACCESS	read-only
		STATUS	mandatory
		DESCRIPTION
			"It represents the type(Primary, or Mirror) of the physical layout."
	::= { nrphysicalAllocLayoutEntry 4 }

	nrpaAdapterNo   OBJECT-TYPE
		SYNTAX  INTEGER
		ACCESS	read-only
		STATUS	mandatory
		DESCRIPTION
			"The SCSI adapter number of the physical device."
	::= { nrphysicalAllocLayoutEntry 5 }

	nrpaChannelNo   OBJECT-TYPE
		SYNTAX  INTEGER
		ACCESS	read-only
		STATUS	mandatory
		DESCRIPTION
			"The SCSI channel number of the physical device."
	::= { nrphysicalAllocLayoutEntry 6 }

	nrpaScsiID  OBJECT-TYPE
		SYNTAX  INTEGER
		ACCESS	read-only
		STATUS	mandatory
		DESCRIPTION
			"The SCSI ID of the physical device."
	::= { nrphysicalAllocLayoutEntry 7 }

	nrpaLun OBJECT-TYPE
		SYNTAX  INTEGER
		ACCESS	read-only
		STATUS	mandatory
		DESCRIPTION
			"The SCSI LUN number of the physical device."
	::= { nrphysicalAllocLayoutEntry 8 }

	nrpaFirstSector OBJECT-TYPE
		SYNTAX  Counter32
		ACCESS	read-only
		STATUS	mandatory
		DESCRIPTION
			"The first sector of the physical device which is allocated by the NAS resource."
	::= { nrphysicalAllocLayoutEntry 9 }

	nrpaLastSector  OBJECT-TYPE
		SYNTAX  Counter32
		ACCESS	read-only
		STATUS	mandatory
		DESCRIPTION
			"The last sector of the physical device which is allocated by the NAS resource."
	::= { nrphysicalAllocLayoutEntry 10 }
		
	nrpaSize    OBJECT-TYPE
		SYNTAX  Counter32
		ACCESS	read-only
		STATUS	mandatory
		DESCRIPTION
			"The amount of the allocated size which is representing with megabyte unit within a physical device."
	::= { nrphysicalAllocLayoutEntry 11 }
		
	nrpaSizeQuantity    OBJECT-TYPE
		SYNTAX  Counter32
		ACCESS	read-only
		STATUS	mandatory
		DESCRIPTION
			"The amount of the allocated size quantity within a physical device."
	::= { nrphysicalAllocLayoutEntry 12 }
		
	nrpaSizeUnit    OBJECT-TYPE
		SYNTAX  INTEGER
		ACCESS	read-only
		STATUS	mandatory
		DESCRIPTION
			"The amount of the allocated size unit within a physical device. 0 presents KB. 1 presents MB. 2 presents GB. 3 presents TB."
	::= { nrphysicalAllocLayoutEntry 13 }

	nrpaFirstSector64 OBJECT-TYPE
		SYNTAX  Counter64
		ACCESS	read-only
		STATUS	mandatory
		DESCRIPTION
			"The first sector of the physical device which is allocated by the NAS resource."
	::= { nrphysicalAllocLayoutEntry 14 }

	nrpaLastSector64  OBJECT-TYPE
		SYNTAX  Counter64
		ACCESS	read-only
		STATUS	mandatory
		DESCRIPTION
			"The last sector of the physical device which is allocated by the NAS resource."
	::= { nrphysicalAllocLayoutEntry 15 }
		
	nrpaSize64    OBJECT-TYPE
		SYNTAX  Counter64
		ACCESS	read-only
		STATUS	mandatory
		DESCRIPTION
			"The amount of the allocated size which is representing with megabyte unit within a physical device."
	::= { nrphysicalAllocLayoutEntry 16 }

	nrShareInfoTable    OBJECT-TYPE
		SYNTAX  SEQUENCE OF ShareInfo
		ACCESS	not-accessible
		STATUS	mandatory
		DESCRIPTION
			"A table containing share information of the NAS resource, which include Windows and NFS shares."
	::= { nasResourceEntry 13 }

	shareInfoEntry  OBJECT-TYPE
		SYNTAX  ShareInfo
		ACCESS	not-accessible
		STATUS	mandatory
		DESCRIPTION
			"Information about the configurations of the sharing NAS resource."
		INDEX { nrsiResourceID }
	::= { nrShareInfoTable 1 }

	ShareInfo ::= SEQUENCE {
		nrsiResourceID		INTEGER,
		nrsiResourceName	DisplayString,
		nrsiRealPath		DisplayString,
		nrsiFolderName		DisplayString,
		nrsiShareName		DisplayString,
		nrsiComment         DisplayString,
		nrsiUsedSpaceSize   INTEGER,
		nrsiMaxConn         INTEGER
--		nrsiMembersTable    OBJECT IDENTIFIER
	}

	nrsiResourceID  OBJECT-TYPE
		SYNTAX	INTEGER
		ACCESS	read-only
		STATUS	mandatory
		DESCRIPTION
			"The NAS resource ID assigned by the IPStor server."
	::= { shareInfoEntry 1 }

	nrsiResourceName    OBJECT-TYPE
		SYNTAX	DisplayString
		ACCESS	read-only
		STATUS	mandatory
		DESCRIPTION
			"The NAS resource name created by the user."
	::= { shareInfoEntry 2 }

	nrsiRealPath    OBJECT-TYPE
		SYNTAX	DisplayString
		ACCESS	read-only
		STATUS	mandatory
		DESCRIPTION
			"The sharing full path."
	::= { shareInfoEntry 3 }

	nrsiFolderName OBJECT-TYPE
		SYNTAX	DisplayString
		ACCESS	read-only
		STATUS	mandatory
		DESCRIPTION
			"The sharing folder name."
	::= { shareInfoEntry 4 }

	nrsiShareName   OBJECT-TYPE
		SYNTAX  DisplayString
		ACCESS	read-only
		STATUS	mandatory
		DESCRIPTION
			"The share name of the NAS resource."
	::= { shareInfoEntry 5 }

	nrsiComment OBJECT-TYPE
		SYNTAX  DisplayString
		ACCESS	read-only
		STATUS	mandatory
		DESCRIPTION
			"The comments setted by users of one share folder."
	::= { shareInfoEntry 6 }

	nrsiUsedSpaceSize OBJECT-TYPE
		SYNTAX  INTEGER
		ACCESS	read-only
		STATUS	mandatory
		DESCRIPTION
			"The current used size which is representing with kilobyte unit of one share folder."
	::= { shareInfoEntry 7 }

	nrsiMaxConn OBJECT-TYPE
		SYNTAX  INTEGER
		ACCESS	read-only
		STATUS	mandatory
		DESCRIPTION
			"The maximum connections of one share folder is allowed. If the value is 0, it means the unlimited connections"
	::= { shareInfoEntry 8 }

	nrsiMembersTable    OBJECT-TYPE
		SYNTAX  SEQUENCE OF MembersList
		ACCESS	not-accessible
		STATUS	mandatory
		DESCRIPTION
			"A table containing all members can access the share folder. If the authentication mode is share-mode, 
			 there is none clients listed due to all of them have the rights when the login password is correct."
	::= { shareInfoEntry 9 }

	membersListEntry    OBJECT-TYPE
		SYNTAX  MembersList
		ACCESS	not-accessible
		STATUS	mandatory
		DESCRIPTION
			"Information about the client types and sharing resources."
		INDEX { mlIndex }
	::= { nrsiMembersTable 1 }
	
	MembersList ::= SEQUENCE {
		mlIndex         INTEGER,
		mlResourceName  DisplayString,
		mlFolderName	DisplayString,
		mlClientName	DisplayString,
		mlType          DisplayString,
		mlAccessRight   DisplayString
	}

	mlIndex OBJECT-TYPE
		SYNTAX	INTEGER
		ACCESS	read-only
		STATUS	mandatory
		DESCRIPTION
			"The sequential digit number as a index key of the member list table."
	::= { membersListEntry 1 }
	
	mlResourceName  OBJECT-TYPE
		SYNTAX	DisplayString
		ACCESS	read-only
		STATUS	mandatory
		DESCRIPTION
			"The NAS resource name created by the user."
	::= { membersListEntry 2 }
	
	mlFolderName    OBJECT-TYPE
		SYNTAX	DisplayString
		ACCESS	read-only
		STATUS	mandatory
		DESCRIPTION
			"The sharing folder name."
	::= { membersListEntry 3 }
	
	mlClientName    OBJECT-TYPE
		SYNTAX	DisplayString
		ACCESS	read-only
		STATUS	mandatory
		DESCRIPTION
			"The client name that the folder is been assigned."
	::= { membersListEntry 4 }
	
	mlType  OBJECT-TYPE
		SYNTAX	DisplayString
		ACCESS	read-only
		STATUS	mandatory
		DESCRIPTION
			"Identify the client type(Windows user, Windows group, and NFS client) that the folder is been assigned."
	::= { membersListEntry 5 }

	mlAccessRight   OBJECT-TYPE
		SYNTAX	DisplayString
		ACCESS	read-only
		STATUS	mandatory
		DESCRIPTION
			"Identify the connecting and accessing status with a resource of the client."
	::= { membersListEntry 6 }	

    nrSnapShotTable OBJECT-TYPE
        SYNTAX  SEQUENCE OF NRSnapShotInfo
        ACCESS  not-accessible
        STATUS  mandatory
        DESCRIPTION
            "A table containing the snapshot resources created by the NAS resource."
    ::= { nasResourceEntry 14 }
    
    nrSnapShotInfoEntry OBJECT-TYPE
        SYNTAX  NRSnapShotInfo
        ACCESS  not-accessible
        STATUS  mandatory
        DESCRIPTION
            "Information about the policy and configuration of the snapshot function."
        INDEX { nrSnapShotResourceID }
    ::= { nrSnapShotTable 1 }

    NRSnapShotInfo ::= SEQUENCE {
        nrSnapShotResourceID    INTEGER,
        nrSnapShotResourceName  DisplayString,
        nrSnapShotOption        DisplayString,
        nrSnapShotSize          Counter32,
        nrSnapShotThreshold     INTEGER,
        nrSnapShotReachTH       DisplayString,
        nrSnapShotIncSize       DisplayString,
        nrSnapShotMaxSize       DisplayString,
        nrSnapShotResourceFull  DisplayString,
        nrSnapShotUsedSize      Counter32,
        nrSnapShotFreeSize      Counter32,
        nrSnapShotUsedPercent   INTEGER,
	nrSnapShotMicroscan             DisplayString,
        nrSnapShotSizeQuantity		Counter32,
        nrSnapShotSizeUnit		INTEGER,
        nrSnapShotUsedSizeQuantity	Counter32,
        nrSnapShotUsedSizeUnit		INTEGER,
        nrSnapShotFreeSizeQuantity	Counter32,
        nrSnapShotFreeSizeUnit		INTEGER,
        nrSnapShotIncSizeQuantity	Counter32,
        nrSnapShotIncSizeUnit		INTEGER,
        nrSnapShotMaxSizeQuantity	Counter32,
        nrSnapShotMaxSizeUnit		INTEGER,
        nrSnapShotOwnResourceID		INTEGER,
        nrSnapShotSize			Counter64,
        nrSnapShotIncSize		Counter64,
        nrSnapShotMaxSize		Counter64,
        nrSnapShotUsedSize		Counter64,
        nrSnapShotFreeSize		Counter64,
        nrSnapShotShrinkPolicy          DisplayString,
        nrSnapShotShrinkThreshold       DisplayString,
        nrSnapShotShrinkMinSize         DisplayString,
        nrSnapShotShrinkMinSizeQuantity Counter32,
        nrSnapShotShrinkMinSizeUnit     INTEGER,
        nrSnapShotShrinkMinSize64       Counter64,
        nrSnapShotResourceStatus	DisplayString
    }

    nrSnapShotResourceID    OBJECT-TYPE
        SYNTAX  INTEGER
        ACCESS  read-only
        STATUS  mandatory
        DESCRIPTION
            "The NAS resource ID assigned by the IPStor server."
    ::= { nrSnapShotInfoEntry 1 }

    nrSnapShotResourceName  OBJECT-TYPE
        SYNTAX  DisplayString
        ACCESS  read-only
        STATUS  mandatory
        DESCRIPTION
            "The NAS resource name created by the user."
    ::= { nrSnapShotInfoEntry 2 }
    
    nrSnapShotOption    OBJECT-TYPE
        SYNTAX  DisplayString
        ACCESS  read-only
        STATUS  mandatory
        DESCRIPTION
            "The status represents the snapshot option is enable or disable of the NAS resource."
    ::= { nrSnapShotInfoEntry 3 }

    nrSnapShotSize  OBJECT-TYPE
        SYNTAX  Counter32
        ACCESS  read-only
        STATUS  mandatory
        DESCRIPTION
            "The allocated size when creating the NAS resource at first time."
    ::= { nrSnapShotInfoEntry 4 }
    
    nrSnapShotThreshold OBJECT-TYPE
        SYNTAX  INTEGER
        ACCESS  read-only
        STATUS  mandatory
        DESCRIPTION
            "The value represents the threshold setting which is in percentage(%) format of the NAS resource."
    ::= { nrSnapShotInfoEntry 5 }

    nrSnapShotReachTH   OBJECT-TYPE
        SYNTAX  DisplayString
        ACCESS  read-only
        STATUS  mandatory
        DESCRIPTION
            "The policy is setting for expanding resource automatically or manually while reaching the threshold."
    ::= { nrSnapShotInfoEntry 6 }

    nrSnapShotIncSize   OBJECT-TYPE
        SYNTAX  DisplayString
        ACCESS  read-only
        STATUS  mandatory
        DESCRIPTION
            "The incremental size for each time when is running out the resource.  This is meaningful when expanding
             resource is automatically."
    ::= { nrSnapShotInfoEntry 7 }

    nrSnapShotMaxSize   OBJECT-TYPE
        SYNTAX  DisplayString
        ACCESS  read-only
        STATUS  mandatory
        DESCRIPTION
            "The maximum resource size which is represented in megabyte unit is allowed for allocating."
    ::= { nrSnapShotInfoEntry 8 }
    
    nrSnapShotResourceFull  OBJECT-TYPE
        SYNTAX  DisplayString
        ACCESS  read-only
        STATUS  mandatory
        DESCRIPTION
            "The policy sets to delete previous timemarks or stop to creating new timemarks when using the maximum resource size."
    ::= { nrSnapShotInfoEntry 9 }

    nrSnapShotUsedSize  OBJECT-TYPE
        SYNTAX  Counter32
        ACCESS  read-only
        STATUS  mandatory
        DESCRIPTION
            "The resource size which is representing in kilobyte unit have been used."
    ::= { nrSnapShotInfoEntry 10 }
    
    nrSnapShotFreeSize  OBJECT-TYPE
        SYNTAX  Counter32
        ACCESS  read-only
        STATUS  mandatory
        DESCRIPTION
            "The free resource size which is representing in megabyte unit before reaching the threshold."
    ::= { nrSnapShotInfoEntry 11 }

    nrSnapShotUsedPercent   OBJECT-TYPE
        SYNTAX  INTEGER
        ACCESS  read-only
        STATUS  mandatory
        DESCRIPTION
            "The percentage of the used resource size."
    ::= { nrSnapShotInfoEntry 12 }
    
    nrSnapShotMicroscan    OBJECT-TYPE
        SYNTAX  DisplayString
        ACCESS  read-only
        STATUS  mandatory
        DESCRIPTION
            "The status represents the snapshot Microscan option is enable or disable of the NAS resource."
    ::= { nrSnapShotInfoEntry 13 }

    nrSnapShotSizeQuantity  OBJECT-TYPE
        SYNTAX  Counter32
        ACCESS  read-only
        STATUS  mandatory
        DESCRIPTION
            "The allocated size quantity when creating the NAS resource at first time."
    ::= { nrSnapShotInfoEntry 14 }

    nrSnapShotSizeUnit  OBJECT-TYPE
        SYNTAX  INTEGER
        ACCESS  read-only
        STATUS  mandatory
        DESCRIPTION
            "The allocated size unit when creating the NAS resource at first time. 0 presents KB. 1 presents MB. 2 presents GB. 3 presents TB."
    ::= { nrSnapShotInfoEntry 15 }

    nrSnapShotUsedSizeQuantity  OBJECT-TYPE
        SYNTAX  Counter32
        ACCESS  read-only
        STATUS  mandatory
        DESCRIPTION
            "The resource size quantity have been used."
    ::= { nrSnapShotInfoEntry 16 }

    nrSnapShotUsedSizeUnit  OBJECT-TYPE
        SYNTAX  INTEGER
        ACCESS  read-only
        STATUS  mandatory
        DESCRIPTION
            "The resource size unit have been used. 0 presents KB. 1 presents MB. 2 presents GB. 3 presents TB."
    ::= { nrSnapShotInfoEntry 17 }
    
    nrSnapShotFreeSizeQuantity  OBJECT-TYPE
        SYNTAX  Counter32
        ACCESS  read-only
        STATUS  mandatory
        DESCRIPTION
            "The free resource size quantity before reaching the threshold."
    ::= { nrSnapShotInfoEntry 18 }
    
    nrSnapShotFreeSizeUnit  OBJECT-TYPE
        SYNTAX  INTEGER
        ACCESS  read-only
        STATUS  mandatory
        DESCRIPTION
            "The free resource size unit before reaching the threshold. 0 presents KB. 1 presents MB. 2 presents GB. 3 presents TB."
    ::= { nrSnapShotInfoEntry 19 }
    
    nrSnapShotIncSizeQuantity  OBJECT-TYPE
        SYNTAX  Counter32
        ACCESS  read-only
        STATUS  mandatory
        DESCRIPTION
            "The incremental size quantity for each time when is running out the resource.  This is meaningful when expanding
             resource is automatically."
    ::= { nrSnapShotInfoEntry 20 }
    
    nrSnapShotIncSizeUnit  OBJECT-TYPE
        SYNTAX  INTEGER
        ACCESS  read-only
        STATUS  mandatory
        DESCRIPTION
            "The incremental size unit for each time when is running out the resource.  This is meaningful when expanding resource is automatically. 0 presents KB. 1 presents MB. 2 presents GB. 3 presents TB."
    ::= { nrSnapShotInfoEntry 21 }
    
    nrSnapShotMaxSizeQuantity  OBJECT-TYPE
        SYNTAX  Counter32
        ACCESS  read-only
        STATUS  mandatory
        DESCRIPTION
            "The maximum resource size quantity which is represented in megabyte unit is allowed for allocating."
    ::= { nrSnapShotInfoEntry 22 }
    
    nrSnapShotMaxSizeUnit  OBJECT-TYPE
        SYNTAX  INTEGER
        ACCESS  read-only
        STATUS  mandatory
        DESCRIPTION
            "The maximum resource size unit which is represented in megabyte unit is allowed for allocating. 0 presents KB. 1 presents MB. 2 presents GB. 3 presents TB."
    ::= { nrSnapShotInfoEntry 23 }

    nrSnapShotOwnResourceID    OBJECT-TYPE
        SYNTAX  INTEGER
        ACCESS  read-only
        STATUS  mandatory
        DESCRIPTION
            "The SnapShot resource ID assigned by the IPStor server."
    ::= { nrSnapShotInfoEntry 24 }

    nrSnapShotSize64  OBJECT-TYPE
        SYNTAX  Counter64
        ACCESS  read-only
        STATUS  mandatory
        DESCRIPTION
            "The allocated size when creating the NAS resource at first time."
    ::= { nrSnapShotInfoEntry 25 }

    nrSnapShotIncSize64   OBJECT-TYPE
        SYNTAX  Counter64
        ACCESS  read-only
        STATUS  mandatory
        DESCRIPTION
            "The incremental size for each time when is running out the resource.  This is meaningful when expanding
             resource is automatically."
    ::= { nrSnapShotInfoEntry 26 }

    nrSnapShotMaxSize64   OBJECT-TYPE
        SYNTAX  Counter64
        ACCESS  read-only
        STATUS  mandatory
        DESCRIPTION
            "The maximum resource size which is represented in megabyte unit is allowed for allocating."
    ::= { nrSnapShotInfoEntry 27 }

    nrSnapShotUsedSize64  OBJECT-TYPE
        SYNTAX  Counter64
        ACCESS  read-only
        STATUS  mandatory
        DESCRIPTION
            "The resource size which is representing in kilobyte unit have been used."
    ::= { nrSnapShotInfoEntry 28 }
    
    nrSnapShotFreeSize64  OBJECT-TYPE
        SYNTAX  Counter64
        ACCESS  read-only
        STATUS  mandatory
        DESCRIPTION
            "The free resource size which is representing in megabyte unit before reaching the threshold."
    ::= { nrSnapShotInfoEntry 29 }

    nrSnapShotShrinkPolicy    OBJECT-TYPE
        SYNTAX  DisplayString
        ACCESS  read-only
        STATUS  mandatory
        DESCRIPTION
            "The status represents the snapshot Shrink option is enabled or
disabled of the SAN resource."
    ::= { nrSnapShotInfoEntry 30 }

    nrSnapShotShrinkThreshold    OBJECT-TYPE
        SYNTAX  DisplayString
        ACCESS  read-only
        STATUS  mandatory
        DESCRIPTION
            "The minimum disk space to shrink the snapshot resource of the SAN
resource."
    ::= { nrSnapShotInfoEntry 31 }

    nrSnapShotShrinkMinSize    OBJECT-TYPE
        SYNTAX  DisplayString
        ACCESS  read-only
        STATUS  mandatory
        DESCRIPTION
            "The minimum size for the snapshot resource to shrink."
    ::= { nrSnapShotInfoEntry 32 }

    nrSnapShotShrinkMinSizeQuantity  OBJECT-TYPE
        SYNTAX  Counter32
        ACCESS  read-only
        STATUS  mandatory
        DESCRIPTION
            "The minimum size quantity for the snapshot resource to shrink."
    ::= { nrSnapShotInfoEntry 33 }

    nrSnapShotShrinkMinSizeUnit  OBJECT-TYPE
        SYNTAX  INTEGER
        ACCESS  read-only
        STATUS  mandatory
        DESCRIPTION
            "The minimum size unit for the snapshot resource to shrink. 0 presents KB. 1 presents MB. 2 presents GB. 3 presents TB."
    ::= { nrSnapShotInfoEntry 34 }

    nrSnapShotShrinkMinSize64    OBJECT-TYPE
        SYNTAX  Counter64
        ACCESS  read-only
        STATUS  mandatory
        DESCRIPTION
            "The minimum size for the snapshot resource to shrink."
    ::= { nrSnapShotInfoEntry 35 }

    nrSnapShotResourceStatus   OBJECT-TYPE
        SYNTAX  DisplayString
        ACCESS  read-only
        STATUS  mandatory
        DESCRIPTION
            "The snapshot resource status of the NAS resouce."
    ::= { nrSnapShotInfoEntry 36 }

    nrTimeMarkTable OBJECT-TYPE
        SYNTAX  SEQUENCE OF NRTimeMarkInfo
        ACCESS  not-accessible
        STATUS  mandatory
        DESCRIPTION
            "A table containing the timamark resources created by the NAS resource."
    ::= { nasResourceEntry 15 }
    
    nrTimeMarkInfoEntry OBJECT-TYPE
        SYNTAX  NRTimeMarkInfo
        ACCESS  not-accessible
        STATUS  mandatory
        DESCRIPTION
            "Information about the policy and configuration of the timemark function."
        INDEX { nrTimeMarkResourceID }
    ::= { nrTimeMarkTable 1 }

    NRTimeMarkInfo ::= SEQUENCE {
        nrTimeMarkResourceID    INTEGER,
        nrTimeMarkResourceName  DisplayString,
        nrTimeMarkOption        DisplayString,
        nrTimeMarkCounts        INTEGER,
        nrTimeMarkSchedule      DisplayString,
        nrTimeMarkLastTimeStamp DisplayString,
        nrTimeMarkSnapshotImage DisplayString,
	nrTimeMarkSnapshotNotificationOption	DisplayString,
	nrTimeMarkReplicationOption		DisplayString
    }

    nrTimeMarkResourceID    OBJECT-TYPE
        SYNTAX  INTEGER
        ACCESS  read-only
        STATUS  mandatory
        DESCRIPTION
            "The NAS resource ID assigned by the IPStor server."
    ::= { nrTimeMarkInfoEntry 1 }

    nrTimeMarkResourceName  OBJECT-TYPE
        SYNTAX  DisplayString
        ACCESS  read-only
        STATUS  mandatory
        DESCRIPTION
            "The NAS resource name created by the user."
    ::= { nrTimeMarkInfoEntry 2 }
    
    nrTimeMarkOption    OBJECT-TYPE
        SYNTAX  DisplayString
        ACCESS  read-only
        STATUS  mandatory
        DESCRIPTION
            "The status represents the timemark option is enable or disable of the NAS resource."
    ::= { nrTimeMarkInfoEntry 3 }

    nrTimeMarkCounts    OBJECT-TYPE
        SYNTAX  INTEGER
        ACCESS  read-only
        STATUS  mandatory
        DESCRIPTION
            "The maximum timemarks that is allowed to create of the NAS resource."
    ::= { nrTimeMarkInfoEntry 4 }
    
    nrTimeMarkSchedule  OBJECT-TYPE
        SYNTAX  DisplayString
        ACCESS  read-only
        STATUS  mandatory
        DESCRIPTION
            "The time interval creates one new timemark."
    ::= { nrTimeMarkInfoEntry 5 }

    nrTimeMarkLastTimeStamp OBJECT-TYPE
        SYNTAX  DisplayString
        ACCESS  read-only
        STATUS  mandatory
        DESCRIPTION
            "The lately timestamp creates timemark."
    ::= { nrTimeMarkInfoEntry 6 }

    nrTimeMarkSnapshotImage OBJECT-TYPE
        SYNTAX  DisplayString
        ACCESS  read-only
        STATUS  mandatory
        DESCRIPTION
            "The time of each day creates snapshot-image automatically."
    ::= { nrTimeMarkInfoEntry 7 }

    nrTimeMarkSnapshotNotificationOption OBJECT-TYPE
        SYNTAX  DisplayString
        ACCESS  read-only
        STATUS  mandatory
        DESCRIPTION
            "The option of triggering snapshot notification schedule."
    ::= { nrTimeMarkInfoEntry 8 }

    nrTimeMarkReplicationOption OBJECT-TYPE
        SYNTAX  DisplayString
        ACCESS  read-only
        STATUS  mandatory
        DESCRIPTION
            "The replication option after the timemark is taken."
    ::= { nrTimeMarkInfoEntry 9 }

    nrBackupTable   OBJECT-TYPE
        SYNTAX  SEQUENCE OF NRBackupInfo
        ACCESS  not-accessible
        STATUS  mandatory
        DESCRIPTION
            "A table containing the backup resources created by the NAS resource."
    ::= { nasResourceEntry 16 }
    
    nrBackupInfoEntry   OBJECT-TYPE
        SYNTAX  NRBackupInfo
        ACCESS  not-accessible
        STATUS  mandatory
        DESCRIPTION
            "Information about the policy and configuration of the backup function."
        INDEX { nrBackupResourceID }
    ::= { nrBackupTable 1 }

    NRBackupInfo ::= SEQUENCE {
        nrBackupResourceID      INTEGER,
        nrBackupResourceName    DisplayString,
        nrBackupOption          DisplayString,
        nrBackupWindow          DisplayString,
        nrBackupSessionLen      DisplayString,
        nrBackupRelativeTime    DisplayString,
        nrBackupWaitTime        INTEGER,
        nrBackupSelectCriteria  DisplayString,
	nrBackupRawDeviceName	DisplayString
    }

    nrBackupResourceID  OBJECT-TYPE
        SYNTAX  INTEGER
        ACCESS  read-only
        STATUS  mandatory
        DESCRIPTION
            "The NAS resource ID assigned by the IPStor server."
    ::= { nrBackupInfoEntry 1 }

    nrBackupResourceName    OBJECT-TYPE
        SYNTAX  DisplayString
        ACCESS  read-only
        STATUS  mandatory
        DESCRIPTION
            "The NAS resource name created by the user."
    ::= { nrBackupInfoEntry 2 }
    
    nrBackupOption  OBJECT-TYPE
        SYNTAX  DisplayString
        ACCESS  read-only
        STATUS  mandatory
        DESCRIPTION
            "The status represents the backup option is enable or disable of the NAS resource."
    ::= { nrBackupInfoEntry 3 }

    nrBackupWindow  OBJECT-TYPE
        SYNTAX  DisplayString
        ACCESS  read-only
        STATUS  mandatory
        DESCRIPTION
            "The daytime allows for opening one backup sesion."
    ::= { nrBackupInfoEntry 4 }
    
    nrBackupSessionLen  OBJECT-TYPE
        SYNTAX  DisplayString
        ACCESS  read-only
        STATUS  mandatory
        DESCRIPTION
            "The time interval allows for one backup session in each time."
    ::= { nrBackupInfoEntry 5 }

    nrBackupRelativeTime    OBJECT-TYPE
        SYNTAX  DisplayString
        ACCESS  read-only
        STATUS  mandatory
        DESCRIPTION
            "The time interval waits before closing the backup session which is in inactivity status."
    ::= { nrBackupInfoEntry 6 }
    
    nrBackupWaitTime    OBJECT-TYPE
        SYNTAX  INTEGER
        ACCESS  read-only
        STATUS  mandatory
        DESCRIPTION
            "The time interval which is represnting in minute unit waits before closing the backup session after completion."
    ::= { nrBackupInfoEntry 7 }

    nrBackupSelectCriteria  OBJECT-TYPE
        SYNTAX  DisplayString
        ACCESS  read-only
        STATUS  mandatory
        DESCRIPTION
            "The snapshot image selection criteria that could be new or latest for the backup session.
             New represents that it always creates new snapshot image for backup, and 
             Latest represents that it uses the last created snapshot image for backup."
    ::= { nrBackupInfoEntry 8 }

    nrBackupRawDeviceName    OBJECT-TYPE
        SYNTAX  DisplayString
        ACCESS  read-only
        STATUS  mandatory
        DESCRIPTION
            "The NAS Backup Resource Raw Device Name created by the user."
    ::= { nrBackupInfoEntry 9 }
    
    nrReplicationTable  OBJECT-TYPE
        SYNTAX  SEQUENCE OF NRReplicationInfo
        ACCESS  not-accessible
        STATUS  mandatory
        DESCRIPTION
            "A table containing the replication resources created by the NAS resource."
    ::= { nasResourceEntry 17 }
    
    nrReplicaInfoEntry  OBJECT-TYPE
        SYNTAX  NRReplicationInfo
        ACCESS  not-accessible
        STATUS  mandatory
        DESCRIPTION
            "Information about the policy and configuration of the replication function."
        INDEX { nrReplicationResourceID }
    ::= { nrReplicationTable 1 }

    NRReplicationInfo ::= SEQUENCE {
        nrReplicationResourceID     INTEGER,
        nrReplicationResourceName   DisplayString,
        nrReplicationOption         DisplayString,
        nrReplicaServer             DisplayString,
        nrReplicaDeviceID           INTEGER,
        nrReplicaSchedule           DisplayString,
        nrReplicaWatermark          DisplayString,
        nrReplicaWatermarkRetry     INTEGER,
        nrReplicaTime               DisplayString,
        nrReplicaInterval           DisplayString,
        nrReplicationContinuousMode             DisplayString,
        nrReplicationCreatePrimaryTimeMark      DisplayString,
        nrReplicaSyncTimeMark                   DisplayString,
        nrReplicationProtocol                   DisplayString,
        nrReplicationCompression                DisplayString,
        nrReplicationEncryption                 DisplayString,
        nrReplicationMicroscan                  DisplayString,
        nrReplicationSyncPriority               DisplayString,
        nrReplicationStatus                     DisplayString,
        nrReplicationMode                       DisplayString,
        nrReplicationContinuousResourceID       INTEGER,
        nrReplicationContinuousResourceUsage    DisplayString,
        nrReplicationDeltaData                  DisplayString,
        nrReplicationUseExistTM                 DisplayString,
        nrReplicationPreserveTM                 DisplayString,
	nrReplicaLastSuccessfulSyncTime         DisplayString,
	nrReplicaAverageThroughput		Counter32,
	nrReplicaAverageThroughputQuantity	Counter32,
	nrReplicaAverageThroughputUnit		INTEGER
    }

    nrReplicationResourceID OBJECT-TYPE
        SYNTAX  INTEGER
        ACCESS  read-only
        STATUS  mandatory
        DESCRIPTION
            "The NAS resource ID assigned by the IPStor server."
    ::= { nrReplicaInfoEntry 1 }

    nrReplicationResourceName   OBJECT-TYPE
        SYNTAX  DisplayString
        ACCESS  read-only
        STATUS  mandatory
        DESCRIPTION
            "The NAS resource name created by the user."
    ::= { nrReplicaInfoEntry 2 }
    
    nrReplicationOption OBJECT-TYPE
        SYNTAX  DisplayString
        ACCESS  read-only
        STATUS  mandatory
        DESCRIPTION
            "The status represents the replication option is enable or disable of the NAS resource."
    ::= { nrReplicaInfoEntry 3 }

    nrReplicaServer OBJECT-TYPE
        SYNTAX  DisplayString
        ACCESS  read-only
        STATUS  mandatory
        DESCRIPTION
            "The target replia server name."
    ::= { nrReplicaInfoEntry 4 }
    
    nrReplicaDeviceID   OBJECT-TYPE
        SYNTAX  INTEGER
        ACCESS  read-only
        STATUS  mandatory
        DESCRIPTION
            "The target replica device ID."
    ::= { nrReplicaInfoEntry 5 }

    nrReplicaSchedule   OBJECT-TYPE
        SYNTAX  DisplayString
        ACCESS  read-only
        STATUS  mandatory
        DESCRIPTION
            "The state of the replication schedule, which is Suspended, On Schedule if existed replica server."
    ::= { nrReplicaInfoEntry 6 }
    
    nrReplicaWatermark  OBJECT-TYPE
        SYNTAX  DisplayString
        ACCESS  read-only
        STATUS  mandatory
        DESCRIPTION
            "The watermark sets to generate one new replication automatically."
    ::= { nrReplicaInfoEntry 7 }

    nrReplicaWatermarkRetry OBJECT-TYPE
        SYNTAX  INTEGER
        ACCESS  read-only
        STATUS  mandatory
        DESCRIPTION
            "The retry interval which is representing in minute unit if the replication failed."
    ::= { nrReplicaInfoEntry 8 }
    
    nrReplicaTime   OBJECT-TYPE
        SYNTAX  DisplayString
        ACCESS  read-only
        STATUS  mandatory
        DESCRIPTION
            "The daytime of each day creates one new replication."
    ::= { nrReplicaInfoEntry 9 }
    
    nrReplicaInterval   OBJECT-TYPE
        SYNTAX  DisplayString
        ACCESS  read-only
        STATUS  mandatory
        DESCRIPTION
            "The time interval creates one new replication."
    ::= { nrReplicaInfoEntry 10 }

    nrReplicationContinuousMode   OBJECT-TYPE
        SYNTAX  DisplayString
        ACCESS  read-only
        STATUS  mandatory
        DESCRIPTION
            "The status represents the Continuous Mode of Replication is enable or disable."
    ::= { nrReplicaInfoEntry 11 }

    nrReplicationCreatePrimaryTimeMark    OBJECT-TYPE
        SYNTAX  DisplayString
        ACCESS  read-only
        STATUS  mandatory
        DESCRIPTION
            "This option allows to create the primary TimeMark when a replica TimeMark is created."
    ::= { nrReplicaInfoEntry 12 }

    nrReplicaSyncTimeMark    OBJECT-TYPE
        SYNTAX  DisplayString
        ACCESS  read-only
        STATUS  mandatory
        DESCRIPTION
            "This option allows to synchronize the replica TimeMark when a primary TimeMark is created."
    ::= { nrReplicaInfoEntry 13 }

    nrReplicationProtocol    OBJECT-TYPE
        SYNTAX  DisplayString
        ACCESS  read-only
        STATUS  mandatory
        DESCRIPTION
            "It states the Protocol which Replication uses."
    ::= { nrReplicaInfoEntry 14 }

    nrReplicationCompression    OBJECT-TYPE
        SYNTAX  DisplayString
        ACCESS  read-only
        STATUS  mandatory
        DESCRIPTION
            "The status represents the Compression option is enable or disable of Replication."
    ::= { nrReplicaInfoEntry 15 }

    nrReplicationEncryption    OBJECT-TYPE
        SYNTAX  DisplayString
        ACCESS  read-only
        STATUS  mandatory
        DESCRIPTION
            "The status represents the Encryption option is enable or disable of Replication."
    ::= { nrReplicaInfoEntry 16 }

    nrReplicationMicroscan    OBJECT-TYPE
        SYNTAX  DisplayString
        ACCESS  read-only
        STATUS  mandatory
        DESCRIPTION
            "The status represents the Microscan option is enable or disable of Replication."
    ::= { nrReplicaInfoEntry 17 }

    nrReplicationSyncPriority    OBJECT-TYPE
        SYNTAX  DisplayString
        ACCESS  read-only
        STATUS  mandatory
        DESCRIPTION
            "The Priority setting when Replication Synchronize of the NAS resource."
    ::= { nrReplicaInfoEntry 18 }

    nrReplicationStatus    OBJECT-TYPE
        SYNTAX  DisplayString
        ACCESS  read-only
        STATUS  mandatory
        DESCRIPTION
            "The Replication status of the NAS resource."
    ::= { nrReplicaInfoEntry 19 }

    nrReplicationMode    OBJECT-TYPE
        SYNTAX  DisplayString
        ACCESS  read-only
        STATUS  mandatory
        DESCRIPTION
            "The Replication mode of the NAS resource."
    ::= { nrReplicaInfoEntry 20 }

    nrReplicationContinuousResourceID    OBJECT-TYPE
        SYNTAX  INTEGER
        ACCESS  read-only
        STATUS  mandatory
        DESCRIPTION
            "The Continuous Replication Resource ID of the NAS resource."
    ::= { nrReplicaInfoEntry 21 }

    nrReplicationContinuousResourceUsage    OBJECT-TYPE
        SYNTAX  DisplayString
        ACCESS  read-only
        STATUS  mandatory
        DESCRIPTION
            "The Continuous Replication Resource Usage of the NAS resource."
    ::= { nrReplicaInfoEntry 22 }

    nrReplicationDeltaData    OBJECT-TYPE
        SYNTAX  DisplayString
        ACCESS  read-only
        STATUS  mandatory
        DESCRIPTION
            "The Accumulated Delta Data of replication of the NAS resource."
    ::= { nrReplicaInfoEntry 23 }

    nrReplicationUseExistTM    OBJECT-TYPE
        SYNTAX  DisplayString
        ACCESS  read-only
        STATUS  mandatory
        DESCRIPTION
            "When Continuous Mode is disabled, the option about using existing TimeMark of the replication."
    ::= { nrReplicaInfoEntry 24 }

    nrReplicationPreserveTM    OBJECT-TYPE
        SYNTAX  DisplayString
        ACCESS  read-only
        STATUS  mandatory
        DESCRIPTION
            "When Continuous Mode is disabled, the option about perserving TimeMark of the replication."
    ::= { nrReplicaInfoEntry 25 }

    nrReplicaLastSuccessfulSyncTime   OBJECT-TYPE
        SYNTAX  DisplayString
        ACCESS  read-only
        STATUS  mandatory
        DESCRIPTION
            "The last successful synchronize time of the replication."
    ::= { nrReplicaInfoEntry 26 }
    
    nrReplicaAverageThroughput   OBJECT-TYPE
        SYNTAX  Counter32
        ACCESS  read-only
        STATUS  mandatory
        DESCRIPTION
            "The average throughput (MB/s) of the replication."
    ::= { nrReplicaInfoEntry 27 }

    nrReplicaAverageThroughputQuantity  OBJECT-TYPE
        SYNTAX  Counter32
        ACCESS  read-only
        STATUS  mandatory
        DESCRIPTION
            "The average throughput quantity of the replication."
    ::= { nrReplicaInfoEntry 28 }

    nrReplicaAverageThroughputUnit  OBJECT-TYPE
        SYNTAX  INTEGER
        ACCESS  read-only
        STATUS  mandatory
        DESCRIPTION
            "The average throughput unit of the replication. 0 presents KB. 1 presents MB. 2 presents GB. 3 presents TB."
    ::= { nrReplicaInfoEntry 29 }

    nrCacheTable    OBJECT-TYPE
        SYNTAX  SEQUENCE OF NRCacheInfo
        ACCESS  not-accessible
        STATUS  mandatory
        DESCRIPTION
            "A table containing the cache resource created by the NAS device."
    ::= { nasResourceEntry 18 }
    
    nrCacheInfoEntry    OBJECT-TYPE
        SYNTAX  NRCacheInfo
        ACCESS  not-accessible
        STATUS  mandatory
        DESCRIPTION
            "Information about the configuration and usage of the cache resource."
        INDEX { nrCacheResourceID }
    ::= { nrCacheTable 1 }

    NRCacheInfo ::= SEQUENCE {
        nrCacheResourceID   INTEGER,
        nrCacheResourceName DisplayString,
        nrCacheOption       DisplayString,
        nrCacheSuspend      DisplayString,
        nrCacheTotalSize    Counter32,
        nrCacheFreeSize     Counter32,
        nrCacheUsage        INTEGER,
        nrCacheThreshold    INTEGER,
        nrCacheFlushTime    INTEGER,
        nrCacheFlushCommand		INTEGER,
        nrCacheSkipWriteCommands	DisplayString,
        nrCacheFlushSpeed		INTEGER,
        nrCacheTotalSizeQuantity	Counter32,
        nrCacheTotalSizeUnit		INTEGER,
        nrCacheFreeSizeQuantity		Counter32,
        nrCacheFreeSizeUnit		INTEGER,
        nrCacheOwnResourceID		INTEGER,
        nrCacheTotalSize64		Counter64,
        nrCacheFreeSize64		Counter64,
	nrCacheStatus			DisplayString
    }

    nrCacheResourceID   OBJECT-TYPE
        SYNTAX  INTEGER
        ACCESS  read-only
        STATUS  mandatory
        DESCRIPTION
            "The NAS resource ID assigned by the IPStor server."
    ::= { nrCacheInfoEntry 1 }

    nrCacheResourceName OBJECT-TYPE
        SYNTAX  DisplayString
        ACCESS  read-only
        STATUS  mandatory
        DESCRIPTION
            "The NAS resource name created by the user."
    ::= { nrCacheInfoEntry 2 }
    
    nrCacheOption   OBJECT-TYPE
        SYNTAX  DisplayString
        ACCESS  read-only
        STATUS  mandatory
        DESCRIPTION
            "The status represents the cache option is enable or disable of the NAS resource."
    ::= { nrCacheInfoEntry 3 }
    
    nrCacheSuspend  OBJECT-TYPE
        SYNTAX  DisplayString
        ACCESS  read-only
        STATUS  mandatory
        DESCRIPTION
            "The cache resource is currently suspended or not."
    ::= { nrCacheInfoEntry 4 }
    
    nrCacheTotalSize    OBJECT-TYPE
        SYNTAX  Counter32
        ACCESS  read-only
        STATUS  mandatory
        DESCRIPTION
            "The allocated size when creating the cache resource."
    ::= { nrCacheInfoEntry 5 }
    
    nrCacheFreeSize OBJECT-TYPE
        SYNTAX  Counter32
        ACCESS  read-only
        STATUS  mandatory
        DESCRIPTION
            "The free resource size which is representing in megabyte unit before reaching the maximum resource size."
    ::= { nrCacheInfoEntry 6 }

    nrCacheUsage    OBJECT-TYPE
        SYNTAX  INTEGER
        ACCESS  read-only
        STATUS  mandatory
        DESCRIPTION
            "The percentage of the used resource size."
    ::= { nrCacheInfoEntry 7 }

    nrCacheThreshold    OBJECT-TYPE
        SYNTAX  INTEGER
        ACCESS  read-only
        STATUS  mandatory
        DESCRIPTION
            "The data needs to be in the cache before beginning flushing the cache."
    ::= { nrCacheInfoEntry 8 }
    
    nrCacheFlushTime    OBJECT-TYPE
        SYNTAX  INTEGER
        ACCESS  read-only
        STATUS  mandatory
        DESCRIPTION
            "The number of milliseconds before cache begins to flush when below the data threshold level."
    ::= { nrCacheInfoEntry 9 }
    
    nrCacheFlushCommand OBJECT-TYPE
        SYNTAX  INTEGER
        ACCESS  read-only
        STATUS  mandatory
        DESCRIPTION
            "The outstanding commands will be sent at one time during the flush process."
    ::= { nrCacheInfoEntry 10 }
    
    nrCacheSkipWriteCommands    OBJECT-TYPE
        SYNTAX  DisplayString
        ACCESS  read-only
        STATUS  mandatory
        DESCRIPTION
            "This option allows the system to skip multiple pending write commands targeted for the same block."
    ::= { nrCacheInfoEntry 11 }
    
    nrCacheFlushSpeed OBJECT-TYPE
        SYNTAX  INTEGER
        ACCESS  read-only
        STATUS  mandatory
        DESCRIPTION
            "The flush speed will be sent at one time during the flush process."
    ::= { nrCacheInfoEntry 12 }
    
    nrCacheTotalSizeQuantity    OBJECT-TYPE
        SYNTAX  Counter32
        ACCESS  read-only
        STATUS  mandatory
        DESCRIPTION
            "The allocated size quantity when creating the cache resource."
    ::= { nrCacheInfoEntry 13 }
    
    nrCacheTotalSizeUnit    OBJECT-TYPE
        SYNTAX  INTEGER
        ACCESS  read-only
        STATUS  mandatory
        DESCRIPTION
            "The allocated size unit when creating the cache resource. 0
presents KB. 1 presents MB. 2 presents GB. 3 presents TB."
    ::= { nrCacheInfoEntry 14 }
    
    nrCacheFreeSizeQuantity OBJECT-TYPE
        SYNTAX  Counter32
        ACCESS  read-only
        STATUS  mandatory
        DESCRIPTION
            "The free resource size quantity before reaching the maximum resource size."
    ::= { nrCacheInfoEntry 15 }
    
    nrCacheFreeSizeUnit OBJECT-TYPE
        SYNTAX  INTEGER
        ACCESS  read-only
        STATUS  mandatory
        DESCRIPTION
            "The free resource size unit before reaching the maximum resource size. 0 presents KB. 1 presents MB. 2 presents GB. 3 presents TB."
    ::= { nrCacheInfoEntry 16 }

    nrCacheOwnResourceID   OBJECT-TYPE
        SYNTAX  INTEGER
        ACCESS  read-only
        STATUS  mandatory
        DESCRIPTION
            "The Cache resource ID assigned by the IPStor server."
    ::= { nrCacheInfoEntry 17 }
    
    nrCacheTotalSize64    OBJECT-TYPE
        SYNTAX  Counter64
        ACCESS  read-only
        STATUS  mandatory
        DESCRIPTION
            "The allocated size when creating the cache resource."
    ::= { nrCacheInfoEntry 18 }
    
    nrCacheFreeSize64 OBJECT-TYPE
        SYNTAX  Counter64
        ACCESS  read-only
        STATUS  mandatory
        DESCRIPTION
            "The free resource size which is representing in megabyte unit before reaching the maximum resource size."
    ::= { nrCacheInfoEntry 19 }
    
    nrCacheStatus    OBJECT-TYPE
        SYNTAX  DisplayString
        ACCESS  read-only
        STATUS  mandatory
        DESCRIPTION
            "The current safecache device's status of the NAS resource."
    ::= { nrCacheInfoEntry 20 }
    
    nrWriteCacheProperty    OBJECT-TYPE
		SYNTAX  DisplayString
		ACCESS  read-only
		STATUS  mandatory
		DESCRIPTION
			"The property represents the write cache is enabled or disabled of the NAS resource."
	::= { nasResourceEntry 19 }
	
    nrMirrorTable OBJECT IDENTIFIER ::= { nasResourceEntry 20 }

    nrMirrorInfoEntry    OBJECT-TYPE
        SYNTAX  NRMirrorInfo
        ACCESS  not-accessible
        STATUS  mandatory
        DESCRIPTION
            "Information about the configuration and usage of the mirror."
        INDEX { nrMirrorResourceID }
    ::= { nrMirrorTable 1 }

    NRMirrorInfo ::= SEQUENCE {
        nrMirrorResourceID                      INTEGER,
        nrMirrorType                            DisplayString,
        nrMirrorSyncPriority                    INTEGER,
        nrMirrorSuspended                       DisplayString,
        nrMirrorThrottle                        INTEGER,
        nrMirrorHealthMonitoringOption          DisplayString,
        nrMirrorHealthCheckInterval             INTEGER,
        nrMirrorMaxLagTime                      INTEGER,
        nrMirrorSuspendThPercent                INTEGER,
        nrMirrorSuspendThIOnum                  INTEGER,
        nrMirrorSyncRetryPolicy                 DisplayString,
        nrMirrorSyncRetryInterval               DisplayString,
        nrMirrorSyncRetryActivity               DisplayString,
        nrMirrorSyncRetryTimes                  INTEGER,
--        nrMirrorThroughputControlOption         DisplayString,
--        nrMirrorThroughputCheckTime             DisplayString,
--        nrMirrorThroughputCheckInterval         DisplayString,
--        nrMirrorThroughputResumeSyncflow        DisplayString,
--        nrMirrorThroughputResumeSyncIO          INTEGER,
--        nrMirrorThroughputCheckRetry            INTEGER
	nrMirrorSynchronizationStatus		DisplayString,
	nrMirrorAlterReadMirror			DisplayString,
	nrMirrorAverageThroughput		Counter32,
	nrMirrorAverageThroughputQuantity	Counter32,
	nrMirrorAverageThroughputUnit		INTEGER,
	nrMirrorNASResourceName			DisplayString
    }

    nrMirrorResourceID   OBJECT-TYPE
        SYNTAX  INTEGER
        ACCESS  read-only
        STATUS  mandatory
        DESCRIPTION
            "The NAS resource ID that enables the mirror property."
    ::= { nrMirrorInfoEntry 1 }

    nrMirrorType   OBJECT-TYPE
        SYNTAX  DisplayString
        ACCESS  read-only
        STATUS  mandatory
        DESCRIPTION
            "The mirror type when a NAS resource enable the mirror property."
    ::= { nrMirrorInfoEntry 2 }

    nrMirrorSyncPriority   OBJECT-TYPE
        SYNTAX  INTEGER
        ACCESS  read-only
        STATUS  mandatory
        DESCRIPTION
            "The mirror synchronization priority when a NAS resource enable
the mirror property."
    ::= { nrMirrorInfoEntry 3 }

    nrMirrorSuspended   OBJECT-TYPE
        SYNTAX  DisplayString
        ACCESS  read-only
        STATUS  mandatory
        DESCRIPTION
            "Whether the mirror is suspended."
    ::= { nrMirrorInfoEntry 4 }

    nrMirrorThrottle   OBJECT-TYPE
        SYNTAX  INTEGER
        ACCESS  read-only
        STATUS  mandatory
        DESCRIPTION
            "The mirror throttle value for NAS resource."
    ::= { nrMirrorInfoEntry 5 }

    nrMirrorHealthMonitoringOption   OBJECT-TYPE
        SYNTAX  DisplayString
        ACCESS  read-only
        STATUS  mandatory
        DESCRIPTION
            "The status represents the mirror health monitoring option is enable or disable."
    ::= { nrMirrorInfoEntry 6 }

    nrMirrorHealthCheckInterval   OBJECT-TYPE
        SYNTAX  INTEGER
        ACCESS  read-only
        STATUS  mandatory
        DESCRIPTION
            "The Interval to Check and report mirror health status."
    ::= { nrMirrorInfoEntry 7 }

    nrMirrorMaxLagTime   OBJECT-TYPE
        SYNTAX  INTEGER
        ACCESS  read-only
        STATUS  mandatory
        DESCRIPTION
            "The Maximum acceptable lagging time for the mirror I/O's."
    ::= { nrMirrorInfoEntry 8 }

    nrMirrorSuspendThPercent   OBJECT-TYPE
        SYNTAX  INTEGER
        ACCESS  read-only
        STATUS  mandatory
        DESCRIPTION
            "Suspended mirroring when the threshold of failure reaches the percentage of the failure conditions."
    ::= { nrMirrorInfoEntry 9 }

    nrMirrorSuspendThIOnum   OBJECT-TYPE
        SYNTAX  INTEGER
        ACCESS  read-only
        STATUS  mandatory
        DESCRIPTION
            "Suspended mirroring when the outstanding IOs is greater than or equals to."
    ::= { nrMirrorInfoEntry 10 }

    nrMirrorSyncRetryPolicy   OBJECT-TYPE
        SYNTAX  DisplayString
        ACCESS  read-only
        STATUS  mandatory
        DESCRIPTION
            "The status represents the mirror synchronization retry policy is enable or not."
    ::= { nrMirrorInfoEntry 11 }

    nrMirrorSyncRetryInterval   OBJECT-TYPE
        SYNTAX  DisplayString
        ACCESS  read-only
        STATUS  mandatory
        DESCRIPTION
            "The mirror synchronization retry at specified interval."
    ::= { nrMirrorInfoEntry 12 }

    nrMirrorSyncRetryActivity   OBJECT-TYPE
        SYNTAX  DisplayString
        ACCESS  read-only
        STATUS  mandatory
        DESCRIPTION
            "The mirror synchronization retry when I/O activity is below or at."
    ::= { nrMirrorInfoEntry 13 }

    nrMirrorSyncRetryTimes   OBJECT-TYPE
        SYNTAX  INTEGER
        ACCESS  read-only
        STATUS  mandatory
        DESCRIPTION
            "The maximum mirror synchronization retry times."
    ::= { nrMirrorInfoEntry 14 }

--    nrMirrorThroughputControlOption   OBJECT-TYPE
--        SYNTAX  DisplayString
--        ACCESS  read-only
--        STATUS  mandatory
--        DESCRIPTION
--            "The status represents the mirror throughput control option is enable or not."
--    ::= { nrMirrorInfoEntry 15 }

--    nrMirrorThroughputCheckTime   OBJECT-TYPE
--        SYNTAX  DisplayString
--        ACCESS  read-only
--        STATUS  mandatory
--        DESCRIPTION
--            "The time to check mirror resource throughput after synchronization in progress."
--    ::= { nrMirrorInfoEntry 16 }

--    nrMirrorThroughputCheckInterval   OBJECT-TYPE
--        SYNTAX  DisplayString
--        ACCESS  read-only
--        STATUS  mandatory
--        DESCRIPTION
--            "Check mirror resource throughput at the specified interval."
--    ::= { nrMirrorInfoEntry 17 }

--    nrMirrorThroughputResumeSyncflow   OBJECT-TYPE
--        SYNTAX  DisplayString
--        ACCESS  read-only
--        STATUS  mandatory
--        DESCRIPTION
--            "Resume synchronization when I/Os per second activity is less than or equal to."
--    ::= { nrMirrorInfoEntry 18 }

--    nrMirrorThroughputResumeSyncIO   OBJECT-TYPE
--        SYNTAX  INTEGER
--        ACCESS  read-only
--        STATUS  mandatory
--        DESCRIPTION
--            "Resume synchronization when numbers of I/Os activity is less than or equal to."
--    ::= { nrMirrorInfoEntry 19 }

--    nrMirrorThroughputCheckRetry   OBJECT-TYPE
--        SYNTAX  INTEGER
--        ACCESS  read-only
--        STATUS  mandatory
--        DESCRIPTION
--            "Number of checking attempts before resuming synchronization."
--    ::= { nrMirrorInfoEntry 20 }
	
    nrMirrorSynchronizationStatus  OBJECT-TYPE
	SYNTAX	DisplayString
	ACCESS	read-only
	STATUS	mandatory
	DESCRIPTION
		"It represents the mirror synchronization status of the NAS resource."
    ::= { nrMirrorInfoEntry 21 }
	
    nrMirrorAlterReadMirror  OBJECT-TYPE
	SYNTAX	DisplayString
	ACCESS	read-only
	STATUS	mandatory
	DESCRIPTION
		"It represents the alternative read mirror option of the NAS resource."
    ::= { nrMirrorInfoEntry 22 }
    
    nrMirrorAverageThroughput   OBJECT-TYPE
        SYNTAX  Counter32
        ACCESS  read-only
        STATUS  mandatory
        DESCRIPTION
            "The average throughput (MB/s) of the mirror synchronization operation."
    ::= { nrMirrorInfoEntry 23 }

    nrMirrorAverageThroughputQuantity  OBJECT-TYPE
        SYNTAX  Counter32
        ACCESS  read-only
        STATUS  mandatory
        DESCRIPTION
            "The average throughput quantity of the mirror synchronization operation."
    ::= { nrMirrorInfoEntry 24 }

    nrMirrorAverageThroughputUnit  OBJECT-TYPE
        SYNTAX  INTEGER
        ACCESS  read-only
        STATUS  mandatory
        DESCRIPTION
            "The average throughput unit of the mirror synchronization operation. 0 presents KB. 1 presents MB. 2 presents GB. 3 presents TB."
    ::= { nrMirrorInfoEntry 25 }

    nrMirrorNASResourceName   OBJECT-TYPE
        SYNTAX  DisplayString
        ACCESS  read-only
        STATUS  mandatory
        DESCRIPTION
            "The NAS resource Name that enables the mirror property."
    ::= { nrMirrorInfoEntry 26 }

--    nrThinProvisionTable    OBJECT-TYPE
--        SYNTAX  SEQUENCE OF NRThinProvisionInfo
--        ACCESS  not-accessible
--        STATUS  mandatory
--        DESCRIPTION
--            "A table containing the Thin Provision of the NAS device."
--    ::= { nasResourceEntry 21 }

--    nrThinProvisionInfoEntry    OBJECT-TYPE
--        SYNTAX  NRThinProvisionInfo
--        ACCESS  not-accessible
--        STATUS  mandatory
--        DESCRIPTION
--            "Information about the usage of the Thin Provision resource."
--        INDEX { nrThinProvisionOption }
--    ::= { nrThinProvisionTable 1 }

--    NRThinProvisionInfo ::= SEQUENCE {
--        nrThinProvisionOption			DisplayString,
--        nrThinProvisionCurrAllocSize		Counter32,
--        nrThinProvisionUsageSize		Counter32,
--        nrThinProvisionUsagePercentage		DisplayString,
--        nrThinProvisionCurrAllocSizeQuantity	Counter32,
--        nrThinProvisionCurrAllocSizeUnit	INTEGER,
--        nrThinProvisionUsageSizeQuantity	Counter32,
--        nrThinProvisionUsageSizeUnit		INTEGER,
--        nrThinProvisionCurrAllocSize64		Counter64,
--        nrThinProvisionUsageSize64		Counter64
--    }

--    nrThinProvisionOption   OBJECT-TYPE
--        SYNTAX  DisplayString
--        ACCESS  read-only
--        STATUS  mandatory
--        DESCRIPTION
--            "It represents the thin provisioning option is enable or disable of the resource."
--    ::= { nrThinProvisionInfoEntry 1 }

--    nrThinProvisionCurrAllocSize   OBJECT-TYPE
--        SYNTAX  Counter32
--        ACCESS  read-only
--        STATUS  mandatory
--        DESCRIPTION
--            "The current Allocated Size of the Thin Provision resource on the IPStor server."
--    ::= { nrThinProvisionInfoEntry 2 }

--    nrThinProvisionUsageSize   OBJECT-TYPE
--        SYNTAX  Counter32
--        ACCESS  read-only
--        STATUS  mandatory
--        DESCRIPTION
--            "The current usage size of the Thin Provision resource."
--    ::= { nrThinProvisionInfoEntry 3 }

--    nrThinProvisionUsagePercentage   OBJECT-TYPE
--        SYNTAX  DisplayString
--        ACCESS  read-only
--        STATUS  mandatory
--        DESCRIPTION
--            "The current usage percentage of the Thin Provision resource."
--    ::= { nrThinProvisionInfoEntry 4 }

--    nrThinProvisionCurrAllocSizeQuantity   OBJECT-TYPE
--        SYNTAX  Counter32
--        ACCESS  read-only
--        STATUS  mandatory
--        DESCRIPTION
--            "The current Allocated Size quantity of the Thin Provision resource on the IPStor server."
--    ::= { nrThinProvisionInfoEntry 5 }

--    nrThinProvisionCurrAllocSizeUnit   OBJECT-TYPE
--        SYNTAX  INTEGER
--        ACCESS  read-only
--        STATUS  mandatory
--        DESCRIPTION
--            "The current Allocated Size unit of the Thin Provision resource on the IPStor server. 0 presents KB. 1 presents MB. 2 presents GB. 3 presents TB."
--    ::= { nrThinProvisionInfoEntry 6 }

--    nrThinProvisionUsageSizeQuantity   OBJECT-TYPE
--        SYNTAX  Counter32
--        ACCESS  read-only
--        STATUS  mandatory
--        DESCRIPTION
--            "The current usage size quantitiy of the Thin Provision resource."
--    ::= { nrThinProvisionInfoEntry 7 }

--    nrThinProvisionUsageSizeUnit   OBJECT-TYPE
--        SYNTAX  INTEGER
--        ACCESS  read-only
--        STATUS  mandatory
--        DESCRIPTION
--            "The current usage size unit of the Thin Provision resource. 0 presents KB. 1 presents MB. 2 presents GB. 3 presents TB."
--    ::= { nrThinProvisionInfoEntry 8 }

--    nrThinProvisionCurrAllocSize64   OBJECT-TYPE
--        SYNTAX  Counter64
--        ACCESS  read-only
--        STATUS  mandatory
--        DESCRIPTION
--            "The current Allocated Size of the Thin Provision resource on the IPStor server."
--    ::= { nrThinProvisionInfoEntry 9 }

--    nrThinProvisionUsageSize64   OBJECT-TYPE
--        SYNTAX  Counter64
--        ACCESS  read-only
--        STATUS  mandatory
--        DESCRIPTION
--            "The current usage size of the Thin Provision resource."
--    ::= { nrThinProvisionInfoEntry 10 }

    nrCDPJournalTable OBJECT IDENTIFIER ::= { nasResourceEntry 22 }

    nrCDPJournalInfoEntry OBJECT-TYPE
        SYNTAX  NRCDPJournalInfo
        ACCESS  not-accessible
        STATUS  mandatory
        DESCRIPTION
            "Information about the policy and configuration of the CDP Journal function."
        INDEX { nrCDPJournalResourceID }
    ::= { nrCDPJournalTable 1 }

    NRCDPJournalInfo ::= SEQUENCE {
        nrCDPJournalResourceID                  INTEGER,
        nrCDPJournalNASResourceID		INTEGER,
        nrCDPJournalOption                      DisplayString,
        nrCDPJournalTotalSize                   Counter32,
        nrCDPJournalStatus                      DisplayString,
        nrCDPJournalPerformanceLevel            DisplayString,
--        nrCDPJournalPolicy                      DisplayString,
--        nrCDPJournalCoveragePeriod              DisplayString,
--        nrCDPJournalExpansionTH                 INTEGER,
--        nrCDPJournalExpansionAllocPercent       INTEGER,
--        nrCDPJournalExpansionAllocMB            INTEGER,
--        nrCDPJournalMaxSize			Counter32,
        nrCDPJournalTotalSizeQuantity		Counter32,
        nrCDPJournalTotalSizeUnit		INTEGER,
--        nrCDPJournalMaxSizeQuantity		Counter32,
--        nrCDPJournalMaxSizeUnit			INTEGER,
--        nrCDPJournalExpansionAllocMBQuantity	Counter32,
--        nrCDPJournalExpansionAllocMBUnit	INTEGER,
        nrCDPJournalTotalSize64			Counter64,
--        nrCDPJournalMaxSize64			Counter64,
--        nrCDPJournalExpansionAllocMB64		Counter64,
	nrCDPJournalAvailableTimerange		DisplayString,
	nrCDPJournalUsageSize			Counter32,
	nrCDPJournalUsagePercentage		Counter32,
        nrCDPJournalUsageSizeQuantity		Counter32,
        nrCDPJournalUsageSizeUnit		INTEGER,
        nrCDPJournalUsageSize64			Counter64,
        nrCDPJournalNASResourceName		DisplayString
    }

    nrCDPJournalResourceID    OBJECT-TYPE
        SYNTAX  INTEGER
        ACCESS  read-only
        STATUS  mandatory
        DESCRIPTION
            "The CDP Journal resource ID assigned by the IPStor server."
    ::= { nrCDPJournalInfoEntry 1 }

    nrCDPJournalNASResourceID    OBJECT-TYPE
        SYNTAX  INTEGER
        ACCESS  read-only
        STATUS  mandatory
        DESCRIPTION
            "The CDP Journal NAS resource ID assigned by the IPStor server."
    ::= { nrCDPJournalInfoEntry 2 }

    nrCDPJournalOption    OBJECT-TYPE
        SYNTAX  DisplayString
        ACCESS  read-only
        STATUS  mandatory
        DESCRIPTION
            "The status represents the CDP Journal option is enable or disable of the NAS resource."
    ::= { nrCDPJournalInfoEntry 3 }

    nrCDPJournalTotalSize    OBJECT-TYPE
        SYNTAX  Counter32
        ACCESS  read-only
        STATUS  mandatory
        DESCRIPTION
            "The CDP Journal Total size of the NAS resource."
    ::= { nrCDPJournalInfoEntry 4 }

    nrCDPJournalStatus    OBJECT-TYPE
        SYNTAX  DisplayString
        ACCESS  read-only
        STATUS  mandatory
        DESCRIPTION
            "The status represents current CDP Journal of the NAS resource."
    ::= { nrCDPJournalInfoEntry 5 }

    nrCDPJournalPerformanceLevel    OBJECT-TYPE
        SYNTAX  DisplayString
        ACCESS  read-only
        STATUS  mandatory
        DESCRIPTION
            "The setting Performance level for the CDP Journal of the NAS resource."
    ::= { nrCDPJournalInfoEntry 6 }

--    nrCDPJournalPolicy    OBJECT-TYPE
--        SYNTAX  DisplayString
--        ACCESS  read-only
--        STATUS  mandatory
--        DESCRIPTION
--            "The CDP Journal Storage Policy when threshold reached and continuous coverage period not exceeded."
--    ::= { nrCDPJournalInfoEntry 7 }

--    nrCDPJournalCoveragePeriod    OBJECT-TYPE
--        SYNTAX  DisplayString
--        ACCESS  read-only
--        STATUS  mandatory
--        DESCRIPTION
--            "Minimun period of continuous coverage to be maintained when journal storage is available or can be allocated."
--    ::= { nrCDPJournalInfoEntry 8 }

--    nrCDPJournalExpansionTH    OBJECT-TYPE
--        SYNTAX  INTEGER
--        ACCESS  read-only
--        STATUS  mandatory
--        DESCRIPTION
--            "The threshold to expand the journal storage when usage reaches."
--    ::= { nrCDPJournalInfoEntry 9 }

--    nrCDPJournalExpansionAllocate    OBJECT-TYPE
--        SYNTAX  INTEGER
--        ACCESS  read-only
--        STATUS  mandatory
--        DESCRIPTION
--            "Amount to allocate when expansion is triggered of the CDP Journal Storage."
--    ::= { nrCDPJournalInfoEntry 10 }

--    nrCDPJournalExpansionAllocMB    OBJECT-TYPE
--        SYNTAX  INTEGER
--        ACCESS  read-only
--        STATUS  mandatory
--        DESCRIPTION
--            "Amount to allocate when expansion is triggered of the CDP Journal Storage."
--    ::= { nrCDPJournalInfoEntry 11 }

--    nrCDPJournalMaxSize    OBJECT-TYPE
--        SYNTAX  Counter32
--        ACCESS  read-only
--        STATUS  mandatory
--        DESCRIPTION
--            "The CDP Journal Storage Maximum size of the NAS resource."
--    ::= { nrCDPJournalInfoEntry 12 }

    nrCDPJournalTotalSizeQuantity    OBJECT-TYPE
        SYNTAX  Counter32
        ACCESS  read-only
        STATUS  mandatory
        DESCRIPTION
            "The CDP Journal Total size quantity of the NAS resource."
    ::= { nrCDPJournalInfoEntry 13 }

    nrCDPJournalTotalSizeUnit    OBJECT-TYPE
        SYNTAX  INTEGER
        ACCESS  read-only
        STATUS  mandatory
        DESCRIPTION
            "The CDP Journal Total size unit of the NAS resource. 0 presents KB. 1 presents MB. 2 presents GB. 3 presents TB."
    ::= { nrCDPJournalInfoEntry 14 }

--    nrCDPJournalMaxSizeQuantity    OBJECT-TYPE
--        SYNTAX  Counter32
--        ACCESS  read-only
--        STATUS  mandatory
--        DESCRIPTION
--            "The CDP Journal Storage Maximum size quantity of the NAS resource."
--    ::= { nrCDPJournalInfoEntry 15 }

--    nrCDPJournalMaxSizeUnit    OBJECT-TYPE
--        SYNTAX  INTEGER
--        ACCESS  read-only
--        STATUS  mandatory
--        DESCRIPTION
--            "The CDP Journal Storage Maximum size unit of the NAS resource. 0 presents KB. 1 presents MB. 2 presents GB. 3 presents TB."
--    ::= { nrCDPJournalInfoEntry 16 }

--    nrCDPJournalExpansionAllocMBQuantity    OBJECT-TYPE
--        SYNTAX  Counter32
--        ACCESS  read-only
--        STATUS  mandatory
--        DESCRIPTION
--            "Amount quantity to allocate when expansion is triggered of the CDP Journal Storage."
--    ::= { nrCDPJournalInfoEntry 17 }

--    nrCDPJournalExpansionAllocMBUnit    OBJECT-TYPE
--        SYNTAX  INTEGER
--        ACCESS  read-only
--        STATUS  mandatory
--        DESCRIPTION
--            "Amount unit to allocate when expansion is triggered of the CDP Journal Storage. 0 presents KB. 1 presents MB. 2 presents GB. 3 presents TB."
--    ::= { nrCDPJournalInfoEntry 18 }

    nrCDPJournalTotalSize64    OBJECT-TYPE
        SYNTAX  Counter64
        ACCESS  read-only
        STATUS  mandatory
        DESCRIPTION
            "The CDP Journal Total size of the NAS resource."
    ::= { nrCDPJournalInfoEntry 19 }

--    nrCDPJournalMaxSize64    OBJECT-TYPE
--        SYNTAX  Counter64
--        ACCESS  read-only
--        STATUS  mandatory
--        DESCRIPTION
--            "The CDP Journal Storage Maximum size of the NAS resource."
--    ::= { nrCDPJournalInfoEntry 20 }

--    nrCDPJournalExpansionAllocMB64    OBJECT-TYPE
--        SYNTAX  Counter64
--        ACCESS  read-only
--        STATUS  mandatory
--        DESCRIPTION
--            "Amount to allocate when expansion is triggered of the CDP Journal Storage."
--    ::= { nrCDPJournalInfoEntry 21 }

    nrCDPJournalAvailableTimerange    OBJECT-TYPE
        SYNTAX  DisplayString
        ACCESS  read-only
        STATUS  mandatory
        DESCRIPTION
            "The CDP Journal available time range of the NAS resource."
    ::= { nrCDPJournalInfoEntry 22 }

    nrCDPJournalUsageSize    OBJECT-TYPE
        SYNTAX  Counter32
        ACCESS  read-only
        STATUS  mandatory
        DESCRIPTION
            "The CDP Journal usage size(MB) of the NAS resource."
    ::= { nrCDPJournalInfoEntry 23 }

    nrCDPJournalUsagePercentage    OBJECT-TYPE
        SYNTAX  Counter32
        ACCESS  read-only
        STATUS  mandatory
        DESCRIPTION
            "The CDP Journal usage percentage of the NAS resource."
    ::= { nrCDPJournalInfoEntry 24 }

    nrCDPJournalUsageSizeQuantity    OBJECT-TYPE
        SYNTAX  Counter32
        ACCESS  read-only
        STATUS  mandatory
        DESCRIPTION
            "The CDP Journal Usage size quantity of the NAS resource."
    ::= { nrCDPJournalInfoEntry 25 }

    nrCDPJournalUsageSizeUnit    OBJECT-TYPE
        SYNTAX  INTEGER
        ACCESS  read-only
        STATUS  mandatory
        DESCRIPTION
            "The CDP Journal Usage size unit of the NAS resource. The size unit of the device. 0 presents KB. 1 presents MB. 2 presents GB. 3 presents TB."
    ::= { nrCDPJournalInfoEntry 26 }

    nrCDPJournalUsageSize64    OBJECT-TYPE
        SYNTAX  Counter64
        ACCESS  read-only
        STATUS  mandatory
        DESCRIPTION
            "The CDP Journal Usage size of the NAS resource."
    ::= { nrCDPJournalInfoEntry 27 }

    nrCDPJournalNASResourceName    OBJECT-TYPE
        SYNTAX  DisplayString
        ACCESS  read-only
        STATUS  mandatory
        DESCRIPTION
            "The CDP Journal NAS resource Name assigned by the IPStor server."
    ::= { nrCDPJournalInfoEntry 28 }

    nrNearLineMirrorTable OBJECT IDENTIFIER ::= { nasResourceEntry 23 }

    nrNearLineMirrorInfoEntry    OBJECT-TYPE
        SYNTAX  NRNearLineMirrorInfo
        ACCESS  not-accessible
        STATUS  mandatory
        DESCRIPTION
            "Information about the configuration of the Near-Line Mirror resource."
        INDEX { nrNearLineMirrorRemoteServerName }
    ::= { nrNearLineMirrorTable 1 }

    NRNearLineMirrorInfo ::= SEQUENCE {
        nrNearLineMirrorRemoteServerName        DisplayString,
        nrNearLineMirrorRemoteServerAlias       DisplayString,
        nrNearLineMirrorRemoteID                INTEGER,
        nrNearLineMirrorRemoteGUID              DisplayString,
        nrNearLineMirrorRemoteSN                DisplayString,
        nrNearLineMirrorNASResourceID		INTEGER,
        nrNearLineMirrorNASResourceName		DisplayString
    }

    nrNearLineMirrorRemoteServerName   OBJECT-TYPE
        SYNTAX  DisplayString
        ACCESS  read-only
        STATUS  mandatory
        DESCRIPTION
            "The remote server name of Near-Line mirror resource sets on the IPStor server."
    ::= { nrNearLineMirrorInfoEntry 1 }

    nrNearLineMirrorRemoteServerAlias   OBJECT-TYPE
        SYNTAX  DisplayString
        ACCESS  read-only
        STATUS  mandatory
        DESCRIPTION
            "The remote server Alias of Near-Line mirror resource sets on the IPStor server."
    ::= { nrNearLineMirrorInfoEntry 2 }

    nrNearLineMirrorRemoteID   OBJECT-TYPE
        SYNTAX  INTEGER
        ACCESS  read-only
        STATUS  mandatory
        DESCRIPTION
            "The remote resource ID of Near-Line mirror resource sets on the IPStor server."
    ::= { nrNearLineMirrorInfoEntry 3 }

    nrNearLineMirrorRemoteGUID   OBJECT-TYPE
        SYNTAX  DisplayString
        ACCESS  read-only
        STATUS  mandatory
        DESCRIPTION
            "The remote resource GUID of Near-Line mirror resource sets on the IPStor server."
    ::= { nrNearLineMirrorInfoEntry 4 }

    nrNearLineMirrorRemoteSN   OBJECT-TYPE
        SYNTAX  DisplayString
        ACCESS  read-only
        STATUS  mandatory
        DESCRIPTION
            "The remote resource serial number of Near-Line mirror resource sets on the IPStor server."
    ::= { nrNearLineMirrorInfoEntry 5 }

    nrNearLineMirrorNASResourceID    OBJECT-TYPE
        SYNTAX  INTEGER
        ACCESS  read-only
        STATUS  mandatory
        DESCRIPTION
            "The NAS resource ID which assigned by the IPStor server enables the Near-Line mirror function."
    ::= { nrNearLineMirrorInfoEntry 6 }

    nrNearLineMirrorNASResourceName    OBJECT-TYPE
        SYNTAX  DisplayString
        ACCESS  read-only
        STATUS  mandatory
        DESCRIPTION
            "The NAS resource Name which assigned by the IPStor server enables the Near-Line mirror function."
    ::= { nrNearLineMirrorInfoEntry 7 }
	
	nrTotalSizeQuantity OBJECT-TYPE
		SYNTAX	Counter32
		ACCESS	read-only
		STATUS	mandatory
		DESCRIPTION
			"The amount of device size quantity of the NAS resource."
	::= { nasResourceEntry 24 }
	
	nrTotalSizeUnit OBJECT-TYPE
		SYNTAX	INTEGER
		ACCESS	read-only
		STATUS	mandatory
		DESCRIPTION
			"The amount of device size unit of the NAS resource. 0 presents KB. 1 presents MB. 2 presents GB. 3 presents TB."
	::= { nasResourceEntry 25 }

	nrTotalSectors64  OBJECT-TYPE
		SYNTAX	Counter64
		ACCESS	read-only
		STATUS	mandatory
		DESCRIPTION
			"The amount of sectors allocated by the NAS resource."
	::= { nasResourceEntry 26 }
	
	nrTotalSize64 OBJECT-TYPE
		SYNTAX	Counter64
		ACCESS	read-only
		STATUS	mandatory
		DESCRIPTION
			"The amount of device size which is representing with megabyte unit of the NAS resource."
	::= { nasResourceEntry 27 }

	nrPhysicalTotalAllocLayoutTable OBJECT IDENTIFIER ::= { nasResourceEntry 28 }

	nrPhysicalTotalAllocLayoutEntry    OBJECT-TYPE
		SYNTAX	NRPhysicalTotalAllocLayout
		ACCESS	not-accessible
		STATUS	mandatory
		DESCRIPTION
			"Information about the physical devices which are reserved and created by logical NAS resource."
		INDEX { nrpaAllocNASResourceName }
	::= { nrPhysicalTotalAllocLayoutTable 1 }

	NRPhysicalTotalAllocLayout ::= SEQUENCE {
		nrpaAllocNASResourceName		DisplayString,
		nrpaAllocName			        DisplayString,
		nrpaAllocType  			        DisplayString,
		nrpaAllocAdapterNo		    	INTEGER,
		nrpaAllocChannelNo		    	INTEGER,
		nrpaAllocScsiID			        INTEGER,
		nrpaAllocLun			        INTEGER,
		nrpaAllocFirstSector		    	Counter32,
		nrpaAllocLastSector			Counter32,
		nrpaAllocFirstSector64			Counter64,
		nrpaAllocLastSector64			Counter64,
		nrpaAllocSize			        Counter32,
		nrpaAllocSizeQuantity		        Counter32,
		nrpaAllocSizeUnit			INTEGER,
		nrpaAllocSize64				Counter64
	}

	nrpaAllocNASResourceName    OBJECT-TYPE
		SYNTAX	DisplayString
		ACCESS	read-only
		STATUS	mandatory
		DESCRIPTION
			"The NAS resource name created by the user."
	::= { nrPhysicalTotalAllocLayoutEntry 1 }

	nrpaAllocName    OBJECT-TYPE
		SYNTAX	DisplayString
		ACCESS	read-only
		STATUS	mandatory
		DESCRIPTION
			"The physical device name."
	::= { nrPhysicalTotalAllocLayoutEntry 2 }
	
	nrpaAllocType OBJECT-TYPE
		SYNTAX	DisplayString
		ACCESS	read-only
		STATUS	mandatory
		DESCRIPTION
			"It represents the type(Primary, or Mirror) of the physical layout."
	::= { nrPhysicalTotalAllocLayoutEntry 3 }

	nrpaAllocAdapterNo OBJECT-TYPE
		SYNTAX  INTEGER
		ACCESS	read-only
		STATUS	mandatory
		DESCRIPTION
			"The SCSI adapter number of the physical device."
	::= { nrPhysicalTotalAllocLayoutEntry 4 }

	nrpaAllocChannelNo OBJECT-TYPE
		SYNTAX  INTEGER
		ACCESS	read-only
		STATUS	mandatory
		DESCRIPTION
			"The SCSI channel number of the physical device."
	::= { nrPhysicalTotalAllocLayoutEntry 5 }

	nrpaAllocScsiID OBJECT-TYPE
		SYNTAX  INTEGER
		ACCESS	read-only
		STATUS	mandatory
		DESCRIPTION
			"The SCSI ID of the physical device."
	::= { nrPhysicalTotalAllocLayoutEntry 6 }

	nrpaAllocLun OBJECT-TYPE
		SYNTAX  INTEGER
		ACCESS	read-only
		STATUS	mandatory
		DESCRIPTION
			"The SCSI LUN number of the physical device."
	::= { nrPhysicalTotalAllocLayoutEntry 7 }

	nrpaAllocFirstSector OBJECT-TYPE
		SYNTAX  Counter32
		ACCESS	read-only
		STATUS	mandatory
		DESCRIPTION
			"The first sector of the physical device which is allocated by the NAS resource."
	::= { nrPhysicalTotalAllocLayoutEntry 8 }

	nrpaAllocLastSector  OBJECT-TYPE
		SYNTAX  Counter32
		ACCESS	read-only
		STATUS	mandatory
		DESCRIPTION
			"The last sector of the physical device which is allocated by the NAS resource."
	::= { nrPhysicalTotalAllocLayoutEntry 9 }

	nrpaAllocFirstSector64 OBJECT-TYPE
		SYNTAX  Counter64
		ACCESS	read-only
		STATUS	mandatory
		DESCRIPTION
			"The first sector of the physical device which is allocated by the NAS resource."
	::= { nrPhysicalTotalAllocLayoutEntry 10 }

	nrpaAllocLastSector64  OBJECT-TYPE
		SYNTAX  Counter64
		ACCESS	read-only
		STATUS	mandatory
		DESCRIPTION
			"The last sector of the physical device which is allocated by the NAS resource."
	::= { nrPhysicalTotalAllocLayoutEntry 11 }
		
	nrpaAllocSize    OBJECT-TYPE
		SYNTAX  Counter32
		ACCESS	read-only
		STATUS	mandatory
		DESCRIPTION
			"The amount of the allocated size which is representing with megabyte unit within a physical device."
	::= { nrPhysicalTotalAllocLayoutEntry 12 }
		
	nrpaAllocSizeQuantity    OBJECT-TYPE
		SYNTAX  Counter32
		ACCESS	read-only
		STATUS	mandatory
		DESCRIPTION
			"The amount of the allocated size quantity within a physical device."
	::= { nrPhysicalTotalAllocLayoutEntry 13 }
		
	nrpaAllocSizeUnit    OBJECT-TYPE
		SYNTAX  INTEGER
		ACCESS	read-only
		STATUS	mandatory
		DESCRIPTION
			"The amount of the allocated size unit within a physical device. The size unit of the device. 0 presents KB. 1 presents MB. 2 presents GB. 3 presents TB."
	::= { nrPhysicalTotalAllocLayoutEntry 14 }
		
	nrpaAllocSize64    OBJECT-TYPE
		SYNTAX  Counter64
		ACCESS	read-only
		STATUS	mandatory
		DESCRIPTION
			"The amount of the allocated size which is representing with megabyte unit within a physical device."
	::= { nrPhysicalTotalAllocLayoutEntry 15 }

	nrHotZonePrefetchInfoTable OBJECT IDENTIFIER ::= { nasResourceEntry 29 }

	nrHotZonePrefetchInfoEntry OBJECT-TYPE
		SYNTAX  NRHotZonePrefetchInfo
		ACCESS  not-accessible
		STATUS  mandatory
		DESCRIPTION
			"Information about the HotZone Prefetch if the NAS resources have enabled."
		INDEX { nrHotZonePrefetchNASResourceID }
	::= { nrHotZonePrefetchInfoTable 1 }

	NRHotZonePrefetchInfo ::= SEQUENCE {
		nrHotZonePrefetchNASResourceID		INTEGER,
		nrHotZonePrefetchMaximumChains		INTEGER,
		nrHotZonePrefetchMaximumReadAhead	INTEGER,
		nrHotZonePrefetchReadAhead		INTEGER,
		nrHotZonePrefetchChainTimeout		DisplayString,
		nrHotZonePrefetchNASResourceName	DisplayString
	}

	nrHotZonePrefetchNASResourceID OBJECT-TYPE
		SYNTAX  INTEGER
		ACCESS  read-only
		STATUS  mandatory
		DESCRIPTION
			"The NAS Resource ID that assigned by IPStor server."
	::= { nrHotZonePrefetchInfoEntry 1 }

	nrHotZonePrefetchMaximumChains OBJECT-TYPE
		SYNTAX  INTEGER
		ACCESS  read-only
		STATUS  mandatory
		DESCRIPTION
			"The maximum number of sequential read chains to detect."
	::= { nrHotZonePrefetchInfoEntry 2 }

	nrHotZonePrefetchMaximumReadAhead OBJECT-TYPE
		SYNTAX  INTEGER
		ACCESS  read-only
		STATUS  mandatory
		DESCRIPTION
			"The maximum size to read ahead representing with KB."
	::= { nrHotZonePrefetchInfoEntry 3 }

	nrHotZonePrefetchReadAhead OBJECT-TYPE
		SYNTAX  INTEGER
		ACCESS  read-only
		STATUS  mandatory
		DESCRIPTION
			"The size of read the read command issued when reading ahead representing with KB."
	::= { nrHotZonePrefetchInfoEntry 4 }

	nrHotZonePrefetchChainTimeout OBJECT-TYPE
		SYNTAX  DisplayString
		ACCESS  read-only
		STATUS  mandatory
		DESCRIPTION
			"The time before the chain is removed and the readahead buffers are freed."
	::= { nrHotZonePrefetchInfoEntry 5 }

	nrHotZonePrefetchNASResourceName OBJECT-TYPE
		SYNTAX  DisplayString
		ACCESS  read-only
		STATUS  mandatory
		DESCRIPTION
			"The NAS Resource Name that assigned by IPStor server."
	::= { nrHotZonePrefetchInfoEntry 6 }

	nrHotZoneReadCacheInfoTable OBJECT IDENTIFIER ::= { nasResourceEntry 30 }

	nrHotZoneReadCacheInfoEntry OBJECT-TYPE
		SYNTAX  NRHotZoneReadCacheInfo
		ACCESS  not-accessible
		STATUS  mandatory
		DESCRIPTION
			"Information about the HotZone Read Cache if the NAS resources have enabled."
		INDEX { nrHotZoneReadCacheResourceID }
	::= { nrHotZoneReadCacheInfoTable 1 }

	NRHotZoneReadCacheInfo ::= SEQUENCE {
		nrHotZoneReadCacheResourceID		INTEGER,
		nrHotZoneReadCacheNASResourceID		INTEGER,
		nrHotZoneReadCacheTotalSize		Counter32,
		nrHotZoneReadCacheStatus		DisplayString,
		nrHotZoneReadCacheSuspended		DisplayString,
		nrHotZoneReadCacheAccessType		DisplayString,
		nrHotZoneReadCacheAccessIntensity	DisplayString,
		nrHotZoneReadCacheMinimumStayTime	DisplayString,
		nrHotZoneReadCacheEachZoneSize		DisplayString,
		nrHotZoneReadCacheTotalZones		Counter32,
		nrHotZoneReadCacheUsedZones		Counter32,
		nrHotZoneReadCacheHitRatio		DisplayString,
		nrHotZoneReadCacheTotalSizeQuantity	Counter32,
		nrHotZoneReadCacheTotalSizeUnit		INTEGER,
		nrHotZoneReadCacheTotalSize64		Counter64,
		nrHotZoneReadCacheNASResourceName	DisplayString
	}

	nrHotZoneReadCacheResourceID OBJECT-TYPE
		SYNTAX  INTEGER
		ACCESS  read-only
		STATUS  mandatory
		DESCRIPTION
			"The Resource ID that assigned by IPStor server."
	::= { nrHotZoneReadCacheInfoEntry 1 }

	nrHotZoneReadCacheNASResourceID OBJECT-TYPE
		SYNTAX  INTEGER
		ACCESS  read-only
		STATUS  mandatory
		DESCRIPTION
			"The NASResource ID that assigned by IPStor server."
	::= { nrHotZoneReadCacheInfoEntry 2 }

	nrHotZoneReadCacheTotalSize OBJECT-TYPE
		SYNTAX  Counter32
		ACCESS  read-only
		STATUS  mandatory
		DESCRIPTION
			"The amount of device size which is representing with megabyte unit of the HotZone read cache resource."
	::= { nrHotZoneReadCacheInfoEntry 3 }

	nrHotZoneReadCacheStatus OBJECT-TYPE
		SYNTAX  DisplayString
		ACCESS  read-only
		STATUS  mandatory
		DESCRIPTION
			"The status represents current HotZone read cache of the NAS resource."
	::= { nrHotZoneReadCacheInfoEntry 4 }

	nrHotZoneReadCacheSuspended OBJECT-TYPE
		SYNTAX  DisplayString
		ACCESS  read-only
		STATUS  mandatory
		DESCRIPTION
			"The Suspended status represents current HotZone read cache of the NAS resource."
	::= { nrHotZoneReadCacheInfoEntry 5 }

	nrHotZoneReadCacheAccessType OBJECT-TYPE
		SYNTAX  DisplayString
		ACCESS  read-only
		STATUS  mandatory
		DESCRIPTION
			"The zone's access type policy of the NAS resource."
	::= { nrHotZoneReadCacheInfoEntry 6 }

	nrHotZoneReadCacheAccessIntensity OBJECT-TYPE
		SYNTAX  DisplayString
		ACCESS  read-only
		STATUS  mandatory
		DESCRIPTION
			"The access intensity to determine how the zone is accessed."
	::= { nrHotZoneReadCacheInfoEntry 7 }

	nrHotZoneReadCacheMinimumStayTime OBJECT-TYPE
		SYNTAX  DisplayString
		ACCESS  read-only
		STATUS  mandatory
		DESCRIPTION
			"The minimum time that how long a zone can stay at least in the HotZone before it is swapped out."
	::= { nrHotZoneReadCacheInfoEntry 8 }

	nrHotZoneReadCacheEachZoneSize OBJECT-TYPE
		SYNTAX  DisplayString
		ACCESS  read-only
		STATUS  mandatory
		DESCRIPTION
			"The size of each zone setting."
	::= { nrHotZoneReadCacheInfoEntry 9 }

	nrHotZoneReadCacheTotalZones OBJECT-TYPE
		SYNTAX  Counter32
		ACCESS  read-only
		STATUS  mandatory
		DESCRIPTION
			"The total zones that is allocated of the NAS resource."
	::= { nrHotZoneReadCacheInfoEntry 10 }

	nrHotZoneReadCacheUsedZones OBJECT-TYPE
		SYNTAX  Counter32
		ACCESS  read-only
		STATUS  mandatory
		DESCRIPTION
			"The current used zones of the NAS resource."
	::= { nrHotZoneReadCacheInfoEntry 11 }

	nrHotZoneReadCacheHitRatio OBJECT-TYPE
		SYNTAX  DisplayString
		ACCESS  read-only
		STATUS  mandatory
		DESCRIPTION
			"The hit ratio represents current HotZone read cache of the NAS resource."
	::= { nrHotZoneReadCacheInfoEntry 12 }

	nrHotZoneReadCacheTotalSizeQuantity OBJECT-TYPE
		SYNTAX  Counter32
		ACCESS  read-only
		STATUS  mandatory
		DESCRIPTION
			"The amount of device size quantity which is representing with megabyte unit of the HotZone read cache resource."
	::= { nrHotZoneReadCacheInfoEntry 13 }

	nrHotZoneReadCacheTotalSizeUnit OBJECT-TYPE
		SYNTAX  INTEGER
		ACCESS  read-only
		STATUS  mandatory
		DESCRIPTION
			"The amount of device size unit of the HotZone read cache resource. The size unit of the device. 0 presents KB. 1 presents MB. 2 presents GB. 3 presents TB."
	::= { nrHotZoneReadCacheInfoEntry 14 }

	nrHotZoneReadCacheTotalSize64 OBJECT-TYPE
		SYNTAX  Counter64
		ACCESS  read-only
		STATUS  mandatory
		DESCRIPTION
			"The amount of device size which is representing with megabyte unit of the HotZone read cache resource."
	::= { nrHotZoneReadCacheInfoEntry 15 }

	nrHotZoneReadCacheNASResourceName OBJECT-TYPE
		SYNTAX  DisplayString
		ACCESS  read-only
		STATUS  mandatory
		DESCRIPTION
			"The NASResource Name that assigned by IPStor server."
	::= { nrHotZoneReadCacheInfoEntry 16 }




--	copyManager OBJECT IDENTIFIER ::= { logicalResources 5 }

--	category    OBJECT-TYPE
--		SYNTAX  DisplayString
--		ACCESS  read-only
--		STATUS  obsolete
--		DESCRIPTION
--			"It defines the category type that is one of the SAN, NAS, Scratch, Umap, SANReplica, NASReplica, and Copy Manager of the copy manager."
--	::= { copyManager 1 }

--	numOfClients    OBJECT-TYPE
--		SYNTAX  INTEGER
--		ACCESS  read-only
--		STATUS  obsolete
--		DESCRIPTION
--			"The amount of clients assigned to the copy manager."
--	::= { copyManager 2 }

--	clientInfoTable OBJECT-TYPE
--		SYNTAX  SEQUENCE OF ClientInfoList
--		ACCESS	not-accessible
--		STATUS	obsolete
--		DESCRIPTION
--			"A table containing the clients information."
--	::= { copyManager 3 }

--	clientinfoEntry OBJECT-TYPE
--		SYNTAX	ClientInfoList
--		ACCESS	not-accessible
--		STATUS	obsolete
--		DESCRIPTION
--			"Information about the clients if the copy manager resources have been assigned."
--		INDEX { cmClientName }
--	::= { clientInfoTable 1 }

--	ClientInfoList ::= SEQUENCE {
--		cmClientName	DisplayString,
--		cmScsiAddress	DisplayString,
--		cmAccess        DisplayString,
--		cmConnAccess	DisplayString
--	}

--	cmClientName    OBJECT-TYPE
--		SYNTAX	DisplayString
--		ACCESS	read-only
--		STATUS	obsolete
--		DESCRIPTION
--			"The client name assigned by the IPStor server."
--	::= { clientinfoEntry 1 }
	
--	cmScsiAddress   OBJECT-TYPE
--		SYNTAX	DisplayString
--		ACCESS	read-only
--		STATUS	obsolete
--		DESCRIPTION
--			"The client's SCSI address with <Adapter:Channel:SCSI:LUN> format."
--	::= { clientinfoEntry 2 }

--	cmAccess    OBJECT-TYPE
--		SYNTAX	DisplayString
--		ACCESS	read-only
--		STATUS	obsolete
--		DESCRIPTION
--			"The resource accessing mode assigned to the client."
--	::= { clientinfoEntry 3 }

--	cmConnAccess    OBJECT-TYPE
--		SYNTAX	DisplayString
--		ACCESS	read-only
--		STATUS	obsolete
--		DESCRIPTION
--			"Identify the connecting and accessing status with a resource."
--	::= { clientinfoEntry 4 }

	replicaResources OBJECT IDENTIFIER ::= { logicalResources 6 }

	numOfReplica    OBJECT-TYPE
		SYNTAX  INTEGER
		ACCESS  read-only
		STATUS  mandatory
		DESCRIPTION
			"The amount of replica resources created by the IPStor server."
	::= { replicaResources 1 }
	
	replicaResourceTable    OBJECT-TYPE
		SYNTAX  SEQUENCE OF ReplicaResourceList
		ACCESS	not-accessible
		STATUS	mandatory
		DESCRIPTION
			"A table containing the replica resources."
	::= { replicaResources 2 }

	replicaResourceEntry    OBJECT-TYPE
		SYNTAX	ReplicaResourceList
		ACCESS	not-accessible
		STATUS	mandatory
		DESCRIPTION
			"Information about the policy and configuration of the replication function."
		INDEX { rrIndex }
	::= { replicaResourceTable 1 }

	ReplicaResourceList ::= SEQUENCE {
		rrIndex                 	INTEGER,
		rrVirtualID             	INTEGER,
		rrVirtualName           	DisplayString,
		rrAllocationType       		DisplayString,
		rrSectors               	Counter32,
		rrTotalSize             	Counter32,
		rrConfigurationStatus   	DisplayString,
		rrGUID                  	DisplayString,
		rrPrimaryVirtualID      	DisplayString,
		rrReplicationStatus     	DisplayString,
		rrLastStartTime         	DisplayString,
		rrMirrorSyncStatus      	DisplayString,
		rrWriteCache			DisplayString,
		rrThinProvisionOption		DisplayString,
		rrThinProvisionCurrAllocSize		Counter32,
		rrThinProvisionUsageSize		Counter32,
		rrThinProvisionUsagePercentage		DisplayString,
		rrTotalSizeQuantity             	Counter32,
		rrTotalSizeUnit		             	INTEGER,
		rrThinProvisionCurrAllocSizeQuantity	Counter32,
		rrThinProvisionCurrAllocSizeUnit	INTEGER,
		rrThinProvisionUsageSizeQuantity	Counter32,
		rrThinProvisionUsageSizeUnit		INTEGER,
		rrSectors64               		Counter64,
		rrTotalSize64             		Counter64,
		rrThinProvisionCurrAllocSize64		Counter64,
		rrThinProvisionUsageSize64		Counter64,
		rrLastSuccessSyncTime			DisplayString,
		rrAverageThroughput			Counter32,
		rrAverageThroughputQuantity		Counter32,
		rrAverageThroughputUnit			INTEGER
	}

	rrIndex OBJECT-TYPE
		SYNTAX	INTEGER
		ACCESS	read-only
		STATUS	mandatory
		DESCRIPTION
			"The sequential digit number as a index key of the replica resource table."
	::= { replicaResourceEntry 1 }
	
	rrVirtualID OBJECT-TYPE
		SYNTAX	INTEGER
		ACCESS	read-only
		STATUS	mandatory
		DESCRIPTION
			"The resource ID assigned by the IPStor server."
	::= { replicaResourceEntry 2 }

	rrVirtualName   OBJECT-TYPE
		SYNTAX	DisplayString
		ACCESS	read-only
		STATUS	mandatory
		DESCRIPTION
			"The resource name created by the user."
	::= { replicaResourceEntry 3 }

	rrAllocationType    OBJECT-TYPE
		SYNTAX	DisplayString
		ACCESS	read-only
		STATUS	mandatory
		DESCRIPTION
			"It represents the resource type when user allocating the resource."
	::= { replicaResourceEntry 4 }

	rrSectors   OBJECT-TYPE
		SYNTAX	Counter32
		ACCESS	read-only
		STATUS	mandatory
		DESCRIPTION
			"The amount of sectors allocated by the resource."
	::= { replicaResourceEntry 5 }

	rrTotalSize OBJECT-TYPE
		SYNTAX	Counter32
		ACCESS	read-only
		STATUS	mandatory
		DESCRIPTION
			"The amount of device size which is representing with megabyte unit of the resource."
	::= { replicaResourceEntry 6 }

	rrConfigurationStatus   OBJECT-TYPE
		SYNTAX	DisplayString
		ACCESS	read-only
		STATUS	mandatory
		DESCRIPTION
			"It represents the attaching status of the resource."
	::= { replicaResourceEntry 7 }

	rrGUID  OBJECT-TYPE
		SYNTAX	DisplayString
		ACCESS	read-only
		STATUS	mandatory
		DESCRIPTION
			"The GUID string of the replica resource."
	::= { replicaResourceEntry 8 }

	rrPrimaryVirtualID  OBJECT-TYPE
		SYNTAX	DisplayString
		ACCESS	read-only
		STATUS	mandatory
		DESCRIPTION
			"It represents the source replication server and device as the format <hostname of source>:<virtual device id>,
			 if the replication option is enabled of the resource."
	::= { replicaResourceEntry 9 }

	rrReplicationStatus OBJECT-TYPE
		SYNTAX	DisplayString
		ACCESS	read-only
		STATUS	mandatory
		DESCRIPTION
			"It represents the current status(Replication failed, New, Idle, and Merging) of the replication schedule."
	::= { replicaResourceEntry 10 }

	rrLastStartTime OBJECT-TYPE
		SYNTAX	DisplayString
		ACCESS	read-only
		STATUS	mandatory
		DESCRIPTION
			"The latest timestamp of the replication."
	::= { replicaResourceEntry 11 }

	rrMirrorSyncStatus  OBJECT-TYPE
		SYNTAX	DisplayString
		ACCESS	read-only
		STATUS	mandatory
		DESCRIPTION
			"It represents the mirror synchronization status of the resource."
	::= { replicaResourceEntry 12 }

	rrWriteCache  OBJECT-TYPE
		SYNTAX	DisplayString
		ACCESS	read-only
		STATUS	mandatory
		DESCRIPTION
			"It represents the write cache option is enable or disable of the resource."
	::= { replicaResourceEntry 13 }

	rrThinProvisionOption  OBJECT-TYPE
		SYNTAX	DisplayString
		ACCESS	read-only
		STATUS	mandatory
		DESCRIPTION
			"It represents the thin provisioning option is enable or disable of the resource."
	::= { replicaResourceEntry 14 }

	rrThinProvisionCurrAllocSize   OBJECT-TYPE
		SYNTAX  Counter32
		ACCESS  read-only
		STATUS  mandatory
		DESCRIPTION
			"The current Allocated Size of the resource which enables thin provisioning."
	::= { replicaResourceEntry 15 }

	rrThinProvisionUsageSize   OBJECT-TYPE
		SYNTAX  Counter32
		ACCESS  read-only
		STATUS  mandatory
		DESCRIPTION
			"The current usage size of the resource which enables thin provisioning."
	::= { replicaResourceEntry 16 }

	rrThinProvisionUsagePercentage   OBJECT-TYPE
		SYNTAX  DisplayString
		ACCESS  read-only
		STATUS  mandatory
		DESCRIPTION
			"The current usage percentage of the resource which enables thin provisioning."
	::= { replicaResourceEntry 17 }

	rrTotalSizeQuantity OBJECT-TYPE
		SYNTAX	Counter32
		ACCESS	read-only
		STATUS	mandatory
		DESCRIPTION
			"The amount of device size quantity of the resource."
	::= { replicaResourceEntry 18 }

	rrTotalSizeUnit OBJECT-TYPE
		SYNTAX	INTEGER
		ACCESS	read-only
		STATUS	mandatory
		DESCRIPTION
			"The amount of device size unit of the resource.0
presents KB. 1 presents MB. 2 presents GB. 3 presents TB."
	::= { replicaResourceEntry 19 }

	rrThinProvisionCurrAllocSizeQuantity   OBJECT-TYPE
		SYNTAX  Counter32
		ACCESS  read-only
		STATUS  mandatory
		DESCRIPTION
			"The current Allocated Size quantity of the resource which enables thin provisioning."
	::= { replicaResourceEntry 20 }

	rrThinProvisionCurrAllocSizeUnit   OBJECT-TYPE
		SYNTAX  INTEGER
		ACCESS  read-only
		STATUS  mandatory
		DESCRIPTION
			"The current Allocated Size unit of the resource which enables thin provisioning. 0 presents KB. 1 presents MB. 2 presents GB. 3 presents TB."
	::= { replicaResourceEntry 21 }

	rrThinProvisionUsageSizeQuantity   OBJECT-TYPE
		SYNTAX  Counter32
		ACCESS  read-only
		STATUS  mandatory
		DESCRIPTION
			"The current usage size quantity of the resource which enables thin provisioning."
	::= { replicaResourceEntry 22 }

	rrThinProvisionUsageSizeUnit   OBJECT-TYPE
		SYNTAX  INTEGER
		ACCESS  read-only
		STATUS  mandatory
		DESCRIPTION
			"The current usage size unit of the resource which enables thin provisioning. 0 presents KB. 1 presents MB. 2 presents GB. 3 presents TB."
	::= { replicaResourceEntry 23 }

	rrSectors64   OBJECT-TYPE
		SYNTAX	Counter64
		ACCESS	read-only
		STATUS	mandatory
		DESCRIPTION
			"The amount of sectors allocated by the resource."
	::= { replicaResourceEntry 24 }

	rrTotalSize64 OBJECT-TYPE
		SYNTAX	Counter64
		ACCESS	read-only
		STATUS	mandatory
		DESCRIPTION
			"The amount of device size which is representing with megabyte unit of the resource."
	::= { replicaResourceEntry 25 }

	rrThinProvisionCurrAllocSize64   OBJECT-TYPE
		SYNTAX  Counter64
		ACCESS  read-only
		STATUS  mandatory
		DESCRIPTION
			"The current Allocated Size of the resource which enables thin provisioning."
	::= { replicaResourceEntry 26 }

	rrThinProvisionUsageSize64   OBJECT-TYPE
		SYNTAX  Counter64
		ACCESS  read-only
		STATUS  mandatory
		DESCRIPTION
			"The current usage size of the resource which enables thin provisioning."
	::= { replicaResourceEntry 27 }

	rrLastSuccessSyncTime OBJECT-TYPE
		SYNTAX	DisplayString
		ACCESS	read-only
		STATUS	mandatory
		DESCRIPTION
			"The last successful synchronize timestamp of the replication."
	::= { replicaResourceEntry 28 }
    
	rrAverageThroughput   OBJECT-TYPE
		SYNTAX  Counter32
		ACCESS  read-only
		STATUS  mandatory
		DESCRIPTION
			"The average throughput (MB/s) of the replication."
	::= { replicaResourceEntry 29 }

	rrAverageThroughputQuantity  OBJECT-TYPE
		SYNTAX  Counter32
		ACCESS  read-only
		STATUS  mandatory
		DESCRIPTION
			"The average throughput quantity of the replication."
	::= { replicaResourceEntry 30 }

	rrAverageThroughputUnit  OBJECT-TYPE
		SYNTAX  INTEGER
		ACCESS  read-only
		STATUS  mandatory
		DESCRIPTION
			"The average throughput unit of the replication. 0 presents KB. 1 presents MB. 2 presents GB. 3 presents TB."
	::= { replicaResourceEntry 31 }

	replicaPhyAllocLayoutTable  OBJECT-TYPE
		SYNTAX  SEQUENCE OF ReplicaPhyAllocLayout
		ACCESS	not-accessible
		STATUS	mandatory
		DESCRIPTION
			"A table containging the physical layout information for the replica resources."
	::= { replicaResources 3 }

	replicaPhyAllocLayoutEntry  OBJECT-TYPE
		SYNTAX  ReplicaPhyAllocLayout
		ACCESS	not-accessible
		STATUS	mandatory
		DESCRIPTION
			"Information about the physical devices which are reserved and created by replica resource."
		INDEX { rrpaIndex }
	::= { replicaPhyAllocLayoutTable 1 }

	ReplicaPhyAllocLayout ::= SEQUENCE {
		rrpaIndex		INTEGER,
		rrpaVirtualID		INTEGER,
		rrpaVirtualName		DisplayString,
		rrpaName		DisplayString,
		rrpaType		DisplayString,
		rrpaSCSIAddress		DisplayString,
		rrpaFirstSector		Counter32,
		rrpaLastSector		Counter32,
		rrpaSize		Counter32,
		rrpaSizeQuantity	Counter32,
		rrpaSizeUnit		INTEGER,
		rrpaFirstSector64	Counter64,
		rrpaLastSector64	Counter64,
		rrpaSize64		Counter64
	}

	rrpaIndex   OBJECT-TYPE
		SYNTAX  INTEGER
		ACCESS	read-only
		STATUS	mandatory
		DESCRIPTION
			"The sequential digit number as a index key of the physical layout table."
	::= { replicaPhyAllocLayoutEntry 1 }

	rrpaVirtualID   OBJECT-TYPE
		SYNTAX  INTEGER
		ACCESS	read-only
		STATUS	mandatory
		DESCRIPTION
			"The replica resource ID assigned by the IPStor server."
	::= { replicaPhyAllocLayoutEntry 2 }

	rrpaVirtualName OBJECT-TYPE
		SYNTAX	DisplayString
		ACCESS	read-only
		STATUS	mandatory
		DESCRIPTION
			"The replica resource name created by the user."
	::= { replicaPhyAllocLayoutEntry 3 }

	rrpaName    OBJECT-TYPE
		SYNTAX	DisplayString
		ACCESS	read-only
		STATUS	mandatory
		DESCRIPTION
			"The physical device name."
	::= { replicaPhyAllocLayoutEntry 4 }
	
	rrpaType    OBJECT-TYPE
		SYNTAX	DisplayString
		ACCESS	read-only
		STATUS	mandatory
		DESCRIPTION
			"It represents the type(Primary, or Mirror) of the physical layout."
	::= { replicaPhyAllocLayoutEntry 5 }

	rrpaSCSIAddress OBJECT-TYPE
		SYNTAX  DisplayString
		ACCESS	read-only
		STATUS	mandatory
		DESCRIPTION
			"The SCSI address with <Adapter:Channel:SCSI:LUN> format of the replica resource."
	::= { replicaPhyAllocLayoutEntry 6 }

	rrpaFirstSector OBJECT-TYPE
		SYNTAX  Counter32
		ACCESS	read-only
		STATUS	mandatory
		DESCRIPTION
			"The first sector of the physical device which is allocated by the replica resource."
	::= { replicaPhyAllocLayoutEntry 7 }

	rrpaLastSector  OBJECT-TYPE
		SYNTAX  Counter32
		ACCESS	read-only
		STATUS	mandatory
		DESCRIPTION
			"The last sector of the physical device which is allocated by the replica resource."
	::= { replicaPhyAllocLayoutEntry 8 }
		
	rrpaSize    OBJECT-TYPE
		SYNTAX  Counter32
		ACCESS	read-only
		STATUS	mandatory
		DESCRIPTION
			"The amount of the allocated size which is representing with megabyte unit within a physical device."
	::= { replicaPhyAllocLayoutEntry 9 }
		
	rrpaSizeQuantity    OBJECT-TYPE
		SYNTAX  Counter32
		ACCESS	read-only
		STATUS	mandatory
		DESCRIPTION
			"The amount of the allocated size quantity within a physical device."
	::= { replicaPhyAllocLayoutEntry 10 }
		
	rrpaSizeUnit    OBJECT-TYPE
		SYNTAX  INTEGER
		ACCESS	read-only
		STATUS	mandatory
		DESCRIPTION
			"The amount of the allocated size unit within a physical device. The size unit of the device. 0 presents KB. 1 presents MB. 2 presents GB. 3 presents TB."
	::= { replicaPhyAllocLayoutEntry 11 }

	rrpaFirstSector64 OBJECT-TYPE
		SYNTAX  Counter64
		ACCESS	read-only
		STATUS	mandatory
		DESCRIPTION
			"The first sector of the physical device which is allocated by the replica resource."
	::= { replicaPhyAllocLayoutEntry 12 }

	rrpaLastSector64  OBJECT-TYPE
		SYNTAX  Counter64
		ACCESS	read-only
		STATUS	mandatory
		DESCRIPTION
			"The last sector of the physical device which is allocated by the replica resource."
	::= { replicaPhyAllocLayoutEntry 13 }
		
	rrpaSize64    OBJECT-TYPE
		SYNTAX  Counter64
		ACCESS	read-only
		STATUS	mandatory
		DESCRIPTION
			"The amount of the allocated size which is representing with megabyte unit within a physical device."
	::= { replicaPhyAllocLayoutEntry 14 }

    snapshotgroupResources OBJECT IDENTIFIER ::= { logicalResources 7 }

    numOfGroup  OBJECT-TYPE
        SYNTAX  INTEGER
        ACCESS  read-only
        STATUS  mandatory
        DESCRIPTION
            "The amount of snapshot groups created by the IPStor server."
    ::= { snapshotgroupResources 1 }
    
    snapshotgroupInfoTable  OBJECT-TYPE
        SYNTAX  SEQUENCE OF SSGResourcesInfo
        ACCESS  not-accessible
        STATUS  mandatory
        DESCRIPTION
            "A table containing the whole types of snapshot groups created by the IPStor server."
    ::= { snapshotgroupResources 2 }
    
    snapshotgroupResourcesInfoEntry OBJECT-TYPE
        SYNTAX  SSGResourcesInfo
        ACCESS  not-accessible
        STATUS  mandatory
        DESCRIPTION
            "Information about the snapshot groups include timemark, backup, and replication properties."
        INDEX { snapshotgroupIndex }
    ::= { snapshotgroupInfoTable 1 }

    SSGResourcesInfo ::= SEQUENCE {
        snapshotgroupIndex                  INTEGER,
        snapshotgroupName                   DisplayString,
        snapshotgroupType                   DisplayString,
--      snapshotgroupTimeMarkInfoTable      OBJECT IDENTIFIER,
--      snapshotgroupBackupInfoTable        OBJECT IDENTIFIER,
--      snapshotgroupReplicationInfoTable   OBJECT IDENTIFIER,
	snapshotgroupMembers		    Counter32,
	snapshotgroupAssignClients	    Counter32,
        snapshotgroupCacheOption            DisplayString,
        snapshotgroupReplicationOption	    DisplayString,
        snapshotgroupTimeMarkOption         DisplayString,
        snapshotgroupCDPOption              DisplayString,
        snapshotgroupBackupOption           DisplayString,
        snapshotgroupSnapShotOption         DisplayString
    }
    
    snapshotgroupIndex  OBJECT-TYPE
        SYNTAX  INTEGER
        ACCESS  read-only
        STATUS  mandatory
        DESCRIPTION
            "The snapshot group resource ID assigned by the IPStor server."
    ::= { snapshotgroupResourcesInfoEntry 1 }

    snapshotgroupName   OBJECT-TYPE
        SYNTAX  DisplayString
        ACCESS  read-only
        STATUS  mandatory
        DESCRIPTION
            "The snapshot group resource name created by the user."
    ::= { snapshotgroupResourcesInfoEntry 2 }

    snapshotgroupType   OBJECT-TYPE
        SYNTAX  DisplayString
        ACCESS  read-only
        STATUS  mandatory
        DESCRIPTION
            "The property of the snapshot group, which it can be one of the following types.
             timemark, backup, replication, timemark + backup, timemark + replication, backup + replication, and timmemark + backup + replication."	
    ::= { snapshotgroupResourcesInfoEntry 3 }

    snapshotgroupTimeMarkInfoTable OBJECT-TYPE
        SYNTAX  SEQUENCE OF SSGTimeMarkInfo
        ACCESS  not-accessible
        STATUS  mandatory
        DESCRIPTION
            "A table containing the timemark properties of snapshot groups."
    ::= { snapshotgroupResourcesInfoEntry 4 }
    
    snapshotgroupTimeMarkInfoTableEntry OBJECT-TYPE
        SYNTAX  SSGTimeMarkInfo
        ACCESS  not-accessible
        STATUS  mandatory
        DESCRIPTION
            "Information about the policy and configuration of the timemark function."
        INDEX { snapshotgroupTimeMarkGroupID }
    ::= { snapshotgroupTimeMarkInfoTable 1 }
    
    SSGTimeMarkInfo ::= SEQUENCE {
        snapshotgroupTimeMarkGroupID			INTEGER,
        snapshotgroupTimeMarkInfoOption			DisplayString,
        snapshotgroupTimeMarkCounts			INTEGER,
        snapshotgroupTimeMarkSchedule			DisplayString,
        snapshotgroupTimeMarkSnapshotImage		DisplayString,
	snapshotgroupTimeMarkSnapshotNotificationOption	DisplayString,
	snapshotgroupTimeMarkReplicationOption		DisplayString
    }
    
    snapshotgroupTimeMarkGroupID    OBJECT-TYPE
        SYNTAX  INTEGER
        ACCESS  read-only
        STATUS  mandatory
        DESCRIPTION
            "The snapshot group resource ID assigned by the IPStor server."
    ::= { snapshotgroupTimeMarkInfoTableEntry 1 }
    
    snapshotgroupTimeMarkInfoOption OBJECT-TYPE
        SYNTAX  DisplayString
        ACCESS  read-only
        STATUS  mandatory
        DESCRIPTION
            "The status represents the timemark option is enable or disable of the snapshot group resource."
    ::= { snapshotgroupTimeMarkInfoTableEntry 2 }
    
    snapshotgroupTimeMarkCounts OBJECT-TYPE
        SYNTAX  INTEGER
        ACCESS  read-only
        STATUS  mandatory
        DESCRIPTION
            "The maximum timemarks that is allowed to create of the snapshot group resource."
    ::= { snapshotgroupTimeMarkInfoTableEntry 3 }
    
    snapshotgroupTimeMarkSchedule   OBJECT-TYPE
        SYNTAX  DisplayString
        ACCESS  read-only
        STATUS  mandatory
        DESCRIPTION
            "The time interval creates one new timemark."
    ::= { snapshotgroupTimeMarkInfoTableEntry 4 }
    
    snapshotgroupTimeMarkSnapshotImage  OBJECT-TYPE
        SYNTAX  DisplayString
        ACCESS  read-only
        STATUS  mandatory
        DESCRIPTION
            "The time of each day creates snapshot-image automatically."
    ::= { snapshotgroupTimeMarkInfoTableEntry 5 }

    snapshotgroupTimeMarkSnapshotNotificationOption OBJECT-TYPE
        SYNTAX  DisplayString
        ACCESS  read-only
        STATUS  mandatory
        DESCRIPTION
            "The option of triggering snapshot notification schedule."
    ::= { snapshotgroupTimeMarkInfoTableEntry 6 }

    snapshotgroupTimeMarkReplicationOption OBJECT-TYPE
        SYNTAX  DisplayString
        ACCESS  read-only
        STATUS  mandatory
        DESCRIPTION
            "The replication option after the timemark is taken."
    ::= { snapshotgroupTimeMarkInfoTableEntry 7 }

    snapshotgroupBackupInfoTable OBJECT-TYPE
        SYNTAX  SEQUENCE OF SSGBackupInfo
        ACCESS  not-accessible
        STATUS  mandatory
        DESCRIPTION
            "A table containing the backup properties of snapshot groups."
    ::= { snapshotgroupResourcesInfoEntry 5 }
    
    snapshotgroupBackupInfoTableEntry    OBJECT-TYPE
        SYNTAX  SSGBackupInfo
        ACCESS  not-accessible
        STATUS  mandatory
        DESCRIPTION
            "Information about the policy and configuration of the backup function."
        INDEX { snapshotgroupBackupGroupID }
    ::= { snapshotgroupBackupInfoTable 1 }
    
    SSGBackupInfo ::= SEQUENCE {
        snapshotgroupBackupGroupID          INTEGER,
        snapshotgroupBackupInfoOption       DisplayString,
        snapshotgroupBackupWindow           DisplayString,
        snapshotgroupBackupSessionLen       DisplayString,
        snapshotgroupBackupRelativeTime     DisplayString,
        snapshotgroupBackupWaitTime         INTEGER,
        snapshotgroupBackupSelectCriteria   DisplayString
    }
    
    snapshotgroupBackupGroupID  OBJECT-TYPE
        SYNTAX  INTEGER
        ACCESS  read-only
        STATUS  mandatory
        DESCRIPTION
            "The snapshot group resource ID assigned by the IPStor server."
    ::= { snapshotgroupBackupInfoTableEntry 1 }
    
    snapshotgroupBackupInfoOption   OBJECT-TYPE
        SYNTAX  DisplayString
        ACCESS  read-only
        STATUS  mandatory
        DESCRIPTION
            "The status represents the backup option is enable or disable of the snapshot group resource."
    ::= { snapshotgroupBackupInfoTableEntry 2 }
    
    snapshotgroupBackupWindow   OBJECT-TYPE
        SYNTAX  DisplayString
        ACCESS  read-only
        STATUS  mandatory
        DESCRIPTION
            "The daytime allows for opening one backup sesion."
    ::= { snapshotgroupBackupInfoTableEntry 3 }
    
    snapshotgroupBackupSessionLen   OBJECT-TYPE
        SYNTAX  DisplayString
        ACCESS  read-only
        STATUS  mandatory
        DESCRIPTION
            "The time interval allows for one backup session in each time."
    ::= { snapshotgroupBackupInfoTableEntry 4 }
    
    snapshotgroupBackupRelativeTime OBJECT-TYPE
        SYNTAX  DisplayString
        ACCESS  read-only
        STATUS  mandatory
        DESCRIPTION
            "The time interval waits before closing the backup session which is in inactivity status."
    ::= { snapshotgroupBackupInfoTableEntry 5 }
    
    snapshotgroupBackupWaitTime OBJECT-TYPE
        SYNTAX  INTEGER
        ACCESS  read-only
        STATUS  mandatory
        DESCRIPTION
            "The time interval which is represnting in minute unit waits before closing the backup session after completion."
    ::= { snapshotgroupBackupInfoTableEntry 6 }
    
    snapshotgroupBackupSelectCriteria   OBJECT-TYPE
        SYNTAX  DisplayString
        ACCESS  read-only
        STATUS  mandatory
        DESCRIPTION
            "The snapshot image selection criteria that could be new or latest for the backup session.
             New represents that it always creates new snapshot image for backup, and 
             Latest represents that it uses the last created snapshot image for backup."
    ::= { snapshotgroupBackupInfoTableEntry 7 }

    snapshotgroupReplicationInfoTable    OBJECT-TYPE
        SYNTAX  SEQUENCE OF SSGReplicationInfo
        ACCESS  not-accessible
        STATUS  mandatory
        DESCRIPTION
            "A table containing the replication properties of snapshot groups."
    ::= { snapshotgroupResourcesInfoEntry 6 }
    
    snapshotgroupReplicationInfoTableEntry OBJECT-TYPE
        SYNTAX  SSGReplicationInfo
        ACCESS  not-accessible
        STATUS  mandatory
        DESCRIPTION
            "Information about the policy and configuration of the replication function."
        INDEX { snapshotgroupReplicationGroupID }
    ::= { snapshotgroupReplicationInfoTable 1 }
    
    SSGReplicationInfo ::= SEQUENCE {
        snapshotgroupReplicationGroupID			INTEGER,
        snapshotgroupReplicationInfoOption		DisplayString,
        snapshotgroupReplicaServer			DisplayString,
        snapshotgroupReplicaGroupID			INTEGER,
        snapshotgroupReplicaWatermark			DisplayString,
        snapshotgroupReplicaTime			DisplayString,
        snapshotgroupReplicaInterval			DisplayString,
        snapshotgroupReplicaWatermarkRetry		INTEGER,
        snapshotgroupReplicaContinuousMode		DisplayString,
        snapshotgroupReplicaCreatePrimaryTimeMark	DisplayString,
        snapshotgroupReplicaSyncTimeMark		DisplayString,
        snapshotgroupReplicaProtocol			DisplayString,
        snapshotgroupReplicaCompression			DisplayString,
        snapshotgroupReplicaEncryption			DisplayString,
        snapshotgroupReplicaMicroscan			DisplayString,
        snapshotgroupReplicaSyncPriority		INTEGER,
        snapshotgroupReplicaMode			DisplayString,
        snapshotgroupReplicaUseExistTM			DisplayString,
        snapshotgroupReplicaPreserveTM			DisplayString
    }
    
    snapshotgroupReplicationGroupID OBJECT-TYPE
        SYNTAX  INTEGER
        ACCESS  read-only
        STATUS  mandatory
        DESCRIPTION
            "The snapshot group resource ID assigned by the IPStor server."
    ::= { snapshotgroupReplicationInfoTableEntry 1 }
    
    snapshotgroupReplicationInfoOption  OBJECT-TYPE
        SYNTAX  DisplayString
        ACCESS  read-only
        STATUS  mandatory
        DESCRIPTION
            "The status represents the replication option is enable or disable of the snapshot group resource."
    ::= { snapshotgroupReplicationInfoTableEntry 2 }
    
    snapshotgroupReplicaServer  OBJECT-TYPE
        SYNTAX  DisplayString
        ACCESS  read-only
        STATUS  mandatory
        DESCRIPTION
            "The target replia server name."
    ::= { snapshotgroupReplicationInfoTableEntry 3 }
    
    snapshotgroupReplicaGroupID OBJECT-TYPE
        SYNTAX  INTEGER
        ACCESS  read-only
        STATUS  mandatory
        DESCRIPTION
            "The target replica group ID."
    ::= { snapshotgroupReplicationInfoTableEntry 4 }
    
    snapshotgroupReplicaWatermark   OBJECT-TYPE
        SYNTAX  DisplayString
        ACCESS  read-only
        STATUS  mandatory
        DESCRIPTION
            "The watermark sets to generate one new replication automatically."
    ::= { snapshotgroupReplicationInfoTableEntry 5 }
    
    snapshotgroupReplicaTime    OBJECT-TYPE
        SYNTAX  DisplayString
        ACCESS  read-only
        STATUS  mandatory
        DESCRIPTION
            "The daytime of each day creates one new replication."
    ::= { snapshotgroupReplicationInfoTableEntry 6 }      
    
    snapshotgroupReplicaInterval    OBJECT-TYPE
        SYNTAX  DisplayString
        ACCESS  read-only
        STATUS  mandatory
        DESCRIPTION
            "The time interval creates one new replication."
    ::= { snapshotgroupReplicationInfoTableEntry 7 }      

    snapshotgroupReplicaWatermarkRetry OBJECT-TYPE
        SYNTAX  INTEGER
        ACCESS  read-only
        STATUS  mandatory
        DESCRIPTION
            "The retry interval which is representing in minute unit if the replication failed."
    ::= { snapshotgroupReplicationInfoTableEntry 8 }

    snapshotgroupReplicaContinuousMode   OBJECT-TYPE
        SYNTAX  DisplayString
        ACCESS  read-only
        STATUS  mandatory
        DESCRIPTION
            "The status represents the Continuous Mode of Replication is enable or disable."
    ::= { snapshotgroupReplicationInfoTableEntry 9 }

    snapshotgroupReplicaCreatePrimaryTimeMark    OBJECT-TYPE
        SYNTAX  DisplayString
        ACCESS  read-only
        STATUS  mandatory
        DESCRIPTION
            "This option allows to create the primary TimeMark when a replica TimeMark is created."
    ::= { snapshotgroupReplicationInfoTableEntry 10 }

    snapshotgroupReplicaSyncTimeMark    OBJECT-TYPE
        SYNTAX  DisplayString
        ACCESS  read-only
        STATUS  mandatory
        DESCRIPTION
            "This option allows to synchronize the replica TimeMark when a primary TimeMark is created."
    ::= { snapshotgroupReplicationInfoTableEntry 11 }

    snapshotgroupReplicaProtocol    OBJECT-TYPE
        SYNTAX  DisplayString
        ACCESS  read-only
        STATUS  mandatory
        DESCRIPTION
            "It states the Protocol which Replication uses."
    ::= { snapshotgroupReplicationInfoTableEntry 12 }

    snapshotgroupReplicaCompression    OBJECT-TYPE
        SYNTAX  DisplayString
        ACCESS  read-only
        STATUS  mandatory
        DESCRIPTION
            "The status represents the Compression option is enable or disable of Replication."
    ::= { snapshotgroupReplicationInfoTableEntry 13 }

    snapshotgroupReplicaEncryption    OBJECT-TYPE
        SYNTAX  DisplayString
        ACCESS  read-only
        STATUS  mandatory
        DESCRIPTION
            "The status represents the Encryption option is enable or disable of Replication."
    ::= { snapshotgroupReplicationInfoTableEntry 14 }

    snapshotgroupReplicaMicroscan    OBJECT-TYPE
        SYNTAX  DisplayString
        ACCESS  read-only
        STATUS  mandatory
        DESCRIPTION
            "The status represents the Microscan option is enable or disable of Replication."
    ::= { snapshotgroupReplicationInfoTableEntry 15 }

    snapshotgroupReplicaSyncPriority    OBJECT-TYPE
        SYNTAX  INTEGER
        ACCESS  read-only
        STATUS  mandatory
        DESCRIPTION
            "The Priority setting when Replication Synchronize of the SAN resource."
    ::= { snapshotgroupReplicationInfoTableEntry 16 }

    snapshotgroupReplicaMode    OBJECT-TYPE
        SYNTAX  DisplayString
        ACCESS  read-only
        STATUS  mandatory
        DESCRIPTION
            "The Replication mode of the SAN resource."
    ::= { snapshotgroupReplicationInfoTableEntry 17 }

    snapshotgroupReplicaUseExistTM    OBJECT-TYPE
        SYNTAX  DisplayString
        ACCESS  read-only
        STATUS  mandatory
        DESCRIPTION
            "When Continuous Mode is disabled, the option about using existing TimeMark of the replication."
    ::= { snapshotgroupReplicationInfoTableEntry 18 }

    snapshotgroupReplicaPreserveTM    OBJECT-TYPE
        SYNTAX  DisplayString
        ACCESS  read-only
        STATUS  mandatory
        DESCRIPTION
            "When Continuous Mode is disabled, the option about perserving TimeMark of the replication."
    ::= { snapshotgroupReplicationInfoTableEntry 19 }

    snapshotgroupCDPInfoTable OBJECT IDENTIFIER ::= {snapshotgroupResourcesInfoEntry 7 }
    
    snapshotgroupCDPInfoTableEntry    OBJECT-TYPE
        SYNTAX  SSGCDPInfo
        ACCESS  not-accessible
        STATUS  mandatory
        DESCRIPTION
            "Information about the policy and configuration of the cdp function."
        INDEX { snapshotgroupCDPInfoGroupID }
    ::= { snapshotgroupCDPInfoTable 1 }
    
    SSGCDPInfo ::= SEQUENCE {
        snapshotgroupCDPInfoGroupID			INTEGER,
        snapshotgroupCDPInfoOption			DisplayString,
        snapshotgroupCDPInfoTotalSize			Counter32,
        snapshotgroupCDPInfoStatus			DisplayString,
        snapshotgroupCDPInfoPerformanceLevel		DisplayString,
        snapshotgroupCDPInfoAvailableTimerange		DisplayString,
	snapshotgroupCDPInfoUsageSize			Counter32,
	snapshotgroupCDPInfoUsagePercent		Counter32,
	snapshotgroupCDPInfoTotalSizeQuantity		Counter32,
	snapshotgroupCDPInfoTotalSizeUnit		INTEGER,
	snapshotgroupCDPInfoTotalSize64			Counter64,
	snapshotgroupCDPInfoUsageSizeQuantity		Counter32,
	snapshotgroupCDPInfoUsageSizeUnit		INTEGER,
	snapshotgroupCDPInfoUsageSize64			Counter64
    }
    
    snapshotgroupCDPInfoGroupID  OBJECT-TYPE
        SYNTAX  INTEGER
        ACCESS  read-only
        STATUS  mandatory
        DESCRIPTION
            "The snapshot group resource ID assigned by the IPStor server."
    ::= { snapshotgroupCDPInfoTableEntry 1 }
    
    snapshotgroupCDPInfoOption  OBJECT-TYPE
        SYNTAX  DisplayString
        ACCESS  read-only
        STATUS  mandatory
        DESCRIPTION
            "The status represents the snapshot group CDP Journal option is enable or disable of the IPStor server."
    ::= { snapshotgroupCDPInfoTableEntry 2 }
    
    snapshotgroupCDPInfoTotalSize  OBJECT-TYPE
        SYNTAX  Counter32
        ACCESS  read-only
        STATUS  mandatory
        DESCRIPTION
            "The total size of snapshot group CDP Journal of the IPStor server."
    ::= { snapshotgroupCDPInfoTableEntry 3 }
    
    snapshotgroupCDPInfoStatus  OBJECT-TYPE
        SYNTAX  DisplayString
        ACCESS  read-only
        STATUS  mandatory
        DESCRIPTION
            "The status of the snapshot group CDP Journal of the IPStor server."
    ::= { snapshotgroupCDPInfoTableEntry 4 }
    
    snapshotgroupCDPInfoPerformanceLevel  OBJECT-TYPE
        SYNTAX  DisplayString
        ACCESS  read-only
        STATUS  mandatory
        DESCRIPTION
            "The performance level setting of the snapshot group CDP Journal of the IPStor server."
    ::= { snapshotgroupCDPInfoTableEntry 5 }
    
    snapshotgroupCDPInfoAvailableTimerange  OBJECT-TYPE
        SYNTAX  DisplayString
        ACCESS  read-only
        STATUS  mandatory
        DESCRIPTION
            "The available time range of the snapshot group CDP Journal of the IPStor server."
    ::= { snapshotgroupCDPInfoTableEntry 6 }
    
    snapshotgroupCDPInfoUsageSize  OBJECT-TYPE
        SYNTAX  Counter32
        ACCESS  read-only
        STATUS  mandatory
        DESCRIPTION
            "The usage size(MB) of snapshot group CDP Journal of the IPStor server."
    ::= { snapshotgroupCDPInfoTableEntry 7 }
    
    snapshotgroupCDPInfoUsagePercent  OBJECT-TYPE
        SYNTAX  Counter32
        ACCESS  read-only
        STATUS  mandatory
        DESCRIPTION
            "The usage percentage of snapshot group CDP Journal of the IPStor server."
    ::= { snapshotgroupCDPInfoTableEntry 8 }
    
    snapshotgroupCDPInfoTotalSizeQuantity  OBJECT-TYPE
        SYNTAX  Counter32
        ACCESS  read-only
        STATUS  mandatory
        DESCRIPTION
            "The total size quantity of snapshot group CDP Journal of the IPStor server."
    ::= { snapshotgroupCDPInfoTableEntry 9 }
    
    snapshotgroupCDPInfoTotalSizeUnit  OBJECT-TYPE
        SYNTAX  Counter32
        ACCESS  read-only
        STATUS  mandatory
        DESCRIPTION
            "The total size unit of snapshot group CDP Journal of the IPStor server. 0 presents KB. 1 presents MB. 2 presents GB. 3 presents
TB."
    ::= { snapshotgroupCDPInfoTableEntry 10 }
    
    snapshotgroupCDPInfoTotalSize64  OBJECT-TYPE
        SYNTAX  Counter64
        ACCESS  read-only
        STATUS  mandatory
        DESCRIPTION
            "The total size 64 bit long of snapshot group CDP Journal of the IPStor server."
    ::= { snapshotgroupCDPInfoTableEntry 11 }
    
    snapshotgroupCDPInfoUsageSizeQuantity  OBJECT-TYPE
        SYNTAX  Counter32
        ACCESS  read-only
        STATUS  mandatory
        DESCRIPTION
            "The usage size quantity of snapshot group CDP Journal of the IPStor server."
    ::= { snapshotgroupCDPInfoTableEntry 12 }
    
    snapshotgroupCDPInfoUsageSizeUnit  OBJECT-TYPE
        SYNTAX  Counter32
        ACCESS  read-only
        STATUS  mandatory
        DESCRIPTION
            "The usage size unit of snapshot group CDP Journal of the IPStor server. 0 presents KB. 1 presents MB. 2 presents GB. 3 presents
TB."
    ::= { snapshotgroupCDPInfoTableEntry 13 }
    
    snapshotgroupCDPInfoUsageSize64  OBJECT-TYPE
        SYNTAX  Counter64
        ACCESS  read-only
        STATUS  mandatory
        DESCRIPTION
            "The usage size 64 bit long of snapshot group CDP Journal of the IPStor server."
    ::= { snapshotgroupCDPInfoTableEntry 14 }

    snapshotgroupSafeCacheInfoTable OBJECT IDENTIFIER ::= {snapshotgroupResourcesInfoEntry 8 }
    
    snapshotgroupSafeCacheInfoTableEntry    OBJECT-TYPE
        SYNTAX  SSGCacheInfo
        ACCESS  not-accessible
        STATUS  mandatory
        DESCRIPTION
            "Information about the policy and configuration of the safecache function."
        INDEX { snapshotgroupCacheInfoGroupID }
    ::= { snapshotgroupSafeCacheInfoTable 1 }

    SSGCacheInfo ::= SEQUENCE {
        snapshotgroupCacheInfoGroupID			INTEGER,
        snapshotgroupCacheInfoOption			DisplayString,
        snapshotgroupCacheInfoSuspend			DisplayString,
        snapshotgroupCacheInfoTotalSize			Counter32,
        snapshotgroupCacheInfoFreeSize			Counter32,
        snapshotgroupCacheInfoUsage			INTEGER,
	snapshotgroupCacheInfoThreshold			INTEGER,
        snapshotgroupCacheInfoFlushTime			INTEGER,
        snapshotgroupCacheInfoSkipWriteCommands		DisplayString,
        snapshotgroupCacheInfoFlushSpeed		INTEGER,
        snapshotgroupCacheInfoTotalSizeQuantity		Counter32,
        snapshotgroupCacheInfoTotalSizeUnit		INTEGER,
        snapshotgroupCacheInfoFreeSizeQuantity		Counter32,
        snapshotgroupCacheInfoFreeSizeUnit		INTEGER,
        snapshotgroupCacheInfoResourceID		INTEGER,
        snapshotgroupCacheInfoTotalSize64		Counter64,
        snapshotgroupCacheInfoFreeSize64		Counter64,
        snapshotgroupCacheInfoStatus			DisplayString
    }

    snapshotgroupCacheInfoGroupID   OBJECT-TYPE
        SYNTAX  INTEGER
        ACCESS  read-only
        STATUS  mandatory
        DESCRIPTION
            "The snapshot group resource ID assigned by the IPStor server."
    ::= { snapshotgroupSafeCacheInfoTableEntry 1 }
    
    snapshotgroupCacheInfoOption   OBJECT-TYPE
        SYNTAX  DisplayString
        ACCESS  read-only
        STATUS  mandatory
        DESCRIPTION
            "The status represents the snapshot group safecache option is enable or disable of the IPStor server."
    ::= { snapshotgroupSafeCacheInfoTableEntry 2 }
    
    snapshotgroupCacheInfoSuspend  OBJECT-TYPE
        SYNTAX  DisplayString
        ACCESS  read-only
        STATUS  mandatory
        DESCRIPTION
            "The group safecache resource is currently suspended or not."
    ::= { snapshotgroupSafeCacheInfoTableEntry 3 }
    
    snapshotgroupCacheInfoTotalSize    OBJECT-TYPE
        SYNTAX  Counter32
        ACCESS  read-only
        STATUS  mandatory
        DESCRIPTION
            "The allocated size when creating the cache resource."
    ::= { snapshotgroupSafeCacheInfoTableEntry 4 }
    
    snapshotgroupCacheInfoFreeSize OBJECT-TYPE
        SYNTAX  Counter32
        ACCESS  read-only
        STATUS  mandatory
        DESCRIPTION
            "The free resource size which is representing in megabyte unit before reaching the maximum resource size."
    ::= { snapshotgroupSafeCacheInfoTableEntry 5 }

    snapshotgroupCacheInfoUsage    OBJECT-TYPE
        SYNTAX  INTEGER
        ACCESS  read-only
        STATUS  mandatory
        DESCRIPTION
            "The percentage of the used resource size."
    ::= { snapshotgroupSafeCacheInfoTableEntry 6 }
    
    snapshotgroupCacheInfoThreshold    OBJECT-TYPE
        SYNTAX  INTEGER
        ACCESS  read-only
        STATUS  mandatory
        DESCRIPTION
            "The data needs to be in the cache before beginning flushing the cache."
    ::= { snapshotgroupSafeCacheInfoTableEntry 7 }
    
    snapshotgroupCacheInfoFlushTime    OBJECT-TYPE
        SYNTAX  INTEGER
        ACCESS  read-only
        STATUS  mandatory
        DESCRIPTION
            "The number of milliseconds before cache begins to flush when below the data threshold level."
    ::= { snapshotgroupSafeCacheInfoTableEntry 8 }
    
    snapshotgroupCacheInfoSkipWriteCommands    OBJECT-TYPE
        SYNTAX  DisplayString
        ACCESS  read-only
        STATUS  mandatory
        DESCRIPTION
            "This option allows the system to skip multiple pending write commands targeted for the same block."
    ::= { snapshotgroupSafeCacheInfoTableEntry 9 }

    snapshotgroupCacheInfoFlushSpeed OBJECT-TYPE
        SYNTAX  INTEGER
        ACCESS  read-only
        STATUS  mandatory
        DESCRIPTION
            "The flush speed will be sent at one time during the flush process."
    ::= { snapshotgroupSafeCacheInfoTableEntry 10 }
    
    snapshotgroupCacheInfoTotalSizeQuantity    OBJECT-TYPE
        SYNTAX  Counter32
        ACCESS  read-only
        STATUS  mandatory
        DESCRIPTION
            "The allocated size quantity when creating the cache resource."
    ::= { snapshotgroupSafeCacheInfoTableEntry 11 }
    
    snapshotgroupCacheInfoTotalSizeUnit    OBJECT-TYPE
        SYNTAX  INTEGER
        ACCESS  read-only
        STATUS  mandatory
        DESCRIPTION
            "The allocated size unit when creating the cache resource. 0 presents KB. 1 presents MB. 2 presents GB. 3 presents TB."
    ::= { snapshotgroupSafeCacheInfoTableEntry 12 }
    
    snapshotgroupCacheInfoFreeSizeQuantity OBJECT-TYPE
        SYNTAX  Counter32
        ACCESS  read-only
        STATUS  mandatory
        DESCRIPTION
            "The free resource size quantity before reaching the maximum resource size."
    ::= { snapshotgroupSafeCacheInfoTableEntry 13 }
    
    snapshotgroupCacheInfoFreeSizeUnit OBJECT-TYPE
        SYNTAX  INTEGER
        ACCESS  read-only
        STATUS  mandatory
        DESCRIPTION
            "The free resource size unit before reaching the maximum resource size. 0 presents KB. 1 presents MB. 2 presents GB. 3 presents TB."
    ::= { snapshotgroupSafeCacheInfoTableEntry 14 }

    snapshotgroupCacheInfoResourceID   OBJECT-TYPE
        SYNTAX  INTEGER
        ACCESS  read-only
        STATUS  mandatory
        DESCRIPTION
            "The Cache resource ID assigned by the IPStor server."
    ::= { snapshotgroupSafeCacheInfoTableEntry 15 }
    
    snapshotgroupCacheInfoTotalSize64    OBJECT-TYPE
        SYNTAX  Counter64
        ACCESS  read-only
        STATUS  mandatory
        DESCRIPTION
            "The allocated size when creating the cache resource."
    ::= { snapshotgroupSafeCacheInfoTableEntry 16 }
    
    snapshotgroupCacheInfoFreeSize64 OBJECT-TYPE
        SYNTAX  Counter64
        ACCESS  read-only
        STATUS  mandatory
        DESCRIPTION
            "The free resource size which is representing in megabyte unit before reaching the maximum resource size."
    ::= { snapshotgroupSafeCacheInfoTableEntry 17 }
    
    snapshotgroupCacheInfoStatus  OBJECT-TYPE
        SYNTAX  DisplayString
        ACCESS  read-only
        STATUS  mandatory
        DESCRIPTION
            "The status of the snapshot group safecache of the IPStor server."
    ::= { snapshotgroupSafeCacheInfoTableEntry 18 }
		
    snapshotgroupMembers	OBJECT-TYPE
	SYNTAX  Counter32
	ACCESS	read-only
	STATUS	mandatory
	DESCRIPTION
	    "The snapshot group member counts of the IPStor server."
    ::= { snapshotgroupResourcesInfoEntry 9 }
		
    snapshotgroupAssignClients	OBJECT-TYPE
	SYNTAX  Counter32
	ACCESS	read-only
	STATUS	mandatory
	DESCRIPTION
	    "The snapshot group assign client counts of the IPStor server."
    ::= { snapshotgroupResourcesInfoEntry 10 }

    snapshotgroupCacheOption   OBJECT-TYPE
        SYNTAX  DisplayString
        ACCESS  read-only
        STATUS  mandatory
        DESCRIPTION
            "The status represents the snapshot group cache option is enable or disable of the IPStor server."
    ::= { snapshotgroupResourcesInfoEntry 11 }

    snapshotgroupReplicationOption   OBJECT-TYPE
        SYNTAX  DisplayString
        ACCESS  read-only
        STATUS  mandatory
        DESCRIPTION
            "The status represents the snapshot group replication option is enable or disable of the IPStor server."
    ::= { snapshotgroupResourcesInfoEntry 12 }

    snapshotgroupTimeMarkOption   OBJECT-TYPE
        SYNTAX  DisplayString
        ACCESS  read-only
        STATUS  mandatory
        DESCRIPTION
            "The status represents the snapshot group timemark option is enable or disable of the IPStor server."
    ::= { snapshotgroupResourcesInfoEntry 13}

    snapshotgroupCDPOption   OBJECT-TYPE
        SYNTAX  DisplayString
        ACCESS  read-only
        STATUS  mandatory
        DESCRIPTION
            "The status represents the snapshot group cdp option is enable or disable of the IPStor server."
    ::= { snapshotgroupResourcesInfoEntry 14 }

    snapshotgroupBackupOption   OBJECT-TYPE
        SYNTAX  DisplayString
        ACCESS  read-only
        STATUS  mandatory
        DESCRIPTION
            "The status represents the snapshot group backup option is enable or disable of the IPStor server."
    ::= { snapshotgroupResourcesInfoEntry 15 }

    snapshotgroupSnapShotOption   OBJECT-TYPE
        SYNTAX  DisplayString
        ACCESS  read-only
        STATUS  mandatory
        DESCRIPTION
            "The status represents the snapshot group snapshot notification option is enable or disable of the IPStor server."
    ::= { snapshotgroupResourcesInfoEntry 16 }


    snapshotgroupMemberTable    OBJECT-TYPE
        SYNTAX  SEQUENCE OF GroupMember
        ACCESS  not-accessible
        STATUS  mandatory
        DESCRIPTION
            "A table containing the members within snapshot groups."
    ::= { snapshotgroupResources 3 }

    snapshotgroupMemberTableEntry OBJECT-TYPE
        SYNTAX  GroupMember
        ACCESS  not-accessible
        STATUS  mandatory
        DESCRIPTION
            "Information about the virtual resource ID in one snapshot group."
        INDEX { snapshotgroupMemberTableIndex }
    ::= { snapshotgroupMemberTable 1 }

    GroupMember ::= SEQUENCE {
        snapshotgroupMemberTableGroupID  INTEGER,
        snapshotgroupMemberTableIndex    INTEGER,
        snapshotgroupMemberTableName     DisplayString
    }
    
    snapshotgroupMemberTableGroupID  OBJECT-TYPE
        SYNTAX  INTEGER
        ACCESS  read-only
        STATUS  mandatory
        DESCRIPTION
            "The snapshot group resource ID assigned by the IPStor server."
    ::= { snapshotgroupMemberTableEntry 1 }
    
    snapshotgroupMemberTableIndex    OBJECT-TYPE
        SYNTAX  INTEGER
        ACCESS  read-only
        STATUS  mandatory
        DESCRIPTION
            "The virtual resource ID assigned by the IPStor server."
    ::= { snapshotgroupMemberTableEntry 2 }

    snapshotgroupMemberTableName OBJECT-TYPE
        SYNTAX  DisplayString
        ACCESS  read-only
        STATUS  mandatory
        DESCRIPTION
            "The virtual resource name created by the user."
    ::= { snapshotgroupMemberTableEntry 3 }

    GlobalSafeCache OBJECT IDENTIFIER ::= { logicalResources 8 }

    GSCsanResourceInfoTable  OBJECT-TYPE
        SYNTAX  SEQUENCE OF GSCsanResourceInfo
        ACCESS  not-accessible
        STATUS  mandatory
        DESCRIPTION
            "A table containing the SAN resources enable the global safe cache option."
    ::= { GlobalSafeCache 1 }
    
    GSCsanResourceNumber  OBJECT-TYPE
        SYNTAX  INTEGER
        ACCESS  read-only
        STATUS  mandatory
        DESCRIPTION
            "The total SAN resource numbers enable the global safe cache."
    ::= { GSCsanResourceInfoTable 1 }
    
    GSCsanResourceInfoEntry OBJECT-TYPE
        SYNTAX  GSCsanResourceInfo
        ACCESS  not-accessible
        STATUS  mandatory
        DESCRIPTION
            "Information about the SAN resources enable the global safe cache option."
        INDEX { GSCsanResourceName }
    ::= { GSCsanResourceInfoTable 2 }

    GSCsanResourceInfo ::= SEQUENCE {
        GSCsanResourceName		DisplayString,
        GSCsanResourceID		INTEGER,
        GSCsanResourceAllocType		DisplayString,
        GSCsanResourceSize		Counter32,
        GSCsanResourceSizeQuantity	Counter32,
        GSCsanResourceSizeUnit		INTEGER,
        GSCsanResourceSize64		Counter64
    }
    
    GSCsanResourceName  OBJECT-TYPE
        SYNTAX  DisplayString
        ACCESS  read-only
        STATUS  mandatory
        DESCRIPTION
            "The SAN resource Name which enables the global safe cache."
    ::= { GSCsanResourceInfoEntry 1 }
    
    GSCsanResourceID  OBJECT-TYPE
        SYNTAX  INTEGER
        ACCESS  read-only
        STATUS  mandatory
        DESCRIPTION
            "The SAN resource ID which enables the global safe cache."
    ::= { GSCsanResourceInfoEntry 2 }
    
    GSCsanResourceAllocType  OBJECT-TYPE
        SYNTAX  DisplayString
        ACCESS  read-only
        STATUS  mandatory
        DESCRIPTION
            "The SAN resource allocation type which enables the global safe cache."
    ::= { GSCsanResourceInfoEntry 3 }
    
    GSCsanResourceSize  OBJECT-TYPE
        SYNTAX  Counter32
        ACCESS  read-only
        STATUS  mandatory
        DESCRIPTION
            "The SAN resource size which is representing with megabyte unit enables the global safe cache."
    ::= { GSCsanResourceInfoEntry 4 }
    
    GSCsanResourceSizeQuantity  OBJECT-TYPE
        SYNTAX  Counter32
        ACCESS  read-only
        STATUS  mandatory
        DESCRIPTION
            "The SAN resource size quantity which enables the global safe cache."
    ::= { GSCsanResourceInfoEntry 5 }
    
    GSCsanResourceSizeUnit  OBJECT-TYPE
        SYNTAX  INTEGER
        ACCESS  read-only
        STATUS  mandatory
        DESCRIPTION
            "The SAN resource size unit which enables the global safe cache. 0 presents KB. 1 presents MB. 2 presents GB. 3 presents TB."
    ::= { GSCsanResourceInfoEntry 6 }
    
    GSCsanResourceSize64  OBJECT-TYPE
        SYNTAX  Counter64
        ACCESS  read-only
        STATUS  mandatory
        DESCRIPTION
            "The SAN resource size which is representing with megabyte unit enables the global safe cache."
    ::= { GSCsanResourceInfoEntry 7 }

	GSCPhysicalTotalAllocLayoutTable  OBJECT-TYPE
		SYNTAX SEQUENCE OF GSCPhysicalTotalAllocLayout
		ACCESS	not-accessible
		STATUS	mandatory
		DESCRIPTION
			"A table containging the total physical layout information for the global safe cache resources."
	::= { GlobalSafeCache 2 }

	GSCPhysicalTotalAllocLayoutEntry    OBJECT-TYPE
		SYNTAX GSCPhysicalTotalAllocLayout
		ACCESS	not-accessible
		STATUS	mandatory
		DESCRIPTION
			"Information about the physical devices allocation layout of global safe cache."
		INDEX { GSCpaAllocSANResourceName }
	::= { GSCPhysicalTotalAllocLayoutTable 1 }

	GSCPhysicalTotalAllocLayout ::= SEQUENCE {
		GSCpaAllocSANResourceName		DisplayString,
		GSCpaAllocName			        DisplayString,
		GSCpaAllocType  		        DisplayString,
		GSCpaAllocAdapterNo		    	INTEGER,
		GSCpaAllocChannelNo		    	INTEGER,
		GSCpaAllocScsiID		        INTEGER,
		GSCpaAllocLun			        INTEGER,
		GSCpaAllocFirstSector		    	Counter32,
		GSCpaAllocLastSector			Counter32,
		GSCpaAllocFirstSector64			Counter64,
		GSCpaAllocLastSector64			Counter64,
		GSCpaAllocSize			        Counter32,
		GSCpaAllocSizeQuantity		        Counter32,
		GSCpaAllocSizeUnit			INTEGER,
		GSCpaAllocSize64			Counter64
	}

	GSCpaAllocSANResourceName    OBJECT-TYPE
		SYNTAX	DisplayString
		ACCESS	read-only
		STATUS	mandatory
		DESCRIPTION
			"The SAN resource name created by the user which enables the global safe cache."
	::= { GSCPhysicalTotalAllocLayoutEntry 1 }

	GSCpaAllocName    OBJECT-TYPE
		SYNTAX	DisplayString
		ACCESS	read-only
		STATUS	mandatory
		DESCRIPTION
			"The physical device name."
	::= { GSCPhysicalTotalAllocLayoutEntry 2 }
	
	GSCpaAllocType OBJECT-TYPE
		SYNTAX	DisplayString
		ACCESS	read-only
		STATUS	mandatory
		DESCRIPTION
			"It represents the type(Primary, or Mirror) of the physical layout."
	::= { GSCPhysicalTotalAllocLayoutEntry 3 }

	GSCpaAllocAdapterNo OBJECT-TYPE
		SYNTAX  INTEGER
		ACCESS	read-only
		STATUS	mandatory
		DESCRIPTION
			"The SCSI adapter number of the physical device."
	::= { GSCPhysicalTotalAllocLayoutEntry 4 }

	GSCpaAllocChannelNo OBJECT-TYPE
		SYNTAX  INTEGER
		ACCESS	read-only
		STATUS	mandatory
		DESCRIPTION
			"The SCSI channel number of the physical device."
	::= { GSCPhysicalTotalAllocLayoutEntry 5 }

	GSCpaAllocScsiID OBJECT-TYPE
		SYNTAX  INTEGER
		ACCESS	read-only
		STATUS	mandatory
		DESCRIPTION
			"The SCSI ID of the physical device."
	::= { GSCPhysicalTotalAllocLayoutEntry 6 }

	GSCpaAllocLun OBJECT-TYPE
		SYNTAX  INTEGER
		ACCESS	read-only
		STATUS	mandatory
		DESCRIPTION
			"The SCSI LUN number of the physical device."
	::= { GSCPhysicalTotalAllocLayoutEntry 7 }

	GSCpaAllocFirstSector OBJECT-TYPE
		SYNTAX  Counter32
		ACCESS	read-only
		STATUS	mandatory
		DESCRIPTION
			"The first sector of the physical device."
	::= { GSCPhysicalTotalAllocLayoutEntry 8 }

	GSCpaAllocLastSector  OBJECT-TYPE
		SYNTAX  Counter32
		ACCESS	read-only
		STATUS	mandatory
		DESCRIPTION
			"The last sector of the physical device."
	::= { GSCPhysicalTotalAllocLayoutEntry 9 }

	GSCpaAllocFirstSector64 OBJECT-TYPE
		SYNTAX  Counter64
		ACCESS	read-only
		STATUS	mandatory
		DESCRIPTION
			"The first sector of the physical device."
	::= { GSCPhysicalTotalAllocLayoutEntry 10 }

	GSCpaAllocLastSector64  OBJECT-TYPE
		SYNTAX  Counter64
		ACCESS	read-only
		STATUS	mandatory
		DESCRIPTION
			"The last sector of the physical device."
	::= { GSCPhysicalTotalAllocLayoutEntry 11 }
		
	GSCpaAllocSize    OBJECT-TYPE
		SYNTAX  Counter32
		ACCESS	read-only
		STATUS	mandatory
		DESCRIPTION
			"The amount of the allocated size which is representing with megabyte unit within a physical device."
	::= { GSCPhysicalTotalAllocLayoutEntry 12 }
		
	GSCpaAllocSizeQuantity    OBJECT-TYPE
		SYNTAX  Counter32
		ACCESS	read-only
		STATUS	mandatory
		DESCRIPTION
			"The amount of the allocated size quantity within a physical device."
	::= { GSCPhysicalTotalAllocLayoutEntry 13 }
		
	GSCpaAllocSizeUnit    OBJECT-TYPE
		SYNTAX  INTEGER
		ACCESS	read-only
		STATUS	mandatory
		DESCRIPTION
			"The amount of the allocated size unit within a physical device. The size unit of the device. 0 presents KB. 1 presents MB. 2 presents GB. 3 presents TB."
	::= { GSCPhysicalTotalAllocLayoutEntry 14 }
		
	GSCpaAllocSize64    OBJECT-TYPE
		SYNTAX  Counter64
		ACCESS	read-only
		STATUS	mandatory
		DESCRIPTION
			"The amount of the allocated size which is representing with megabyte unit within a physical device."
	::= { GSCPhysicalTotalAllocLayoutEntry 15 }

    GSCResourceID  OBJECT-TYPE
        SYNTAX  INTEGER
        ACCESS  read-only
        STATUS  mandatory
        DESCRIPTION
            "The Resource ID of the global safe cache."
    ::= { GlobalSafeCache 3 }

    GSCTotalSize  OBJECT-TYPE
        SYNTAX  Counter32
        ACCESS  read-only
        STATUS  mandatory
        DESCRIPTION
            "The total size of the global safe cache resource."
    ::= { GlobalSafeCache 4 }

    GSCStatus  OBJECT-TYPE
        SYNTAX  DisplayString
        ACCESS  read-only
        STATUS  mandatory
        DESCRIPTION
            "The current status of the global safe cache."
    ::= { GlobalSafeCache 5 }

    GSCSuspend  OBJECT-TYPE
        SYNTAX  DisplayString
        ACCESS  read-only
        STATUS  mandatory
        DESCRIPTION
            "It represents whether the global safe cache is suspended or not."
    ::= { GlobalSafeCache 6 }

    GSCFreeSize  OBJECT-TYPE
        SYNTAX  Counter32
        ACCESS  read-only
        STATUS  mandatory
        DESCRIPTION
            "It represents the free size of the global safe cache resource."
    ::= { GlobalSafeCache 7 }

    GSCFlushSpeed  OBJECT-TYPE
        SYNTAX  INTEGER
        ACCESS  read-only
        STATUS  mandatory
        DESCRIPTION
            "The flush speed setting of the global safe cache resource."
    ::= { GlobalSafeCache 8 }

    GSCSkipDupWriteCommand  OBJECT-TYPE
        SYNTAX  DisplayString
        ACCESS  read-only
        STATUS  mandatory
        DESCRIPTION
            "It represents the skip duplicate write commands option."
    ::= { GlobalSafeCache 9 }

    GSCTotalSizeQuantity  OBJECT-TYPE
        SYNTAX  Counter32
        ACCESS  read-only
        STATUS  mandatory
        DESCRIPTION
            "The total size quantity of the global safe cache resource."
    ::= { GlobalSafeCache 10 }

    GSCTotalSizeUnit  OBJECT-TYPE
        SYNTAX  INTEGER
        ACCESS  read-only
        STATUS  mandatory
        DESCRIPTION
            "The total size unit of the global safe cache resource. 0 presents KB. 1 presents MB. 2 presents GB. 3 presents TB."
    ::= { GlobalSafeCache 11 }

    GSCFreeSizeQuantity  OBJECT-TYPE
        SYNTAX  Counter32
        ACCESS  read-only
        STATUS  mandatory
        DESCRIPTION
            "It represents the free size quantity of the global safe cache resource."
    ::= { GlobalSafeCache 12 }

    GSCFreeSizeUnit  OBJECT-TYPE
        SYNTAX  INTEGER
        ACCESS  read-only
        STATUS  mandatory
        DESCRIPTION
            "It represents the free size unit of the global safe cache resource. 0 presents KB. 1 presents MB. 2 presents GB. 3 presents TB."
    ::= { GlobalSafeCache 13 }

    GSCTotalSize64  OBJECT-TYPE
        SYNTAX  Counter64
        ACCESS  read-only
        STATUS  mandatory
        DESCRIPTION
            "The total size of the global safe cache resource."
    ::= { GlobalSafeCache 14 }

    GSCFreeSize64  OBJECT-TYPE
        SYNTAX  Counter64
        ACCESS  read-only
        STATUS  mandatory
        DESCRIPTION
            "It represents the free size of the global safe cache resource."
    ::= { GlobalSafeCache 15 }

--
-- SAN Clients
--
	sanClients OBJECT IDENTIFIER ::= { ipstorserver 4 }

	numOfSANClients OBJECT-TYPE
		SYNTAX  INTEGER
		ACCESS	read-only
		STATUS	mandatory
		DESCRIPTION
			"The amount of SAN clients authenticated by IPStor server."
	::= { sanClients 1 }

	sanClientTable  OBJECT-TYPE
		SYNTAX  SEQUENCE OF SANClient
		ACCESS	not-accessible
		STATUS	mandatory
		DESCRIPTION
			"A table containing client ID, name, and virtual resources assigned to SAN clients."
	::= { sanClients 2 }

	sanClientEntry  OBJECT-TYPE
		SYNTAX  SANClient
		ACCESS	not-accessible
		STATUS	mandatory
		DESCRIPTION
			"Information about resources assigned to SAN client."
		INDEX { sanClientID }
	::= { sanClientTable 1 }

	SANClient ::= SEQUENCE {
		sanClientID     INTEGER,
		sanClientName	DisplayString,
--		scResourceTable OBJECT IDENTIFIER	
		sanClientType		DisplayString
	}

	sanClientID OBJECT-TYPE
		SYNTAX	INTEGER
		ACCESS	read-only
		STATUS	mandatory
		DESCRIPTION
			"The SAN client ID assigned by the IPStor server."
	::= { sanClientEntry 1 }

	sanClientName   OBJECT-TYPE
		SYNTAX	DisplayString
		ACCESS	read-only
		STATUS	mandatory
		DESCRIPTION
			"The SAN client name assigned by the IPStor server."
	::= { sanClientEntry 2 }

	scResourceTable OBJECT-TYPE
		SYNTAX  SEQUENCE OF SCResource
		ACCESS	not-accessible
		STATUS	mandatory
		DESCRIPTION
			"A table containing SAN resources that assigned to client using SAN/IP protocol."
	::= { sanClientEntry 3 }

	scResourceEntry OBJECT-TYPE
		SYNTAX SCResource
		ACCESS	not-accessible
		STATUS	mandatory
		DESCRIPTION
			"Information about the SAN resources that have been assigned to SAN client."
		INDEX { scResourceID }
	::= { scResourceTable 1 }

	SCResource ::= SEQUENCE {
		scResourceID            INTEGER,
		scResourceName          DisplayString,
		scClientID              INTEGER,
		scClientName            DisplayString,
		scResourceAllocType     DisplayString,
		scResourceAdapterNo     INTEGER,
		scResourceChannelNo     INTEGER,
		scResourceScsiID        INTEGER,
		scResourceLun           INTEGER,
		scResourceSize          INTEGER,
		scResourceTotalSectors  INTEGER,
		scResourceSectorSize    INTEGER,
		scResourceAccess        DisplayString
	}

	scResourceID    OBJECT-TYPE
		SYNTAX  INTEGER
		ACCESS	read-only
		STATUS	mandatory
		DESCRIPTION
			"The SAN resource ID assigned by the IPStor server."
	::= { scResourceEntry 1 }

	scResourceName  OBJECT-TYPE
		SYNTAX  DisplayString
		ACCESS	read-only
		STATUS	mandatory
		DESCRIPTION
			"The SAN resource name created by the user."
	::= { scResourceEntry 2 }

	scClientID  OBJECT-TYPE
		SYNTAX  INTEGER
		ACCESS	read-only
		STATUS	mandatory
		DESCRIPTION
			"The SAN client ID assigned by the IPStor server."
	::= { scResourceEntry 3 }

	scClientName    OBJECT-TYPE
		SYNTAX  DisplayString
		ACCESS	read-only
		STATUS	mandatory
		DESCRIPTION
			"The SAN client name assigned by the IPStor server."
	::= { scResourceEntry 4 }

	scResourceAllocType OBJECT-TYPE
		SYNTAX  DisplayString
		ACCESS	read-only
		STATUS	mandatory
		DESCRIPTION
			"It represents the resource type when user allocating the SAN device."
	::= { scResourceEntry 5 }

	scResourceAdapterNo OBJECT-TYPE
		SYNTAX  INTEGER
		ACCESS	read-only
		STATUS	mandatory
		DESCRIPTION
			"The adapter number of the SAN resource."
	::= { scResourceEntry 6 }

	scResourceChannelNo OBJECT-TYPE
		SYNTAX  INTEGER
		ACCESS	read-only
		STATUS	mandatory
		DESCRIPTION
			"The channel number of the SAN resource."
	::= { scResourceEntry 7 }

	scResourceScsiID    OBJECT-TYPE
		SYNTAX  INTEGER
		ACCESS	read-only
		STATUS	mandatory
		DESCRIPTION
			"The SCSI ID of the SAN resource."
	::= { scResourceEntry 8 }

	scResourceLun   OBJECT-TYPE
		SYNTAX  INTEGER
		ACCESS	read-only
		STATUS	mandatory
		DESCRIPTION
			"The SCSI LUN number of the SAN resource."
	::= { scResourceEntry 9 }

	scResourceSize  OBJECT-TYPE
		SYNTAX  INTEGER
		ACCESS	read-only
		STATUS	mandatory
		DESCRIPTION
			"The amount of device size which is representing with megabyte unit of the SAN resource."
	::= { scResourceEntry 10 }

	scResourceTotalSectors  OBJECT-TYPE
		SYNTAX  INTEGER
		ACCESS	read-only
		STATUS	mandatory
		DESCRIPTION
			"The amount of sectors allocated by the SAN resource."
	::= { scResourceEntry 11 }

	scResourceSectorSize    OBJECT-TYPE
		SYNTAX  INTEGER
		ACCESS	read-only
		STATUS	mandatory
		DESCRIPTION
			"The size of bytes for each sector or block."
	::= { scResourceEntry 12 }

	scResourceAccess    OBJECT-TYPE
		SYNTAX  DisplayString
		ACCESS	read-only
		STATUS	mandatory
		DESCRIPTION
			"The SAN resource accessing mode assigned to the SAN client."
	::= { scResourceEntry 13 }

	scFCResourceTable   OBJECT-TYPE
		SYNTAX  SEQUENCE OF SCFCResource
		ACCESS	not-accessible
		STATUS	mandatory
		DESCRIPTION
			"A table containing client ID, name, and virtual resources assigned to Fibre Channel clients."
	::= { sanClientEntry 4 }

	scFCResourceEntry   OBJECT-TYPE
		SYNTAX SCFCResource
		ACCESS	not-accessible
		STATUS	mandatory
		DESCRIPTION
			"Information about the SAN resources that have been assigned to Fibre Channel client."
		INDEX { scfcResourceID }
	::= { scFCResourceTable 1 }

	SCFCResource ::= SEQUENCE {
		scfcResourceID			INTEGER,
		scfcResourceName		DisplayString,
		scfcClientID			INTEGER,
		scfcClientName			DisplayString,
		scfcResourceAllocType		DisplayString,
		scfcLUN				INTEGER,
		scfcInitatorWWPN		DisplayString,
		scfcTargetWWPN			DisplayString,
		scfcAccess			DisplayString,
		scfcTotalsize			Counter32,
		scfcTotalSectors		Counter32,
		scfcSectorSize			INTEGER,
		scfcTotalsize64			Counter64,
		scfcTotalSectors64		Counter64,
		scfcTotalsizeQuantity		Counter32,
		scfcTotalsizeUnit		INTEGER
	}

	scfcResourceID OBJECT-TYPE
		SYNTAX  INTEGER
		ACCESS	read-only
		STATUS	mandatory
		DESCRIPTION
			"The unique resource ID that assigned by IPStor server."
	::= { scFCResourceEntry 1 }

	scfcResourceName    OBJECT-TYPE
		SYNTAX  DisplayString
		ACCESS	read-only
		STATUS	mandatory
		DESCRIPTION
			"The resource name that created by user."
	::= { scFCResourceEntry 2 }

	scfcClientID    OBJECT-TYPE
		SYNTAX  INTEGER
		ACCESS	read-only
		STATUS	mandatory
		DESCRIPTION
			"The unique client ID that assigned by IPStor server."
	::= { scFCResourceEntry 3 }

	scfcClientName  OBJECT-TYPE
		SYNTAX  DisplayString
		ACCESS	read-only
		STATUS	mandatory
		DESCRIPTION
			"The client name that created by user."
	::= { scFCResourceEntry 4 }

	scfcResourceAllocType   OBJECT-TYPE
		SYNTAX  DisplayString
		ACCESS	read-only
		STATUS	mandatory
		DESCRIPTION
			"It represents the resource type when user allocating the SAN device."
	::= { scFCResourceEntry 5 }

	scfcLUN OBJECT-TYPE
		SYNTAX  INTEGER
		ACCESS	read-only
		STATUS	mandatory
		DESCRIPTION
			"The SCSI LUN number that assigned to the resource."
	::= { scFCResourceEntry 6 }

	scfcInitatorWWPN    OBJECT-TYPE
		SYNTAX  DisplayString
		ACCESS	read-only
		STATUS	mandatory
		DESCRIPTION
			"The initiator world wide port name(WWPN) of the resource."
	::= { scFCResourceEntry 7 }

	scfcTargetWWPN  OBJECT-TYPE
		SYNTAX  DisplayString
		ACCESS	read-only
		STATUS	mandatory
		DESCRIPTION
			"The target world wide port name(WWPN) of the resource."
	::= { scFCResourceEntry 8 }

	scfcAccess  OBJECT-TYPE
		SYNTAX  DisplayString
		ACCESS	read-only
		STATUS	mandatory
		DESCRIPTION
			"The access rights of the resource."
	::= { scFCResourceEntry 9 }

	scfcTotalsize   OBJECT-TYPE
		SYNTAX  Counter32
		ACCESS	read-only
		STATUS	mandatory
		DESCRIPTION
			"The amount of device size which is representing with megabyte unit of the resource."
	::= { scFCResourceEntry 10 }

	scfcTotalSectors    OBJECT-TYPE
		SYNTAX  Counter32
		ACCESS	read-only
		STATUS	mandatory
		DESCRIPTION
			"Total sectors allocated of the resource."
	::= { scFCResourceEntry 11 }

	scfcSectorSize  OBJECT-TYPE
		SYNTAX  INTEGER
		ACCESS	read-only
		STATUS	mandatory
		DESCRIPTION
			"The size of bytes per sector or block."
	::= { scFCResourceEntry 12 }

	scfcTotalsize64   OBJECT-TYPE
		SYNTAX  Counter64
		ACCESS	read-only
		STATUS	mandatory
		DESCRIPTION
			"The amount of device size which is representing with megabyte unit of the resource."
	::= { scFCResourceEntry 13 }

	scfcTotalSectors64    OBJECT-TYPE
		SYNTAX  Counter64
		ACCESS	read-only
		STATUS	mandatory
		DESCRIPTION
			"Total sectors allocated of the resource."
	::= { scFCResourceEntry 14 }

	scfcTotalsizeQuantity  OBJECT-TYPE
		SYNTAX  Counter32
		ACCESS  read-only
		STATUS  mandatory
		DESCRIPTION
            "The amount of device size quantity of the resource."
	::= { scFCResourceEntry 15 }

	scfcTotalsizeUnit  OBJECT-TYPE
		SYNTAX  INTEGER
		ACCESS  read-only
		STATUS  mandatory
		DESCRIPTION
            "The amount of device size unit of the resource. 0 presents KB. 1 presents MB. 2 presents GB. 3 presents TB."
	::= { scFCResourceEntry 16 }

	scBootIPTable   OBJECT-TYPE
		SYNTAX  SEQUENCE OF SCBootIPClient
		ACCESS	not-accessible
		STATUS	mandatory
		DESCRIPTION
			"A table containing IP Address, MAC address , and Default Boot clients which enable the BootIP option."
	::= { sanClientEntry 6 }

	scBootIPEntry   OBJECT-TYPE
		SYNTAX SCBootIPClient
		ACCESS	not-accessible
		STATUS	mandatory
		DESCRIPTION
			"Information about the SAN client that enable the BootIP option."
		INDEX { scbootipIPAddress }
	::= { scBootIPTable 1 }

	SCBootIPClient ::= SEQUENCE {
		scbootipIPAddress		DisplayString,
		scbootipMAC			DisplayString,
		scbootipDefaultBoot		DisplayString
	}

	scbootipIPAddress OBJECT-TYPE
		SYNTAX  DisplayString
		ACCESS	read-only
		STATUS	mandatory
		DESCRIPTION
			"The IP address setting of BootIP option."
	::= { scBootIPEntry 1 }

	scbootipMAC OBJECT-TYPE
		SYNTAX  DisplayString
		ACCESS	read-only
		STATUS	mandatory
		DESCRIPTION
			"The MAC address setting of BootIP option."
	::= { scBootIPEntry 2 }

	scbootipDefaultBoot OBJECT-TYPE
		SYNTAX  DisplayString
		ACCESS	read-only
		STATUS	mandatory
		DESCRIPTION
			"The default boot setting of BootIP option."
	::= { scBootIPEntry 3 }

	sanClientType    OBJECT-TYPE
		SYNTAX  DisplayString
		ACCESS	read-only
		STATUS	mandatory
		DESCRIPTION
			"The SAN Client Type set to the IPStor server."
	::= { sanClientEntry 7 }

	sanClientPersistentReserv    OBJECT-TYPE
		SYNTAX  DisplayString
		ACCESS	read-only
		STATUS	mandatory
		DESCRIPTION
			"The SAN Client Persistent Reservation option to the IPStor server."
	::= { sanClientEntry 8 }

	sanClientIsClusted    OBJECT-TYPE
		SYNTAX  DisplayString
		ACCESS	read-only
		STATUS	mandatory
		DESCRIPTION
			"The SAN Client is clusted set to the IPStor server."
	::= { sanClientEntry 9 }

	scISCSIResourceTable   OBJECT-TYPE
		SYNTAX  SEQUENCE OF SCISCSIResource
		ACCESS	not-accessible
		STATUS	mandatory
		DESCRIPTION
			"A table containing client ID, name, and virtual resources assigned to iSCSI clients."
	::= { sanClientEntry 10 }

	scISCSIResourceEntry   OBJECT-TYPE
		SYNTAX  SCISCSIResource
		ACCESS	not-accessible
		STATUS	mandatory
		DESCRIPTION
			"Information about the SAN resources that have been assigned to iSCSI client."
		INDEX { sciscsiResourceID }
	::= { scISCSIResourceTable 1 }

	SCISCSIResource ::= SEQUENCE {
		sciscsiResourceID			INTEGER,
		sciscsiResourceName			DisplayString,
		sciscsiClientID				INTEGER,
		sciscsiClientName			DisplayString,
		sciscsiResourceAllocType		DisplayString,
		sciscsiLUN				INTEGER,
		sciscsiAuthentication			DisplayString,
		sciscsiAuthDefaultUser			DisplayString,
		sciscsiAuthAdditionalUser		DisplayString,
		sciscsiMutualCHAPSecret			DisplayString,
		sciscsiInitiatorName			DisplayString,
		sciscsiInitiatorAccessType		DisplayString,
		sciscsiTargetID				INTEGER,
		sciscsiTargetName			DisplayString,
		sciscsiTargetIP				DisplayString,
		sciscsiAcessRight			DisplayString,
		sciscsiTotalsize			Counter32,
		sciscsiTotalSectors			Counter32,
		sciscsiSectorSize			INTEGER,
		sciscsiTotalsize64			Counter64,
		sciscsiTotalSectors64			Counter64,
		sciscsiTotalsizeQuantity		Counter32,
		sciscsiTotalsizeUnit			INTEGER
	}

	sciscsiResourceID OBJECT-TYPE
		SYNTAX  INTEGER
		ACCESS	read-only
		STATUS	mandatory
		DESCRIPTION
			"The unique resource ID that assigned by IPStor server."
	::= { scISCSIResourceEntry 1 }

	sciscsiResourceName    OBJECT-TYPE
		SYNTAX  DisplayString
		ACCESS	read-only
		STATUS	mandatory
		DESCRIPTION
			"The resource name that created by user."
	::= { scISCSIResourceEntry 2 }

	sciscsiClientID    OBJECT-TYPE
		SYNTAX  INTEGER
		ACCESS	read-only
		STATUS	mandatory
		DESCRIPTION
			"The unique client ID that assigned by IPStor server."
	::= { scISCSIResourceEntry 3 }

	sciscsiClientName  OBJECT-TYPE
		SYNTAX  DisplayString
		ACCESS	read-only
		STATUS	mandatory
		DESCRIPTION
			"The client name that created by user."
	::= { scISCSIResourceEntry 4 }

	sciscsiResourceAllocType   OBJECT-TYPE
		SYNTAX  DisplayString
		ACCESS	read-only
		STATUS	mandatory
		DESCRIPTION
			"It represents the resource type when user allocating the SAN device."
	::= { scISCSIResourceEntry 5 }

	sciscsiLUN	OBJECT-TYPE
		SYNTAX  INTEGER
		ACCESS	read-only
		STATUS	mandatory
		DESCRIPTION
			"The SCSI LUN number that assigned to the resource."
	::= { scISCSIResourceEntry 6 }

	sciscsiAuthentication	OBJECT-TYPE
		SYNTAX  DisplayString
		ACCESS	read-only
		STATUS	mandatory
		DESCRIPTION
			"The authentication of the iSCSI client."
	::= { scISCSIResourceEntry 7 }

	sciscsiAuthDefaultUser	OBJECT-TYPE
		SYNTAX  DisplayString
		ACCESS	read-only
		STATUS	mandatory
		DESCRIPTION
			"The default user when authentication enabled of the iSCSI client."
	::= { scISCSIResourceEntry 8 }

	sciscsiAuthAdditionalUser	OBJECT-TYPE
		SYNTAX  DisplayString
		ACCESS	read-only
		STATUS	mandatory
		DESCRIPTION
			"The additional user when authentication enabled of the iSCSI client."
	::= { scISCSIResourceEntry 9 }

	sciscsiMutualCHAPSecret	OBJECT-TYPE
		SYNTAX  DisplayString
		ACCESS	read-only
		STATUS	mandatory
		DESCRIPTION
			"The mutual CHAP secret option when authentication enabled of the iSCSI client."
	::= { scISCSIResourceEntry 10 }

	sciscsiInitiatorName	OBJECT-TYPE
		SYNTAX  DisplayString
		ACCESS	read-only
		STATUS	mandatory
		DESCRIPTION
			"The Initiator name of the iSCSI client."
	::= { scISCSIResourceEntry 11 }

	sciscsiInitiatorAccessType	OBJECT-TYPE
		SYNTAX  DisplayString
		ACCESS	read-only
		STATUS	mandatory
		DESCRIPTION
			"The Initiator access type of the iSCSI client."
	::= { scISCSIResourceEntry 12 }

	sciscsiTargetID   OBJECT-TYPE
		SYNTAX  INTEGER
		ACCESS	read-only
		STATUS	mandatory
		DESCRIPTION
			"The target ID belongs to the iSCSI client."
	::= { scISCSIResourceEntry 13 }

	sciscsiTargetName	OBJECT-TYPE
		SYNTAX  DisplayString
		ACCESS	read-only
		STATUS	mandatory
		DESCRIPTION
			"The target name belongs to the iSCSI client."
	::= { scISCSIResourceEntry 14 }

	sciscsiTargetIP		OBJECT-TYPE
		SYNTAX  DisplayString
		ACCESS	read-only
		STATUS	mandatory
		DESCRIPTION
			"The target IP address of the iSCSI client."
	::= { scISCSIResourceEntry 15 }

	sciscsiAcessRight	OBJECT-TYPE
		SYNTAX  DisplayString
		ACCESS	read-only
		STATUS	mandatory
		DESCRIPTION
			"The target access rights of the iSCSI client."
	::= { scISCSIResourceEntry 16 }

	sciscsiTotalsize   OBJECT-TYPE
		SYNTAX  Counter32
		ACCESS	read-only
		STATUS	mandatory
		DESCRIPTION
			"The amount of device size which is representing with megabyte unit of the resource."
	::= { scISCSIResourceEntry 17 }

	sciscsiTotalSectors    OBJECT-TYPE
		SYNTAX  Counter32
		ACCESS	read-only
		STATUS	mandatory
		DESCRIPTION
			"Total sectors allocated of the resource."
	::= { scISCSIResourceEntry 18 }

	sciscsiSectorSize  OBJECT-TYPE
		SYNTAX  INTEGER
		ACCESS	read-only
		STATUS	mandatory
		DESCRIPTION
			"The size of bytes per sector or block."
	::= { scISCSIResourceEntry 19 }

	sciscsiTotalsize64   OBJECT-TYPE
		SYNTAX  Counter64
		ACCESS	read-only
		STATUS	mandatory
		DESCRIPTION
			"The amount of device size which is representing with megabyte unit of the resource."
	::= { scISCSIResourceEntry 20 }

	sciscsiTotalSectors64    OBJECT-TYPE
		SYNTAX  Counter64
		ACCESS	read-only
		STATUS	mandatory
		DESCRIPTION
			"Total sectors allocated of the resource."
	::= { scISCSIResourceEntry 21 }

	sciscsiTotalsizeQuantity  OBJECT-TYPE
		SYNTAX  Counter32
		ACCESS  read-only
		STATUS  mandatory
		DESCRIPTION
            "The amount of device size quantity of the resource."
	::= { scISCSIResourceEntry 22 }

	sciscsiTotalsizeUnit  OBJECT-TYPE
		SYNTAX  INTEGER
		ACCESS  read-only
		STATUS  mandatory
		DESCRIPTION
            "The amount of device size unit of the resource. 0 presents KB. 1 presents MB. 2 presents GB. 3 presents TB."
	::= { scISCSIResourceEntry 23 }


--
-- NAS Clients
--
	nasClients OBJECT IDENTIFIER ::= { ipstorserver 5 }

	windowsClients OBJECT IDENTIFIER ::= { nasClients 1 }

	wcServerName OBJECT-TYPE
		SYNTAX  DisplayString
		ACCESS	read-only
		STATUS	mandatory
		DESCRIPTION
			"NAS server name."
	::= { windowsClients 1 }

	wcComment OBJECT-TYPE
		SYNTAX  DisplayString
		ACCESS	read-only
		STATUS	mandatory
		DESCRIPTION
			"Comment."
	::= { windowsClients 2 }
	
	wcDomain OBJECT-TYPE
		SYNTAX  DisplayString
		ACCESS	read-only
		STATUS	mandatory
		DESCRIPTION
			"Workgroup."
	::= { windowsClients 3 }

	wcAuthServer OBJECT-TYPE
		SYNTAX  DisplayString
		ACCESS	read-only
		STATUS	mandatory
		DESCRIPTION
			"Authentication Server."
	::= { windowsClients 4 }

	wcBackupAuthServer OBJECT-TYPE
		SYNTAX  DisplayString
		ACCESS	read-only
		STATUS	mandatory
		DESCRIPTION
			"Backup Authentication Server."
	::= { windowsClients 5 }
	
	wcAuthMode OBJECT-TYPE
		SYNTAX  DisplayString
		ACCESS	read-only
		STATUS	mandatory
		DESCRIPTION
			"Authentication Mode, included Share Mode, Server Mode or
			 Domain Mode."
	::= { windowsClients 6 }
	
	wcUIDRangeTable OBJECT-TYPE
		SYNTAX  SEQUENCE OF UIDRanges
		ACCESS	not-accessible
		STATUS	mandatory
		DESCRIPTION
			"A list of UID range of windows clients."
	::= { windowsClients 7 }

	wcUIDRangeEntry OBJECT-TYPE
		SYNTAX  UIDRanges
		ACCESS	not-accessible
		STATUS	mandatory
		DESCRIPTION
			"A list of UID range of windows clients."
		INDEX { wcUIDRange }
	::= { wcUIDRangeTable 1 }

	UIDRanges ::= SEQUENCE {
		wcUIDRange	DisplayString
	}

	wcUIDRange OBJECT-TYPE
		SYNTAX  DisplayString
		ACCESS	read-only
		STATUS	mandatory
		DESCRIPTION
			"UID Range."
	::= { wcUIDRangeEntry 1 }
	
	wcGIDRangeTable OBJECT-TYPE
		SYNTAX  SEQUENCE OF GIDRanges
		ACCESS	not-accessible
		STATUS	mandatory
		DESCRIPTION
			"A list of GID range of windows clients."
	::= { windowsClients 8 }

	wcGIDRangeEntry OBJECT-TYPE
		SYNTAX  GIDRanges
		ACCESS	not-accessible
		STATUS	mandatory
		DESCRIPTION
			"A list of GID range of windows clients."
		INDEX { wcGIDRange }
	::= { wcGIDRangeTable 1 }

	GIDRanges ::= SEQUENCE {
		wcGIDRange	DisplayString
	}

	wcGIDRange OBJECT-TYPE
		SYNTAX  DisplayString
		ACCESS	read-only
		STATUS	mandatory
		DESCRIPTION
			"GID Range."
	::= { wcGIDRangeEntry 1 }

--	wcAccountsSyncStatus OBJECT-TYPE
--		SYNTAX  DisplayString
--		ACCESS	read-only
--		STATUS	mandatory
--		DESCRIPTION
--			"Accounts Synchronization Status."
--	::= { windowsClients 9 }
	
	wcNetBiosAliasTable OBJECT-TYPE
		SYNTAX  SEQUENCE OF NetBiosAliases
		ACCESS	not-accessible
		STATUS	mandatory
		DESCRIPTION
			"A list of NetBios Alias of windows clients."
	::= { windowsClients 10 }

	wcNetBiosAliasEntry OBJECT-TYPE
		SYNTAX  NetBiosAliases
		ACCESS	not-accessible
		STATUS	mandatory
		DESCRIPTION
			"A list of NetBios Alias of windows clients."
		INDEX { wcNetBiosAlias }
	::= { wcNetBiosAliasTable 1 }

	NetBiosAliases ::= SEQUENCE {
		wcNetBiosAlias	DisplayString
	}

	wcNetBiosAlias OBJECT-TYPE
		SYNTAX  DisplayString
		ACCESS	read-only
		STATUS	mandatory
		DESCRIPTION
			"NetBios Alias."
	::= { wcNetBiosAliasEntry 1 }

	wcUsers OBJECT IDENTIFIER ::= { windowsClients 11 }

	numOfUsers OBJECT-TYPE
		SYNTAX  INTEGER
		ACCESS	read-only
		STATUS	mandatory
		DESCRIPTION
			"Total number of users."
	::= { wcUsers 1 }
	
	wcUsersTable OBJECT-TYPE
		SYNTAX  SEQUENCE OF UUsers
		ACCESS	not-accessible
		STATUS	mandatory
		DESCRIPTION
			"A list of users of windows clients."
	::= { wcUsers 2 }

	wcUsersEntry OBJECT-TYPE
		SYNTAX  UUsers
		ACCESS	not-accessible
		STATUS	mandatory
		DESCRIPTION
			"A list of users of windows clients."
		INDEX { wcUserIndex }
	::= { wcUsersTable 1 }

	UUsers ::= SEQUENCE {
		wcUserIndex		INTEGER,
		wcUserName		DisplayString,
		wcUserDescription	DisplayString
	}
	
	wcUserIndex OBJECT-TYPE
		SYNTAX  INTEGER
		ACCESS	read-only
		STATUS	mandatory
		DESCRIPTION
			"Windows user index."
	::= { wcUsersEntry 1 }
	
	wcUserName OBJECT-TYPE
		SYNTAX  DisplayString
		ACCESS	read-only
		STATUS	mandatory
		DESCRIPTION
			"User name of this windows client."
	::= { wcUsersEntry 2 }

	wcUserDescription OBJECT-TYPE
		SYNTAX  DisplayString
		ACCESS	read-only
		STATUS	mandatory
		DESCRIPTION
			"Description of this user."
	::= { wcUsersEntry 3 }

--	wcUserSharesTable OBJECT-TYPE
--		SYNTAX  SEQUENCE OF UUserShares
--		ACCESS	not-accessible
--		STATUS	mandatory
--		DESCRIPTION
--			" List all folders that shared to the users. "
--	::= { wcUsers 3 }

--	wcUserSharesEntry OBJECT-TYPE
--		SYNTAX  UUserShares
--		ACCESS	not-accessible
--		STATUS	mandatory
--		DESCRIPTION
--			" Folders list. "
--		INDEX { wcusIndex }
--	::= { wcUserSharesTable 1 }

--	UUserShares ::= SEQUENCE {
--		wcusIndex	INTEGER,
--		wcusUserName    DisplayString,
--		wcusShareName	DisplayString,
--		wcusComment	DisplayString,
--		wcusAccessRight	DisplayString,
--		wcusDeriveFrom	DisplayString
--	}
	
--	wcusIndex OBJECT-TYPE
--		SYNTAX  INTEGER
--		ACCESS	read-only
--		STATUS	mandatory
--		DESCRIPTION
--			" Index. "
--	::= { wcUserSharesEntry 1 }

--	wcusUserName OBJECT-TYPE
--		SYNTAX  DisplayString
--		ACCESS	read-only
--		STATUS	mandatory
--		DESCRIPTION
--			" This folder can share to which user. "
--	::= { wcUserSharesEntry 2 }

--	wcusShareName OBJECT-TYPE
--		SYNTAX  DisplayString
--		ACCESS	read-only
--		STATUS	mandatory
--		DESCRIPTION
--			" The share name of the folder. "
--	::= { wcUserSharesEntry 3 }

--	wcusComment OBJECT-TYPE
--		SYNTAX  DisplayString
--		ACCESS	read-only
--		STATUS	mandatory
--		DESCRIPTION
--			" The comment of this folder. "
--	::= { wcUserSharesEntry 4 }

--	wcusAccessRight OBJECT-TYPE
--		SYNTAX  DisplayString
--		ACCESS	read-only
--		STATUS	mandatory
--		DESCRIPTION
--			" The access right of this user. "
--	::= { wcUserSharesEntry 5 }

--	wcusDeriveFrom OBJECT-TYPE
--		SYNTAX  DisplayString
--		ACCESS	read-only
--		STATUS	mandatory
--		DESCRIPTION
--			" Derive from which folder. "
--	::= { wcUserSharesEntry 6 }

--	wcUserQuotaUsageTable OBJECT-TYPE
--		SYNTAX  SEQUENCE OF UUserQuotaUsage
--		ACCESS	not-accessible
--		STATUS	mandatory
--		DESCRIPTION
--			" List all the device name that this user's quota. "
--	::= { wcUsers 4 }

--	wcUserQuotaUsageEntry OBJECT-TYPE
--		SYNTAX  UUserQuotaUsage
--		ACCESS	not-accessible
--		STATUS	mandatory
--		DESCRIPTION
--			" List all the device name. "
--		INDEX { wcusIndex }
--	::= { wcUserQuotaUsageTable 1 }

--	UUserQuotaUsage ::= SEQUENCE {
--		wcquIndex	INTEGER,
--		wcquUserName    DisplayString,
--		wcquDeviceName	DisplayString,
--		wcquUsedSpace	DisplayString
--	}
	
--	wcquIndex OBJECT-TYPE
--		SYNTAX  INTEGER
--		ACCESS	read-only
--		STATUS	mandatory
--		DESCRIPTION
--			" The index. "
--	::= { wcUserQuotaUsageEntry 1 }

--	wcquUserName OBJECT-TYPE
--		SYNTAX  DisplayString
--		ACCESS	read-only
--		STATUS	mandatory
--		DESCRIPTION
--			" This deivce can be assigned to which user. "
--	::= { wcUserQuotaUsageEntry 2 }

--	wcquDeviceName OBJECT-TYPE
--		SYNTAX  DisplayString
--		ACCESS	read-only
--		STATUS	mandatory
--		DESCRIPTION
--			" Which device assigned to the user. "
--	::= { wcUserQuotaUsageEntry 3 }

--	wcquUsedSpace OBJECT-TYPE
--		SYNTAX  DisplayString
--		ACCESS	read-only
--		STATUS	mandatory
--		DESCRIPTION
--			" The used space of this device. "
--	::= { wcUserQuotaUsageEntry 4 }

	wcGroups OBJECT IDENTIFIER ::= { windowsClients 12 }

	numOfGroups OBJECT-TYPE
		SYNTAX  INTEGER
		ACCESS	read-only
		STATUS	mandatory
		DESCRIPTION
			"Total number of groups."
	::= { wcGroups 1 }
	
	wcGroupsTable OBJECT-TYPE
		SYNTAX  SEQUENCE OF WCGroups
		ACCESS	not-accessible
		STATUS	mandatory
		DESCRIPTION
			" A list of groups of windows clients. "
	::= { wcGroups 2 }

	wcGroupsEntry OBJECT-TYPE
		SYNTAX  WCGroups
		ACCESS	not-accessible
		STATUS	mandatory
		DESCRIPTION
			" List of the gropus. "
		INDEX { wcGroupIndex }
	::= { wcGroupsTable 1 }

	WCGroups ::= SEQUENCE {
		wcGroupIndex		INTEGER,
		wcGroupName		DisplayString,
		wcGroupDescription	DisplayString
	}
	
	wcGroupIndex OBJECT-TYPE
		SYNTAX  INTEGER
		ACCESS	read-only
		STATUS	mandatory
		DESCRIPTION
			" Ths index. "
	::= { wcGroupsEntry 1 }
	
	wcGroupName OBJECT-TYPE
		SYNTAX  DisplayString
		ACCESS	read-only
		STATUS	mandatory
		DESCRIPTION
			" The group name. "
	::= { wcGroupsEntry 2 }
	
	wcGroupDescription OBJECT-TYPE
		SYNTAX  DisplayString
		ACCESS	read-only
		STATUS	mandatory
		DESCRIPTION
			" The group description. "
	::= { wcGroupsEntry 3 }

--	wcGroupUserTable OBJECT-TYPE
--		SYNTAX  SEQUENCE OF WCGroupUsers
--		ACCESS	not-accessible
--		STATUS	mandatory
--		DESCRIPTION
--			" A list of users in group of windows clients. "
--	::= { wcGroups 3 }

--	wcGroupUsersEntry OBJECT-TYPE
--		SYNTAX  WCGroupUsers
--		ACCESS	not-accessible
--		STATUS	mandatory
--		DESCRIPTION
--			"  "
--		INDEX { wcguIndex }
--	::= { wcGroupUserTable 1 }

--	WCGroupUsers ::= SEQUENCE {
--		wcguIndex	INTEGER,
--		wcguGroupName   DisplayString,
--		wcguUserName    DisplayString,
--		wcguDescription DisplayString
--	}	
	
--	wcguIndex OBJECT-TYPE
--		SYNTAX  INTEGER
--		ACCESS	read-only
--		STATUS	mandatory
--		DESCRIPTION
--			" Ths index. "
--	::= { wcGroupUsersEntry 1 }
	
--	wcguGroupName OBJECT-TYPE
--		SYNTAX  DisplayString
--		ACCESS	read-only
--		STATUS	mandatory
--		DESCRIPTION
--			" The group name. "
--	::= { wcGroupUsersEntry 2 }
	
--	wcguUserName OBJECT-TYPE
--		SYNTAX  DisplayString
--		ACCESS	read-only
--		STATUS	mandatory
--		DESCRIPTION
--			" The user name of this group. "
--	::= { wcGroupUsersEntry 3 }
--	
--	wcguDescription OBJECT-TYPE
--		SYNTAX  DisplayString
--		ACCESS	read-only
--		STATUS	mandatory
--		DESCRIPTION
--			" The user description of this group. "
--	::= { wcGroupUsersEntry 4 }

--	wcGroupSharesTable OBJECT-TYPE
--		SYNTAX  SEQUENCE OF WCGroupShares
--		ACCESS	not-accessible
--		STATUS	mandatory
--		DESCRIPTION
--			" A list all the share folders for the group. "
--	::= { wcGroups 4 }

--	wcGroupSharesEntry OBJECT-TYPE
--		SYNTAX  WCGroupShares
--		ACCESS	not-accessible
--		STATUS	mandatory
--		DESCRIPTION
--			" List all the share folders. "
--		INDEX { wcgsIndex }
--	::= { wcGroupSharesTable 1 }

--	WCGroupShares ::= SEQUENCE {
--		wcgsIndex	    INTEGER,
--		wcgsGroupName   DisplayString,
--		wcgsShareName   DisplayString,
--		wcgsComment     DisplayString,
--		wcgsAccessRight DisplayString,
--		wcgsFolderName  DisplayString,
--		wcgsRealPath    DisplayString,
--		wcgsMaximumConn DisplayString
--	}	

--	wcgsIndex OBJECT-TYPE
--		SYNTAX  INTEGER
--		ACCESS	read-only
--		STATUS	mandatory
--		DESCRIPTION
--			" The Index. "
--	::= { wcGroupSharesEntry 1 }
	
--	wcgsGroupName OBJECT-TYPE
--		SYNTAX  DisplayString
--		ACCESS	read-only
--		STATUS	mandatory
--		DESCRIPTION
--			" This group cantains which share folders. "
--	::= { wcGroupSharesEntry 2 }
	
--	wcgsShareName OBJECT-TYPE
--		SYNTAX  DisplayString
--		ACCESS	read-only
--		STATUS	mandatory
--		DESCRIPTION
--			" The share folder name. "
--	::= { wcGroupSharesEntry 3 }	

--	wcgsComment OBJECT-TYPE
--		SYNTAX  DisplayString
--		ACCESS	read-only
--		STATUS	mandatory
--		DESCRIPTION
--			" The share comment. "
--	::= { wcGroupSharesEntry 4 }	
	
--	wcgsAccessRight OBJECT-TYPE
--		SYNTAX  DisplayString
--		ACCESS	read-only
--		STATUS	mandatory
--		DESCRIPTION
--			" The access right of the folder. "
--	::= { wcGroupSharesEntry 5 }		

--	wcgsFolderName OBJECT-TYPE
--		SYNTAX  DisplayString
--		ACCESS	read-only
--		STATUS	mandatory
--		DESCRIPTION
--			" The folder name. "
--	::= { wcGroupSharesEntry 6 }		

--	wcgsRealPath OBJECT-TYPE
--		SYNTAX  DisplayString
--		ACCESS	read-only
--		STATUS	mandatory
--		DESCRIPTION
--			" The folder read path. "
--	::= { wcGroupSharesEntry 7 }		

--	wcgsMaximumConn OBJECT-TYPE
--		SYNTAX  DisplayString
--		ACCESS	read-only
--		STATUS	mandatory
--		DESCRIPTION
--			" The Maximum Connection of this Share"
--	::= { wcGroupSharesEntry 8 }		

	wcConnections OBJECT IDENTIFIER ::= { windowsClients 13 }

	numOfConnections OBJECT-TYPE
		SYNTAX  INTEGER
		ACCESS	read-only
		STATUS	mandatory
		DESCRIPTION
			"Total number of connections."
	::= { wcConnections 1 }
		
	wcConnectionsTable OBJECT-TYPE
		SYNTAX  SEQUENCE OF WCConnections
		ACCESS	not-accessible
		STATUS	mandatory
		DESCRIPTION
			" A list all connection(s) of windows clients.
			  The data is the real-time status.  "
	::= { wcConnections 2 }

	wcConnectionsEntry OBJECT-TYPE
		SYNTAX  WCConnections
		ACCESS	not-accessible
		STATUS	mandatory
		DESCRIPTION
			" List all connection(s). "
		INDEX { wcConnIndex }
	::= { wcConnectionsTable 1 }

	WCConnections ::= SEQUENCE {
		wcConnIndex	INTEGER,
		wcConnUser	DisplayString,
		wcConnClient	DisplayString,
		wcConnDate	DisplayString
	}

	wcConnIndex OBJECT-TYPE
		SYNTAX  INTEGER
		ACCESS	read-only
		STATUS	mandatory
		DESCRIPTION
			" The index. "
	::= { wcConnectionsEntry 1 }

	wcConnUser OBJECT-TYPE
		SYNTAX  DisplayString
		ACCESS	read-only
		STATUS	mandatory
		DESCRIPTION
			" List the connection user."
	::= { wcConnectionsEntry 2 }

	wcConnClient OBJECT-TYPE
		SYNTAX  DisplayString
		ACCESS	read-only
		STATUS	mandatory
		DESCRIPTION
			" List which client is connectting. "
	::= { wcConnectionsEntry 3 }

	wcConnDate OBJECT-TYPE
		SYNTAX  DisplayString
		ACCESS	read-only
		STATUS	mandatory
		DESCRIPTION
			" List the connection date. "
	::= { wcConnectionsEntry 4 }

	wcShares OBJECT IDENTIFIER ::= { windowsClients 14 }

	numOfShares OBJECT-TYPE
		SYNTAX  INTEGER
		ACCESS	read-only
		STATUS	mandatory
		DESCRIPTION
			"Total number of shares."
	::= { wcShares 1 }
	
	wcSharesTable OBJECT-TYPE
		SYNTAX SEQUENCE OF WCShares
		ACCESS	not-accessible
		STATUS	mandatory
		DESCRIPTION
			" A list all share(s) of windows clients.
			  The share(s) status is the real-time status. "
	::= { wcShares 2 }

	wcSharesEntry OBJECT-TYPE
		SYNTAX WCShares
		ACCESS	not-accessible
		STATUS	mandatory
		DESCRIPTION
			" List all share(s). "
		INDEX { wcShareIndex }
	::= { wcSharesTable 1 }

	WCShares ::= SEQUENCE {
		wcShareIndex	INTEGER,
		wcShareName	DisplayString,
		wcShareUser	DisplayString,
		wcShareGroup	DisplayString,
		wcShareClient	DisplayString,
		wcShareDate	DisplayString
	}

	wcShareIndex OBJECT-TYPE
		SYNTAX  INTEGER
		ACCESS	read-only
		STATUS	mandatory
		DESCRIPTION
			" The index. "
	::= { wcSharesEntry 1 }

	wcShareName OBJECT-TYPE
		SYNTAX  DisplayString
		ACCESS	read-only
		STATUS	mandatory
		DESCRIPTION
			" List the share folder name. "
	::= { wcSharesEntry 2 }

	wcShareUser OBJECT-TYPE
		SYNTAX  DisplayString
		ACCESS	read-only
		STATUS	mandatory
		DESCRIPTION
			" List which user is using the share folder right now. "
	::= { wcSharesEntry 3 }

	wcShareGroup OBJECT-TYPE
		SYNTAX  DisplayString
		ACCESS	read-only
		STATUS	mandatory
		DESCRIPTION
			" List which group of the user. "
	::= { wcSharesEntry 4 }

	wcShareClient OBJECT-TYPE
		SYNTAX  DisplayString
		ACCESS	read-only
		STATUS	mandatory
		DESCRIPTION
			" List which client is connected to this share folder. "
	::= { wcSharesEntry 5 }

	wcShareDate OBJECT-TYPE
		SYNTAX  DisplayString
		ACCESS	read-only
		STATUS	mandatory
		DESCRIPTION
			" List the client connected date. "
	::= { wcSharesEntry 6 }

	wcActivityLogMaxSize OBJECT-TYPE
		SYNTAX  DisplayString
		ACCESS	read-only
		STATUS	mandatory
		DESCRIPTION
			"Maximum activity data file size (MB)."
	::= { windowsClients 15 }

	wcActivityLogKeepDays OBJECT-TYPE
		SYNTAX  DisplayString
		ACCESS	read-only
		STATUS	mandatory
		DESCRIPTION
			"Number of days of activities to keep."
	::= { windowsClients 16 }

	wcLockedFiles OBJECT IDENTIFIER ::= { windowsClients 17 }

	numOfLockedFiles OBJECT-TYPE
		SYNTAX  INTEGER
		ACCESS	read-only
		STATUS	mandatory
		DESCRIPTION
			"Total number of locked files."
	::= { wcLockedFiles 1 }
	
	wcLockedFilesTable OBJECT-TYPE
		SYNTAX SEQUENCE OF WCLockedFiles
		ACCESS	not-accessible
		STATUS	mandatory
		DESCRIPTION
			" A list all open file(s) of windows clients.
			  The open file(s) is the real-time status. "
	::= { wcLockedFiles 2 }

	wcLockedFilesEntry OBJECT-TYPE
		SYNTAX WCLockedFiles
		ACCESS	not-accessible
		STATUS	mandatory
		DESCRIPTION
			" List all open file(s). "
		INDEX { wclIndex }
	::= { wcLockedFilesTable 1 }

	WCLockedFiles ::= SEQUENCE {
		wclIndex	INTEGER,
		wclUser		DisplayString,
		wclClientHost	DisplayString,
		wclFile		DisplayString,
		wclDate		DisplayString
	}
	
	wclIndex OBJECT-TYPE
		SYNTAX  INTEGER
		ACCESS	read-only
		STATUS	mandatory
		DESCRIPTION
			" The index. "
	::= { wcLockedFilesEntry 1 }

	wclUser OBJECT-TYPE
		SYNTAX  DisplayString
		ACCESS	read-only
		STATUS	mandatory
		DESCRIPTION
			"."
	::= { wcLockedFilesEntry 2 }

	wclClientHost OBJECT-TYPE
		SYNTAX  DisplayString
		ACCESS	read-only
		STATUS	mandatory
		DESCRIPTION
			""
	::= { wcLockedFilesEntry 3 }

	wclFile OBJECT-TYPE
		SYNTAX  DisplayString
		ACCESS	read-only
		STATUS	mandatory
		DESCRIPTION
			"List which file is locked."
	::= { wcLockedFilesEntry 4 }

	wclDate OBJECT-TYPE
		SYNTAX  DisplayString
		ACCESS	read-only
		STATUS	mandatory
		DESCRIPTION
			"List date."
	::= { wcLockedFilesEntry 5 }

	wcDomainPollDataInterval OBJECT-TYPE
		SYNTAX  DisplayString
		ACCESS	read-only
		STATUS	mandatory
		DESCRIPTION
			"Domain controller poll interval (minute(s))"
	::= { windowsClients 18 }

	nfsClients OBJECT IDENTIFIER ::= { nasClients 2 }
	
	numOfNFSClients OBJECT-TYPE
		SYNTAX  INTEGER
		ACCESS	read-only
		STATUS	mandatory
		DESCRIPTION
			"The amount of NFS clients assigned by the IPStor server."
	::= { nfsClients 1 }

	numOfNFSShares  OBJECT-TYPE
		SYNTAX  INTEGER
		ACCESS	read-only
		STATUS	mandatory
		DESCRIPTION
			"The amount of NFS shares created by the IPStor server."
	::= { nfsClients 2 }
	
	ncNFSClientTable    OBJECT-TYPE
		SYNTAX  SEQUENCE OF NCNFSClient
		ACCESS	not-accessible
		STATUS	mandatory
		DESCRIPTION
			"A table containing NFS clients which share the resource."
	::= { nfsClients 3 }

	ncNFSClientEntry    OBJECT-TYPE
		SYNTAX  NCNFSClient
		ACCESS	not-accessible
		STATUS	mandatory
		DESCRIPTION
			"Information about the assigned NFS client."
		INDEX { ncIndex }
	::= { ncNFSClientTable 1 }

	NCNFSClient ::= SEQUENCE {
		ncIndex		INTEGER,
		ncLabel		DisplayString,
		ncMachine	DisplayString,
		ncComment	DisplayString
	}

	ncIndex OBJECT-TYPE
		SYNTAX  INTEGER
		ACCESS	read-only
		STATUS	mandatory
		DESCRIPTION
			"The sequential digit number as a index key of the NFS client table."
	::= { ncNFSClientEntry 1 }

	ncLabel OBJECT-TYPE
		SYNTAX  DisplayString
		ACCESS	read-only
		STATUS	mandatory
		DESCRIPTION
			"The displaying name of the assigned NFS client."
	::= { ncNFSClientEntry 2 }

	ncMachine   OBJECT-TYPE
		SYNTAX  DisplayString
		ACCESS	read-only
		STATUS	mandatory
		DESCRIPTION
			"The host name of the assigned NFS client."
	::= { ncNFSClientEntry 3 }

	ncComment   OBJECT-TYPE
		SYNTAX  DisplayString
		ACCESS	read-only
		STATUS	mandatory
		DESCRIPTION
			"The comment of the NFS client."
	::= { ncNFSClientEntry 4 }

	ncNFSShareTable OBJECT-TYPE
		SYNTAX  SEQUENCE OF NCNFSShare
		ACCESS	not-accessible
		STATUS	mandatory
		DESCRIPTION
			"A table containing shared resource that assigned to NFS client."
	::= { nfsClients 4 }

	ncNFSShareEntry OBJECT-TYPE
		SYNTAX  NCNFSShare
		ACCESS	not-accessible
		STATUS	mandatory
		DESCRIPTION
			"Information about the shared resource."
		INDEX { ncsIndex }
	::= { ncNFSShareTable 1 }

	NCNFSShare ::= SEQUENCE {
		ncsIndex        INTEGER,
		ncsDiaplayName  DisplayString,
		ncsMachine      DisplayString,
		ncsShareName    DisplayString,
		ncsComment      DisplayString,
		ncsAccessRight  DisplayString,
		ncsFolderName   DisplayString,
		ncsRealPath     DisplayString
	}

	ncsIndex    OBJECT-TYPE
		SYNTAX  INTEGER
		ACCESS	read-only
		STATUS	mandatory
		DESCRIPTION
			"The sequential digit number as a index key of the NFS client share table."
	::= { ncNFSShareEntry 1 }

	ncsDiaplayName  OBJECT-TYPE
		SYNTAX  DisplayString
		ACCESS	read-only
		STATUS	mandatory
		DESCRIPTION
			"The displaying name of the assigned NFS client."
	::= { ncNFSShareEntry 2 }

	ncsMachine OBJECT-TYPE
		SYNTAX  DisplayString
		ACCESS	read-only
		STATUS	mandatory
		DESCRIPTION
			"The host name of the assigned NFS client."
	::= { ncNFSShareEntry 3 }

	ncsShareName    OBJECT-TYPE
		SYNTAX  DisplayString
		ACCESS	read-only
		STATUS	mandatory
		DESCRIPTION
			"The share name of the shared resource."
	::= { ncNFSShareEntry 4 }

	ncsComment  OBJECT-TYPE
		SYNTAX  DisplayString
		ACCESS	read-only
		STATUS	mandatory
		DESCRIPTION
			"The comments setted by users of one share folder."
	::= { ncNFSShareEntry 5 }

	ncsAccessRight  OBJECT-TYPE
		SYNTAX  DisplayString
		ACCESS	read-only
		STATUS	mandatory
		DESCRIPTION
			"The access rights setted for the shared folder to the NFS clients."
	::= { ncNFSShareEntry 6 }

	ncsFolderName   OBJECT-TYPE
		SYNTAX  DisplayString
		ACCESS	read-only
		STATUS	mandatory
		DESCRIPTION
			"The sharing folder name."
	::= { ncNFSShareEntry 7 }

	ncsRealPath OBJECT-TYPE
		SYNTAX  DisplayString
		ACCESS	read-only
		STATUS	mandatory
		DESCRIPTION
			"The sharing full path."
	::= { ncNFSShareEntry 8 }
		
--
-- Virtual Resource States Information
--

	virtualResourceStates OBJECT IDENTIFIER ::= { ipstorserver 6 }

	vrsNumOfVirResources    OBJECT-TYPE
		SYNTAX  INTEGER
		ACCESS	read-only
		STATUS	mandatory
		DESCRIPTION
			"The amount of logical resources which including the SAN, NAS, and Replica devices are available in the IPStor server."
	::= { virtualResourceStates 1 }

	vrsVirResourcesTable    OBJECT-TYPE
		SYNTAX  SEQUENCE OF VRSVirResource
		ACCESS	not-accessible
		STATUS	mandatory
		DESCRIPTION
			"A table containing usage and SCSI command statistics of virtual resources."
	::= { virtualResourceStates 2 }

	vrsVirResourceEntry OBJECT-TYPE
		SYNTAX  VRSVirResource
		ACCESS	not-accessible
		STATUS	mandatory
		DESCRIPTION
			"Information about resource usage and SCSI commands have been read/write of virtual resource."
		INDEX { vrsVirResourceID }
	::= { vrsVirResourcesTable 1 }

	VRSVirResource ::= SEQUENCE {
		vrsVirResourceID    INTEGER,
		vrsVirResourceName	DisplayString,
		vrsInquiry          DisplayString,
		vrsCmdPending		INTEGER,
		vrsSize             	Counter32,
		vrsBlockSize		INTEGER,
		vrsKBRead    	        INTEGER,
		vrsKBWritten		INTEGER,
		vrsSCSIReadCmd		INTEGER,
		vrsSCSIWriteCmd		INTEGER,
		vrsOtherSCSICmd		INTEGER,
		vrsReadError		INTEGER,
		vrsWriteError		INTEGER,
--		vrsRealDevTable		OBJECT IDENTIFIER,
--		vrsClientTable		OBJECT IDENTIFIER,
		vrsSizeQuantity         Counter32,
		vrsSizeUnit             INTEGER,
		vrsSize64		Counter64,
		vrsKBRead64    	        Counter64,
		vrsKBWritten64		Counter64
	}

	vrsVirResourceID    OBJECT-TYPE
		SYNTAX  INTEGER
		ACCESS	read-only
		STATUS	mandatory
		DESCRIPTION
			"The virtual resource ID assigned by the IPStor server."
	::= { vrsVirResourceEntry 1 }

	vrsVirResourceName  OBJECT-TYPE
		SYNTAX	DisplayString
		ACCESS	read-only
		STATUS	mandatory
		DESCRIPTION
			"The virtual resource name created by the user."
	::= { vrsVirResourceEntry 2 }

	vrsInquiry  OBJECT-TYPE
		SYNTAX	DisplayString
		ACCESS	read-only
		STATUS	mandatory
		DESCRIPTION
			"The inquiry string of virtual resource."
	::= { vrsVirResourceEntry 3 }

	vrsCmdPending   OBJECT-TYPE
		SYNTAX	INTEGER
		ACCESS	read-only
		STATUS	mandatory
		DESCRIPTION
			"The amount of outstanding SCSI commands of virtual resource."
	::= { vrsVirResourceEntry 4 }

	vrsSize OBJECT-TYPE
		SYNTAX	Counter32
		ACCESS	read-only
		STATUS	mandatory
		DESCRIPTION
			"The amount of device size which is representing with megabyte unit of the virtual resource."
	::= { vrsVirResourceEntry 5 }

	vrsBlockSize    OBJECT-TYPE
		SYNTAX	INTEGER
		ACCESS	read-only
		STATUS	mandatory
		DESCRIPTION
			"The size of bytes for each sector or block."
	::= { vrsVirResourceEntry 6 }

	vrsKBRead   OBJECT-TYPE
		SYNTAX	INTEGER
		ACCESS	read-only
		STATUS	mandatory
		DESCRIPTION
			"The amount of kilobytes have been read from the virtual resource."
	::= { vrsVirResourceEntry 7 }

	vrsKBWritten    OBJECT-TYPE
		SYNTAX	INTEGER
		ACCESS	read-only
		STATUS	mandatory
		DESCRIPTION
			"The amount of kilobytes have been written to the virtual resource."
	::= { vrsVirResourceEntry 8 }

	vrsSCSIReadCmd  OBJECT-TYPE
		SYNTAX	INTEGER
		ACCESS	read-only
		STATUS	mandatory
		DESCRIPTION
			"The amount of read SCSI commands have been sent to the virtual resource."
	::= { vrsVirResourceEntry 9 }

	vrsSCSIWriteCmd OBJECT-TYPE
		SYNTAX	INTEGER
		ACCESS	read-only
		STATUS	mandatory
		DESCRIPTION
			"The amount of write SCSI commands have been sent to the virtual resource."
	::= { vrsVirResourceEntry 10 }

	vrsOtherSCSICmd OBJECT-TYPE
		SYNTAX	INTEGER
		ACCESS	read-only
		STATUS	mandatory
		DESCRIPTION
			"The amount of not read or write SCSI commands have been sent to the virtual resource."
	::= { vrsVirResourceEntry 11 }

	vrsReadError    OBJECT-TYPE
		SYNTAX	INTEGER
		ACCESS	read-only
		STATUS	mandatory
		DESCRIPTION
			"The amount of SCSI commands that occur read error of the virtual resource."
	::= { vrsVirResourceEntry 12 }

	vrsWriteError   OBJECT-TYPE
		SYNTAX	INTEGER
		ACCESS	read-only
		STATUS	mandatory
		DESCRIPTION
			"The amount of SCSI commands that occur write error of the virtual resource."
	::= { vrsVirResourceEntry 13 }

	vrsRealDevTable OBJECT-TYPE
		SYNTAX  SEQUENCE OF VRSRealDev
		ACCESS	not-accessible
		STATUS	mandatory
		DESCRIPTION
			"A table containing usage and SCSI command statistics of physical devices that used by virtual resources."
	::= { vrsVirResourceEntry 14 }

	vrsRealDevEntry OBJECT-TYPE
		SYNTAX  VRSRealDev
		ACCESS	not-accessible
		STATUS	mandatory
		DESCRIPTION
			"Information about resource usage and SCSI commands have been read/write of physical resource."
		INDEX { vrsrdVirResourceID }
	::= { vrsRealDevTable 1 }

	VRSRealDev ::= SEQUENCE {
		vrsrdVirResourceID	INTEGER,
		vrsrdType	        DisplayString,
		vrsrdAdapterNo		INTEGER,
		vrsrdChannelNo		INTEGER,
		vrsrdScsiID		INTEGER,
		vrsrdLun		INTEGER,
		vrsrdFirstSector	Counter32,
		vrsrdLastSector		Counter32,
		vrsrdKBRead		INTEGER,
		vrsrdKBWritten		INTEGER,
		vrsrdSCSIReadCmd	INTEGER,
		vrsrdSCSIWriteCmd	INTEGER,
		vrsrdOtherSCSICmd	INTEGER,
		vrsrdReadError		INTEGER,
		vrsrdWriteError		INTEGER,
		vrsrdFirstSector64	Counter64,
		vrsrdLastSector64	Counter64,
		vrsrdKBRead64		Counter64,
		vrsrdKBWritten64	Counter64
	}

	vrsrdVirResourceID  OBJECT-TYPE
		SYNTAX  INTEGER
		ACCESS	read-only
		STATUS	mandatory
		DESCRIPTION
			"The virtual resource ID assigned by the IPStor server."
	::= { vrsRealDevEntry 1 }

	vrsrdType   OBJECT-TYPE
		SYNTAX  DisplayString
		ACCESS	read-only
		STATUS	mandatory
		DESCRIPTION
			"It represents the type(Primary, or Mirror) of the physical layout."
	::= { vrsRealDevEntry 2 }

	vrsrdAdapterNo  OBJECT-TYPE
		SYNTAX  INTEGER
		ACCESS	read-only
		STATUS	mandatory
		DESCRIPTION
			"The SCSI adapter number of the physical device."
	::= { vrsRealDevEntry 3 }

	vrsrdChannelNo  OBJECT-TYPE
		SYNTAX  INTEGER
		ACCESS	read-only
		STATUS	mandatory
		DESCRIPTION
			"The SCSI channel number of the physical device."
	::= { vrsRealDevEntry 4 }

	vrsrdScsiID OBJECT-TYPE
		SYNTAX  INTEGER
		ACCESS	read-only
		STATUS	mandatory
		DESCRIPTION
			"The SCSI ID of the physical device."
	::= { vrsRealDevEntry 5 }

	vrsrdLun    OBJECT-TYPE
		SYNTAX  INTEGER
		ACCESS	read-only
		STATUS	mandatory
		DESCRIPTION
			"The SCSI LUN number of the physical device."
	::= { vrsRealDevEntry 6 }

	vrsrdFirstSector    OBJECT-TYPE
		SYNTAX  Counter32
		ACCESS	read-only
		STATUS	mandatory
		DESCRIPTION
			"The first sector of the physical device which is allocated by the virtual resource."
	::= { vrsRealDevEntry 7 }

	vrsrdLastSector OBJECT-TYPE
		SYNTAX  Counter32
		ACCESS	read-only
		STATUS	mandatory
		DESCRIPTION
			"The last sector of the physical device which is allocated by the virtual resource."
	::= { vrsRealDevEntry 8 }
		
	vrsrdKBRead OBJECT-TYPE
		SYNTAX	INTEGER
		ACCESS	read-only
		STATUS	mandatory
		DESCRIPTION
			"The amount of kilobytes have been read from the physical resource."
	::= { vrsRealDevEntry 9 }

	vrsrdKBWritten  OBJECT-TYPE
		SYNTAX	INTEGER
		ACCESS	read-only
		STATUS	mandatory
		DESCRIPTION
			"The amount of kilobytes have been written to the physical resource."
	::= { vrsRealDevEntry 10 }

	vrsrdSCSIReadCmd OBJECT-TYPE
		SYNTAX	INTEGER
		ACCESS	read-only
		STATUS	mandatory
		DESCRIPTION
			"The amount of read SCSI commands have been sent to the physical resource."
	::= { vrsRealDevEntry 11 }

	vrsrdSCSIWriteCmd OBJECT-TYPE
		SYNTAX	INTEGER
		ACCESS	read-only
		STATUS	mandatory
		DESCRIPTION
			"The amount of write SCSI commands have been sent to the physical resource."
	::= { vrsRealDevEntry 12 }

	vrsrdOtherSCSICmd OBJECT-TYPE
		SYNTAX	INTEGER
		ACCESS	read-only
		STATUS	mandatory
		DESCRIPTION
			"The amount of not read or write SCSI commands have been sent to the physical resource."
	::= { vrsRealDevEntry 13 }

	vrsrdReadError OBJECT-TYPE
		SYNTAX	INTEGER
		ACCESS	read-only
		STATUS	mandatory
		DESCRIPTION
			"The amount of SCSI commands that occur read error of the physical resource."
	::= { vrsRealDevEntry 14 }

	vrsrdWriteError OBJECT-TYPE
		SYNTAX	INTEGER
		ACCESS	read-only
		STATUS	mandatory
		DESCRIPTION
			"The amount of SCSI commands that occur write error of the physical resource."
	::= { vrsRealDevEntry 15 }

	vrsClientTable  OBJECT-TYPE
		SYNTAX  SEQUENCE OF VRSClient
		ACCESS	not-accessible
		STATUS	mandatory
		DESCRIPTION
			"A table containing usage and SCSI command statistics of clients that assigned to virtual resources."
	::= { vrsVirResourceEntry 15 }

	vrsrdFirstSector64    OBJECT-TYPE
		SYNTAX  Counter64
		ACCESS	read-only
		STATUS	mandatory
		DESCRIPTION
			"The first sector of the physical device which is allocated by the virtual resource."
	::= { vrsRealDevEntry 16 }

	vrsrdLastSector64 OBJECT-TYPE
		SYNTAX  Counter64
		ACCESS	read-only
		STATUS	mandatory
		DESCRIPTION
			"The last sector of the physical device which is allocated by the virtual resource."
	::= { vrsRealDevEntry 17 }
		
	vrsrdKBRead64 OBJECT-TYPE
		SYNTAX	Counter64
		ACCESS	read-only
		STATUS	mandatory
		DESCRIPTION
			"The amount of kilobytes have been read from the physical resource."
	::= { vrsRealDevEntry 18 }

	vrsrdKBWritten64  OBJECT-TYPE
		SYNTAX	Counter64
		ACCESS	read-only
		STATUS	mandatory
		DESCRIPTION
			"The amount of kilobytes have been written to the physical resource."
	::= { vrsRealDevEntry 19 }

	vrsClientEntry  OBJECT-TYPE
		SYNTAX  VRSClient
		ACCESS	not-accessible
		STATUS	mandatory
		DESCRIPTION
			"Information about SCSI commands have been read/write of the clients."
		INDEX { vrsclClientName }
	::= { vrsClientTable 1 }

	VRSClient ::= SEQUENCE {
		vrsclClientName         DisplayString,
		vrsclClientID           INTEGER,
		vrsclVirResourceName    DisplayString,
		vrsclVirResourceID      INTEGER,
		vrsclAccess             DisplayString,
		vrsclConnAccess         DisplayString,
		vrsclConnected          DisplayString,
		vrsclKBRead             INTEGER,
		vrsclKBWritten          INTEGER,
		vrsclSCSIReadCmd        INTEGER,
		vrsclSCSIWriteCmd       INTEGER,
		vrsclOtherSCSICmd       INTEGER,
		vrsclReadError          INTEGER,
		vrsclWriteError         INTEGER,
		vrsclKBRead64           Counter64,
		vrsclKBWritten64        Counter64
	}

	vrsclClientName OBJECT-TYPE
		SYNTAX	DisplayString
		ACCESS	read-only
		STATUS	mandatory
		DESCRIPTION
			"The client name assigned by the IPStor server."
	::= { vrsClientEntry 1 }

	vrsclClientID   OBJECT-TYPE
		SYNTAX	INTEGER
		ACCESS	read-only
		STATUS	mandatory
		DESCRIPTION
			"The client ID assigned by the IPStor server."
	::= { vrsClientEntry 2 }

	vrsclVirResourceName    OBJECT-TYPE
		SYNTAX	DisplayString
		ACCESS	read-only
		STATUS	mandatory
		DESCRIPTION
			"The virtual resource name created by the user."
	::= { vrsClientEntry 3 }

	vrsclVirResourceID  OBJECT-TYPE
		SYNTAX	INTEGER
		ACCESS	read-only
		STATUS	mandatory
		DESCRIPTION
			"The virtual resource ID assigned by the IPStor server."
	::= { vrsClientEntry 4 }

	vrsclAccess OBJECT-TYPE
		SYNTAX	DisplayString
		ACCESS	read-only
		STATUS	mandatory
		DESCRIPTION
			"The virtual resource accessing mode assigned to the client."
	::= { vrsClientEntry 5 }

	vrsclConnAccess OBJECT-TYPE
		SYNTAX	DisplayString
		ACCESS	read-only
		STATUS	mandatory
		DESCRIPTION
			"Identify the accessing status with a virtual resource of the client."
	::= { vrsClientEntry 6 }

	vrsclConnected  OBJECT-TYPE
		SYNTAX	DisplayString
		ACCESS	read-only
		STATUS	mandatory
		DESCRIPTION
			"Identify the connecting status(on-line, or off-line) with a virtual resource of the client."
	::= { vrsClientEntry 7 }

	vrsclKBRead OBJECT-TYPE
		SYNTAX	INTEGER
		ACCESS	read-only
		STATUS	mandatory
		DESCRIPTION
			"The amount of kilobytes have been read by the client."
	::= { vrsClientEntry 8 }

	vrsclKBWritten  OBJECT-TYPE
		SYNTAX	INTEGER
		ACCESS	read-only
		STATUS	mandatory
		DESCRIPTION
			"The amount of kilobytes have been written by the client."
	::= { vrsClientEntry 9 }

	vrsclSCSIReadCmd    OBJECT-TYPE
		SYNTAX	INTEGER
		ACCESS	read-only
		STATUS	mandatory
		DESCRIPTION
			"The amount of read SCSI commands have been sent by the client."
	::= { vrsClientEntry 10 }

	vrsclSCSIWriteCmd   OBJECT-TYPE
		SYNTAX	INTEGER
		ACCESS	read-only
		STATUS	mandatory
		DESCRIPTION
			"The amount of write SCSI commands have been sent by the client."
	::= { vrsClientEntry 11 }

	vrsclOtherSCSICmd   OBJECT-TYPE
		SYNTAX	INTEGER
		ACCESS	read-only
		STATUS	mandatory
		DESCRIPTION
			"The amount of not read or write SCSI commands have been sent by the client."
	::= { vrsClientEntry 12 }

	vrsclReadError  OBJECT-TYPE
		SYNTAX	INTEGER
		ACCESS	read-only
		STATUS	mandatory
		DESCRIPTION
			"The amount of SCSI commands that occur read error sent by the client."
	::= { vrsClientEntry 13 }

	vrsclWriteError OBJECT-TYPE
		SYNTAX	INTEGER
		ACCESS	read-only
		STATUS	mandatory
		DESCRIPTION
			"The amount of SCSI commands that occur write error sent by the client."
	::= { vrsClientEntry 14 }

	vrsclKBRead64 OBJECT-TYPE
		SYNTAX	Counter64
		ACCESS	read-only
		STATUS	mandatory
		DESCRIPTION
			"The amount of kilobytes have been read by the client."
	::= { vrsClientEntry 15 }

	vrsclKBWritten64  OBJECT-TYPE
		SYNTAX	Counter64
		ACCESS	read-only
		STATUS	mandatory
		DESCRIPTION
			"The amount of kilobytes have been written by the client."
	::= { vrsClientEntry 16 }

	vrsSizeQuantity OBJECT-TYPE
		SYNTAX	Counter32
		ACCESS	read-only
		STATUS	mandatory
		DESCRIPTION
			"The amount of device size quantity of the virtual resource."
	::= { vrsVirResourceEntry 16 }

	vrsSizeUnit OBJECT-TYPE
		SYNTAX	INTEGER
		ACCESS	read-only
		STATUS	mandatory
		DESCRIPTION
			"The amount of device size unit of the virtual resource. 0 presents KB. 1 presents MB. 2 presents GB. 3 presents TB."
	::= { vrsVirResourceEntry 17 }

	vrsSize64 OBJECT-TYPE
		SYNTAX	Counter64
		ACCESS	read-only
		STATUS	mandatory
		DESCRIPTION
			"The amount of device size which is representing with megabyte unit of the virtual resource."
	::= { vrsVirResourceEntry 18 }

	vrsKBRead64   OBJECT-TYPE
		SYNTAX	Counter64
		ACCESS	read-only
		STATUS	mandatory
		DESCRIPTION
			"The amount of kilobytes have been read from the virtual resource."
	::= { vrsVirResourceEntry 19 }

	vrsKBWritten64    OBJECT-TYPE
		SYNTAX	Counter64
		ACCESS	read-only
		STATUS	mandatory
		DESCRIPTION
			"The amount of kilobytes have been written to the virtual resource."
	::= { vrsVirResourceEntry 20 }

--
-- SNMP Trap Registration Group 
--

   	trapReg OBJECT IDENTIFIER ::= { ipstorserver 7 }

	trapAuthtrapenable  OBJECT-TYPE
        SYNTAX  INTEGER {
        	enable (1),
        	disable(2)
        }
        ACCESS  read-write
        STATUS  mandatory
        DESCRIPTION
            "The switch to generate the authentication failure trap if the community string is wrong. 
             The default value is 2 (disable)."
        ::= { trapReg 1 }
            
	trapCommunity   OBJECT-TYPE
        SYNTAX  DisplayString
        ACCESS  read-write
        STATUS  mandatory
        DESCRIPTION
            "It defines the default community string while sending traps."
        ::= { trapReg 2 }
            
	trapSinkSettingTable    OBJECT-TYPE
        SYNTAX  SEQUENCE OF TrapSinkSettingList
        ACCESS  not-accessible 
        STATUS  mandatory
        DESCRIPTION
            "A table containing all the management systems that would like to receive traps from IPStor server."
        ::= { trapReg 3 }
	 
	trapSinkSettingEntry    OBJECT-TYPE
        SYNTAX  TrapSinkSettingList
        ACCESS  not-accessible 
        STATUS  mandatory
        DESCRIPTION
            "Information about the community string and hosts that configured to receive traps.  The 5 is the maximum management systems allowed."
        INDEX { trIndex }
        ::= { trapSinkSettingTable 1 }

	TrapSinkSettingList ::= SEQUENCE {
	    trIndex     INTEGER,
	    trHost      DisplayString,
	    trCommunity DisplayString
	}
	    
	trIndex OBJECT-TYPE
        SYNTAX  INTEGER
        ACCESS  read-only
        STATUS  mandatory
        DESCRIPTION
            "The sequential digit number as a index key of the trap sink table."
        ::= { trapSinkSettingEntry 1 }
	 
	trHost  OBJECT-TYPE
        SYNTAX  DisplayString
        ACCESS  read-write
        STATUS  mandatory
        DESCRIPTION
            "Identify the host name which is configured to receive traps from IPStor server." 
        ::= { trapSinkSettingEntry 2 }

	trCommunity OBJECT-TYPE
        SYNTAX  DisplayString
        ACCESS  read-write
        STATUS  mandatory
        DESCRIPTION
            "Identify the community string to be used with the management system if it's not an empty string.
             If the empty string is set, the string configured by oid (.trapCommunity) will be used instead."
        ::= { trapSinkSettingEntry 3 }
                          
--
-- The Alarm Group (requires the implementation of the event group)
--

	alarmTable  OBJECT-TYPE
	    SYNTAX  SEQUENCE OF AlarmEntry
	    ACCESS  not-accessible
	    STATUS  mandatory
	    DESCRIPTION
		    "A table containing the alarm configurations of the IPStor server.  All these configurations that can be
		     modified is in the configuration file IPStorSNMPD.conf."
	    ::= { ipstorserver 8 }

	alarmEntry  OBJECT-TYPE
	    SYNTAX  AlarmEntry
	    ACCESS  not-accessible
	    STATUS  mandatory
	    DESCRIPTION
		    "Information about the the thresholds, monitor interval, and active status of the alarm table."
	    INDEX { alarmIndex }
	    ::= { alarmTable 1 }

	AlarmEntry ::= SEQUENCE {
	    alarmIndex              INTEGER,
	    alarmName			    DisplayString,
	    alarmVariable           DisplayString,
	    alarmMonitor		    INTEGER,
	    alarmInterval           INTEGER,
	    alarmValue              INTEGER,
	    alarmRisingThreshold    INTEGER,
	    alarmFallingThreshold   INTEGER,
	    alarmStatus             INTEGER
	}

	alarmIndex  OBJECT-TYPE
	    SYNTAX  INTEGER (1..65535)
	    ACCESS  read-only
	    STATUS  mandatory
	    DESCRIPTION
		    "The sequential digit number as a index key of the alarm table."
	    ::= { alarmEntry 1 }

	alarmName   OBJECT-TYPE
	    SYNTAX  DisplayString
	    ACCESS  read-only
	    STATUS  mandatory
	    DESCRIPTION
		    "Identify the type(process, module, or object identifier(OID)) is been monitored."
	    ::= { alarmEntry 2 }

	alarmVariable   OBJECT-TYPE
	    SYNTAX  DisplayString
	    ACCESS  read-only
	    STATUS  mandatory
	    DESCRIPTION
    		"Identify the process/module name, or the object identifier specified to be monitored."
	    ::= { alarmEntry 3 }

	alarmMonitor    OBJECT-TYPE
	    SYNTAX  INTEGER
	    ACCESS  read-write
	    STATUS  mandatory
	    DESCRIPTION
    		"It's time interval in second unit to check the monitored object if the value has over the rising threshold."
	    ::= { alarmEntry 4 }

	alarmInterval   OBJECT-TYPE
	    SYNTAX  INTEGER
	    ACCESS  read-write
	    STATUS  mandatory
	    DESCRIPTION
    		"It's time interval in second unit to check the monitored object if againt the thresholds."
	    ::= { alarmEntry 5 }

	alarmValue  OBJECT-TYPE
	    SYNTAX  INTEGER
	    ACCESS  read-only
	    STATUS  mandatory
	    DESCRIPTION
    		"The statistic value of the monitored object last sampled.
    		 If the the monitor entry is process or module, 0 stands for process down and 1 for process alive."
	    ::= { alarmEntry 6 }

	alarmRisingThreshold    OBJECT-TYPE
	    SYNTAX  INTEGER
	    ACCESS  read-write
	    STATUS  mandatory
	    DESCRIPTION
    		"A threshold sets for the upper-bound of the monitored object.  The event generated when the sampled
    		 value is greater than or equal to the threshold.  Once the event is generated, another such kind of 
    		 events will be ignored. 
    		 This object may not be modified if the associated alarmStatus object is enabled."
	    ::= { alarmEntry 7 }

	alarmFallingThreshold   OBJECT-TYPE
	    SYNTAX  INTEGER
	    ACCESS  read-write
	    STATUS  mandatory
	    DESCRIPTION
    		"A threshold sets for the lower-bound of the monitored object.  The event generated when the sampled
    		 value is less than or equal to the threshold.  Once the event is generated, another such kind of 
    		 events will be ignored.
    		 This object may not be modified if the associated alarmStatus object is enabled."
	    ::= { alarmEntry 8 }

	alarmStatus OBJECT-TYPE
	    SYNTAX  INTEGER {
			disable(0),
			enable (1)
		}
	    ACCESS  read-write
	    STATUS  mandatory
	    DESCRIPTION
		    "The active status of the alarm entry."
	    ::= { alarmEntry 9 }

-- ***************************************************************
-- IPStor Client group
-- ***************************************************************

	clientInfo OBJECT IDENTIFIER ::= { ipstorclient 1 }

	ipstorClientVersion	OBJECT-TYPE
		SYNTAX  DisplayString
		ACCESS  read-only
		STATUS  mandatory
		DESCRIPTION
			"The version number of IPStor client."
	::= { clientInfo 1 }

	sanServers OBJECT IDENTIFIER ::= { ipstorclient 2 }

	numOfSANServers OBJECT-TYPE
		SYNTAX  INTEGER
		ACCESS	read-only
		STATUS	mandatory
		DESCRIPTION
			"The amount of IPStor servers that the client are connecting."
	::= { sanServers 1 }

	sanServerTable  OBJECT-TYPE
		SYNTAX  SEQUENCE OF SANServer
		ACCESS	not-accessible
		STATUS	mandatory
		DESCRIPTION
			"A table containing the IPStor servers which the client connected."
	::= { sanServers 2 }

	sanServerEntry  OBJECT-TYPE
		SYNTAX  SANServer
		ACCESS	not-accessible
		STATUS	mandatory
		DESCRIPTION
			"Information about the running environment, hardware compoments of IPStor server and statistic of read/write SCSI commands."
		INDEX { clsName }
	::= { sanServerTable 1 }

	SANServer ::= SEQUENCE {
		clsName			    DisplayString,
		clsIPAddress		DisplayString,
		clsType			    DisplayString,
		clsOS			    DisplayString,
		clsTypeOfCPU		DisplayString,
		clsNumOfCPU		    INTEGER,
		clsSpeedOfCPU		DisplayString,
		clsFlags		    DisplayString,
		clsDataPort		    INTEGER,
		clsManagePort		INTEGER,
		clsNumOfAdapters	INTEGER,
		clsNumOfDevices		INTEGER,
		clsVersion		    DisplayString,
		clsBuild		    DisplayString,
		clsReleaseDate		DisplayString,
		clsConnErrors		INTEGER,
		clsConn			    DisplayString,
		clsActivity		    DisplayString,
		clsSCSIReadCmds		INTEGER,
		clsSCSIWriteCmds	INTEGER,
		clsOtherSCSICmds	INTEGER,
		clsErrors		    INTEGER,
		clsDataRead		    DisplayString,
		clsDataWritten		DisplayString
--		clsAdapterList		OBJECT IDENTIFIER		
	}

	clsName OBJECT-TYPE
		SYNTAX	DisplayString
		ACCESS	read-only
		STATUS	mandatory
		DESCRIPTION
			"The hostname of the IPStor server that the client connected."
	::= { sanServerEntry 1 }

	clsIPAddress    OBJECT-TYPE
		SYNTAX	DisplayString
		ACCESS	read-only
		STATUS	mandatory
		DESCRIPTION
			"The IP address of the IPStor server that the client connected."
	::= { sanServerEntry 2 }

	clsType OBJECT-TYPE
		SYNTAX	DisplayString
		ACCESS	read-only
		STATUS	mandatory
		DESCRIPTION
			"The server type which the client connected."
	::= { sanServerEntry 3 }

	clsOS   OBJECT-TYPE
		SYNTAX	DisplayString
		ACCESS	read-only
		STATUS	mandatory
		DESCRIPTION
			"The operation system version of the IPStor server is running."
	::= { sanServerEntry 4 }

	clsTypeOfCPU    OBJECT-TYPE
		SYNTAX	DisplayString
		ACCESS	read-only
		STATUS	mandatory
		DESCRIPTION
			"The models of CPU the the IPStor server owned."
	::= { sanServerEntry 5 }

	clsNumOfCPU OBJECT-TYPE
		SYNTAX	INTEGER
		ACCESS	read-only
		STATUS	mandatory
		DESCRIPTION
			"The amount of CPUs that the IPStor server owned."
	::= { sanServerEntry 6 }

	clsSpeedOfCPU   OBJECT-TYPE
		SYNTAX	DisplayString
		ACCESS	read-only
		STATUS	mandatory
		DESCRIPTION
			"The power of CPU that the IPStor server owned."
	::= { sanServerEntry 7 }


	clsFlags    OBJECT-TYPE
		SYNTAX	DisplayString
		ACCESS	read-only
		STATUS	mandatory
		DESCRIPTION
			"Identify the special property(UTF-8 encoding, IPv6/IPv4) of the IPStor server." 
	::= { sanServerEntry 8 }

	clsDataPort OBJECT-TYPE
		SYNTAX	INTEGER
		ACCESS	read-only
		STATUS	mandatory
		DESCRIPTION
			"The UDP port number that used to send/receive data between IPStor server and client."
	::= { sanServerEntry 9 }

	clsManagePort   OBJECT-TYPE
		SYNTAX	INTEGER
		ACCESS	read-only
		STATUS	mandatory
		DESCRIPTION
			"The UDP port number that used to send/receive managed data between IPStor server and client."
	::= { sanServerEntry 10 }

	clsNumOfAdapters    OBJECT-TYPE
		SYNTAX	INTEGER
		ACCESS	read-only
		STATUS	mandatory
		DESCRIPTION
			"The amount of SCSI adapters of the IPStor server."
	::= { sanServerEntry 11 }

	clsNumOfDevices OBJECT-TYPE
		SYNTAX	INTEGER
		ACCESS	read-only
		STATUS	mandatory
		DESCRIPTION
			"The amount of logical devices of the IPStor server."
	::= { sanServerEntry 12 }

	clsVersion  OBJECT-TYPE
		SYNTAX	DisplayString
		ACCESS	read-only
		STATUS	mandatory
		DESCRIPTION
			"The version of the IPStor server."
	::= { sanServerEntry 13 }

	clsBuild    OBJECT-TYPE
		SYNTAX	DisplayString
		ACCESS	read-only
		STATUS	mandatory
		DESCRIPTION
			"The build number of the IPStor server."
	::= { sanServerEntry 14 }

	clsReleaseDate  OBJECT-TYPE
		SYNTAX	DisplayString
		ACCESS	read-only
		STATUS	mandatory
		DESCRIPTION
			"The release date of the IPStor server version."
	::= { sanServerEntry 15 }

	clsConnErrors   OBJECT-TYPE
		SYNTAX	INTEGER
		ACCESS	read-only
		STATUS	mandatory
		DESCRIPTION
			"The amount of connection error with the IPStor server and client."
	::= { sanServerEntry 16 }

	clsConn OBJECT-TYPE
		SYNTAX	DisplayString
		ACCESS	read-only
		STATUS	mandatory
		DESCRIPTION
			"The mandatory states which include Attached, Connected, Mounted, Registered, 
			 Skipped, or Disabled of the connection with IPStor server."
	::= { sanServerEntry 17 }

	clsActivity OBJECT-TYPE
		SYNTAX	DisplayString
		ACCESS	read-only
		STATUS	mandatory
		DESCRIPTION
			"The activities which include Read, Write, Misc, Error, or Reconnect of the sorage server."
	::= { sanServerEntry 18 }

	clsSCSIReadCmds OBJECT-TYPE
		SYNTAX	INTEGER
		ACCESS	read-only
		STATUS	mandatory
		DESCRIPTION
			"The amount of read SCSI commands have been sent to the IPStor server."
	::= { sanServerEntry 19 }

	clsSCSIWriteCmds    OBJECT-TYPE
		SYNTAX	INTEGER
		ACCESS	read-only
		STATUS	mandatory
		DESCRIPTION
			"The amount of write SCSI commands have been sent to the IPStor server."
	::= { sanServerEntry 20 }

	clsOtherSCSICmds    OBJECT-TYPE
		SYNTAX	INTEGER
		ACCESS	read-only
		STATUS	mandatory
		DESCRIPTION
			"The amount of not read or write SCSI commands have been sent to the IPStor server."
	::= { sanServerEntry 21 }

	clsErrors   OBJECT-TYPE
		SYNTAX	INTEGER
		ACCESS	read-only
		STATUS	mandatory
		DESCRIPTION
			"The amount of SCSI commands that occur read/write error sent to the IPStor server."
	::= { sanServerEntry 22 }

	clsDataRead OBJECT-TYPE
		SYNTAX	DisplayString
		ACCESS	read-only
		STATUS	mandatory
		DESCRIPTION
			"The amount of bytes have been read from the IPStor server."
	::= { sanServerEntry 23 }

	clsDataWritten  OBJECT-TYPE
		SYNTAX	DisplayString
		ACCESS	read-only
		STATUS	mandatory
		DESCRIPTION
			"The amount of bytes have been write to the IPStor server."
	::= { sanServerEntry 24 }

	clsAdapterTable OBJECT-TYPE
		SYNTAX  SEQUENCE OF ClsAdapter
		ACCESS	not-accessible
		STATUS	mandatory
		DESCRIPTION
			"A table containing the adapters configured of the IPStor server."
	::= { sanServerEntry 25 }

	clsAdapterEntry OBJECT-TYPE
		SYNTAX  ClsAdapter
		ACCESS	not-accessible
		STATUS	mandatory
		DESCRIPTION
			"Information about the hardware configurations of the adapter."
		INDEX { clsaName }
	::= { clsAdapterTable 1 }

	ClsAdapter ::= SEQUENCE {
		clsaName                DisplayString,
		clsaAdapterNum          INTEGER,
		clsaChannels            INTEGER,
		clsaSCSIAddress         DisplayString,
		clsaLocalSCSIAddress    DisplayString
--		clsaDeviceList          OBJECT IDENTIFIER		
	}

	clsaName    OBJECT-TYPE
		SYNTAX	DisplayString
		ACCESS	read-only
		STATUS	mandatory
		DESCRIPTION
			"The hostname of the IPStor server that the client connected."
	::= { clsAdapterEntry 1 }

	clsaAdapterNum  OBJECT-TYPE
		SYNTAX	INTEGER
		ACCESS	read-only
		STATUS	mandatory
		DESCRIPTION
			"The SCSI adapter number."
	::= { clsAdapterEntry 2 }

	clsaChannels    OBJECT-TYPE
		SYNTAX	INTEGER
		ACCESS	read-only
		STATUS	mandatory
		DESCRIPTION
			"The SCSI channel number."
	::= { clsAdapterEntry 3 }

	clsaSCSIAddress OBJECT-TYPE
		SYNTAX	DisplayString
		ACCESS	read-only
		STATUS	mandatory
		DESCRIPTION
			"The SCSI address with <Adapter:Channel:SCSI:LUN> format assigned by the IPStor server."
	::= { clsAdapterEntry 4 }

	clsaLocalSCSIAddress    OBJECT-TYPE
		SYNTAX	DisplayString
		ACCESS	read-only
		STATUS	mandatory
		DESCRIPTION
			"The SCSI address with <Adapter:Channel:SCSI:LUN> format assigned by the local client."
	::= { clsAdapterEntry 5 }

	clsaDeviceTable OBJECT-TYPE
		SYNTAX  SEQUENCE OF ClsaDevice
		ACCESS	not-accessible
		STATUS	mandatory
		DESCRIPTION
			"A table containing devices that attached to the adapter."
	::= { clsAdapterEntry 6 }

	clsaDeviceEntry OBJECT-TYPE
		SYNTAX  ClsaDevice
		ACCESS	not-accessible
		STATUS	mandatory
		DESCRIPTION
			"Information about the hardware configurations and read/write statistic of the device."
		INDEX { clsadName }
	::= { clsaDeviceTable 1 }

	ClsaDevice ::= SEQUENCE {
		clsadName               DisplayString,
		clsadAdapterNum         INTEGER,
		clsadDeviceName         DisplayString,
		clsadType               DisplayString,
		clsadAttachMode         DisplayString,
		clsadSCSIAddress        DisplayString,
		clsadLocalSCSIAddress   DisplayString,
		clsadLogicalDevice      DisplayString,
		clsadConnection         DisplayString,
		clsadActivity           DisplayString,
		clsadSCSIReadCmds       INTEGER,
		clsadSCSIWriteCmds      INTEGER,
		clsadOtherSCSICmds      INTEGER,
		clsadErrors             INTEGER,
		clsadDataRead           DisplayString,
		clsadDataWritten        DisplayString
--		clsadVolumeList         OBJECT IDENTIFIER		
	}

	clsadName   OBJECT-TYPE
		SYNTAX	DisplayString
		ACCESS	read-only
		STATUS	mandatory
		DESCRIPTION
			"The hostname of the IPStor server that the client connected."
	::= { clsaDeviceEntry 1 }

	clsadAdapterNum OBJECT-TYPE
		SYNTAX	INTEGER
		ACCESS	read-only
		STATUS	mandatory
		DESCRIPTION
			"The SCSI adapter number."
	::= { clsaDeviceEntry 2 }

	clsadDeviceName OBJECT-TYPE
		SYNTAX	DisplayString
		ACCESS	read-only
		STATUS	mandatory
		DESCRIPTION
			"The resource name created by the user."
	::= { clsaDeviceEntry 3 }

	clsadType   OBJECT-TYPE
		SYNTAX	DisplayString
		ACCESS	read-only
		STATUS	mandatory
		DESCRIPTION
			"It represents the resource type when user allocating the resource."
	::= { clsaDeviceEntry 4 }

	clsadAttachMode OBJECT-TYPE
		SYNTAX	DisplayString
		ACCESS	read-only
		STATUS	mandatory
		DESCRIPTION
			"The resource accessing mode assigned by the user."
	::= { clsaDeviceEntry 5 }

	clsadSCSIAddress    OBJECT-TYPE
		SYNTAX	DisplayString
		ACCESS	read-only
		STATUS	mandatory
		DESCRIPTION
			"The SCSI address with <Adapter:Channel:SCSI:LUN> format assigned by the IPStor server."
	::= { clsaDeviceEntry 6 }

	clsadLocalSCSIAddress   OBJECT-TYPE
		SYNTAX	DisplayString
		ACCESS	read-only
		STATUS	mandatory
		DESCRIPTION
			"The SCSI address with <Adapter:Channel:SCSI:LUN> format assigned by the local client."
	::= { clsaDeviceEntry 7}

	clsadLogicalDevice  OBJECT-TYPE
		SYNTAX	DisplayString
		ACCESS	read-only
		STATUS	mandatory
		DESCRIPTION
			"The resource name created by the user."
	::= { clsaDeviceEntry 8}

	clsadConnection OBJECT-TYPE
		SYNTAX	DisplayString
		ACCESS	read-only
		STATUS	mandatory
		DESCRIPTION
			"The current connected states which includes Attached, Connected, Mounted, Registered, Skipped, 
			 or Disable of the device."
	::= { clsaDeviceEntry 9}

	clsadActivity   OBJECT-TYPE
		SYNTAX	DisplayString
		ACCESS	read-only
		STATUS	mandatory
		DESCRIPTION
			"Current activities which includes Read, Write, Misc, Error, Reconnect or None of the device."
	::= { clsaDeviceEntry 10}

	clsadSCSIReadCmds   OBJECT-TYPE
		SYNTAX	INTEGER
		ACCESS	read-only
		STATUS	mandatory
		DESCRIPTION
			"The amount of read SCSI commands have been sent to the device."
	::= { clsaDeviceEntry 11 }

	clsadSCSIWriteCmds  OBJECT-TYPE
		SYNTAX	INTEGER
		ACCESS	read-only
		STATUS	mandatory
		DESCRIPTION
			"The amount of write SCSI commands have been sent to the device."
	::= { clsaDeviceEntry 12 }

	clsadOtherSCSICmds  OBJECT-TYPE
		SYNTAX	INTEGER
		ACCESS	read-only
		STATUS	mandatory
		DESCRIPTION
			"The amount of not read or write SCSI commands have been sent to the device."
	::= { clsaDeviceEntry 13 }

	clsadErrors OBJECT-TYPE
		SYNTAX	INTEGER
		ACCESS	read-only
		STATUS	mandatory
		DESCRIPTION
			"The amount of SCSI commands that occur read/write error sent to the device."
	::= { clsaDeviceEntry 14 }

	clsadDataRead   OBJECT-TYPE
		SYNTAX	DisplayString
		ACCESS	read-only
		STATUS	mandatory
		DESCRIPTION
			"The amount of bytes have been read from the device."
	::= { clsaDeviceEntry 15 }

	clsadDataWritten    OBJECT-TYPE
		SYNTAX	DisplayString
		ACCESS	read-only
		STATUS	mandatory
		DESCRIPTION
			"The amount of bytes have been writen to the device."
	::= { clsaDeviceEntry 16 }

	clsadVolumeTable    OBJECT-TYPE
		SYNTAX  SEQUENCE OF ClsadVolume
		ACCESS	not-accessible
		STATUS	mandatory
		DESCRIPTION
			"A table containing volume created of the device."
	::= { clsaDeviceEntry 17 }

	clsadVolumeEntry    OBJECT-TYPE
		SYNTAX  ClsadVolume
		ACCESS  not-accessible
		STATUS	mandatory
		DESCRIPTION
			"Information about the hardware property and file system of one volume."
		INDEX { clsadvName }
	::= { clsadVolumeTable 1 }

	ClsadVolume ::= SEQUENCE {
		clsadvName              DisplayString,
		clsadvAdapterNum        INTEGER,
		clsadvDeviceName        DisplayString,
		clsadvLogicalVolumeName DisplayString,
		clsadvFS                DisplayString,
		clsadvLogical           DisplayString,
		clsadvTotalSize         DisplayString,
		clsadvAvailSize         DisplayString		
	}

	clsadvName  OBJECT-TYPE
		SYNTAX	DisplayString
		ACCESS	read-only
		STATUS	mandatory
		DESCRIPTION
			"The hostname of the IPStor server that the client connected."
	::= { clsadVolumeEntry 1 }

	clsadvAdapterNum    OBJECT-TYPE
		SYNTAX	INTEGER
		ACCESS	read-only
		STATUS	mandatory
		DESCRIPTION
			"The SCSI adapter number."
	::= { clsadVolumeEntry 2 }

	clsadvDeviceName    OBJECT-TYPE
		SYNTAX	DisplayString
		ACCESS	read-only
		STATUS	mandatory
		DESCRIPTION
			"The resource name created by the user."
	::= { clsadVolumeEntry 3 }

	clsadvLogicalVolumeName OBJECT-TYPE
		SYNTAX	DisplayString
		ACCESS	read-only
		STATUS	mandatory
		DESCRIPTION
			"The volume name created by the user."
	::= { clsadVolumeEntry 4 }

	clsadvFS    OBJECT-TYPE
		SYNTAX	DisplayString
		ACCESS	read-only
		STATUS	mandatory
		DESCRIPTION
			"Inentify the type of file system on the volume."
	::= { clsadVolumeEntry 5 }

	clsadvLogical   OBJECT-TYPE
		SYNTAX	DisplayString
		ACCESS	read-only
		STATUS	mandatory
		DESCRIPTION
			"Identify the drive letter if it's available."
	::= { clsadVolumeEntry 6 }

	clsadvTotalSize OBJECT-TYPE
		SYNTAX	DisplayString
		ACCESS	read-only
		STATUS	mandatory
		DESCRIPTION
			"The amount of the allocated size which is representing with byte unit."
	::= { clsadVolumeEntry 7 }

	clsadvAvailSize OBJECT-TYPE
		SYNTAX	DisplayString
		ACCESS	read-only
		STATUS	mandatory
		DESCRIPTION
			"The amount of the available size which is representing with byte unit."
	::= { clsadVolumeEntry 8 }
	
-- ***************************************************************
-- IPStor OEM type.
-- ***************************************************************
--
-- These are the returned values of the OEM type.
-- returned to:  .iso.org.dod.internet.mgmt.mib-2.system.sysObjectID.0
--

	companyName	OBJECT-TYPE
		SYNTAX  DisplayString
		ACCESS  read-only
		STATUS  mandatory
		DESCRIPTION
			"Identify the company name of the OEM product."
	::= { ipstoroeminfo 1 }

	productName	OBJECT-TYPE
		SYNTAX  DisplayString
		ACCESS  read-only
		STATUS  mandatory
		DESCRIPTION
			"Identify the OEM product name."
	::= { ipstoroeminfo 2 }

-- ***************************************************************
-- FalconStor Appliance Info.
-- ***************************************************************

      modelName   OBJECT-TYPE
            SYNTAX  DisplayString
            ACCESS  read-only
            STATUS  mandatory
            DESCRIPTION
                  "Identify the FalconStor appliance model."
      ::= { falconstorapplianceinfo 1 }

      serialNumber      OBJECT-TYPE
            SYNTAX  DisplayString
            ACCESS  read-only
            STATUS  mandatory
            DESCRIPTION
                  "Identify the FalconStor appliance serial number."
      ::= { falconstorapplianceinfo 2 }


-- ***************************************************************
-- IPStor SNMP Agent type.
-- ***************************************************************
--
-- These are the returned values of the agent type.
-- returned to:  .iso.org.dod.internet.mgmt.mib-2.system.sysObjectID.0
--
--	hpux9             OBJECT IDENTIFIER ::= { ipstorsnmpagent 1 }
--	hpux10            OBJECT IDENTIFIER ::= { ipstorsnmpagent 6 }
--	sunos4            OBJECT IDENTIFIER ::= { ipstorsnmpagent 2 }
--	solaris           OBJECT IDENTIFIER ::= { ipstorsnmpagent 3 }
--	osf               OBJECT IDENTIFIER ::= { ipstorsnmpagent 4 }
--	ultrix            OBJECT IDENTIFIER ::= { ipstorsnmpagent 5 }
--	netbsd1           OBJECT IDENTIFIER ::= { ipstorsnmpagent 7 }
--	freebsd           OBJECT IDENTIFIER ::= { ipstorsnmpagent 8 }
--	irix              OBJECT IDENTIFIER ::= { ipstorsnmpagent 9 }
--	linux             OBJECT IDENTIFIER ::= { ipstorsnmpagent 10 }
--	bsdi              OBJECT IDENTIFIER ::= { ipstorsnmpagent 11 }
--	openbsd           OBJECT IDENTIFIER ::= { ipstorsnmpagent 12 }

-- ***************************************************************
-- Related traps 
-- ***************************************************************

    statisticTrap   TRAP-TYPE
        ENTERPRISE  ipstor
        VARIABLES   { alarmValue, alarmRisingThreshold, alarmFallingThreshold }
        DESCRIPTION
            "When the sampled value of monitered object is greater than the threshold of upper-bound or 
	         less than the lower-bound, the snmp daemon of IPStor server will send out such kind of trap."
        ::= 1

    diskFullTrap    TRAP-TYPE
        ENTERPRISE  ipstor
        VARIABLES   { alarmValue, alarmRisingThreshold }
        DESCRIPTION
            "When the usage of virtual resource is greater than the threshold of upper-bound, the snmp daemon 
             of IPStor server will send out such kind of trap."
        ::= 2
        
    processDownTrap TRAP-TYPE
        ENTERPRISE  ipstor
        VARIABLES   { alarmName }
        DESCRIPTION 
            "When the monitored process or module is stop to service, the snmp daemon of IPStor server will send out such kind of trap."
        ::= 3
        
    failOverStartTrap   TRAP-TYPE
        ENTERPRISE  ipstor
        DESCRIPTION 
            "When the failover module start to take over the dead one, the snmp daemon of IPStor server will send out such kind of trap."
        ::= 4

    failOverRecoveredTrap   TRAP-TYPE
        ENTERPRISE  ipstor
        DESCRIPTION 
            "When the failover module start to recover from another one, the snmp daemon of IPStor server will send out such kind of trap."
        ::= 5

    criticalLogMessage  TRAP-TYPE
        ENTERPRISE  ipstor
        DESCRIPTION 
            "The IPStor console will receive all log messages of critical degree if the property is set via IPStor console."
        ::= 6

    errorLogMessage TRAP-TYPE
        ENTERPRISE  ipstor
        DESCRIPTION 
            "The IPStor console will receive all log messages of error degree if the property is set via IPStor console."
        ::= 7

    warningLogMessage   TRAP-TYPE
        ENTERPRISE  ipstor
        DESCRIPTION 
            "The IPStor console will receive all log messages of warning degree if the property is set via IPStor console."
        ::= 8
        
    informationalLogMessage TRAP-TYPE
        ENTERPRISE  ipstor
        DESCRIPTION 
            "The IPStor console will receive all log messages of informational degree if the property is set via IPStor console."
        ::= 9
END
