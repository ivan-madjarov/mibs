HP-USER-AUTH DEFINITIONS ::= BEGIN

    IMPORTS
        hpSwitch            
            FROM HP-ICF-OID            
        InterfaceIndex            
            FROM IF-MIB            
        VlanIndex            
            FROM Q-BRIDGE-MIB            
        SnmpAdminString            
            FROM SNMP-FRAMEWORK-MIB            
        OBJECT-GROUP, MODULE-COMPLIANCE, NOTIFICATION-GROUP            
            FROM SNMPv2-CONF            
        IpAddress, Integer32, Unsigned32, OBJECT-TYPE, Counter32,
        MODULE-IDENTITY, NOTIFICATION-TYPE
            FROM SNMPv2-SMI
        TruthValue, MacAddress, RowStatus, DisplayString, DateAndTime
            FROM SNMPv2-TC
        InetAddressType, InetAddress
            FROM INET-ADDRESS-MIB;


    -- 1.3.6.1.4.1.11.2.14.11.5.1.19
    hpicfUsrAuthMIB MODULE-IDENTITY
 
        LAST-UPDATED "201306120000Z"      -- Jun 12, 2013 at 00:00 GMT
        ORGANIZATION "HP Networking"
        CONTACT-INFO 
                    "Hewlett-Packard Company
                     8000 Foothills Blvd.
                     Roseville, CA 95747"
        DESCRIPTION 
            "Added description for hpicfUsrAuthMacAuthUsrNumberCnt in
             hpicfUsrAuthSystem and hpicfUsrAuthMacAuthSessionUsrNumberCnt
             in hpicfUsrAuthMacAuthSessionStatsEntry."
        REVISION "201306120000Z"      -- Jun 12, 2013 at 00:00 GMT
        DESCRIPTION
            "Added hpicfUsrAuthLastLogin objects and group
              hpicfUsrAuthLastLoginGroup. Added objects
              hpicfUsrAuthLastLoginNotifyStatus,
              hpicfUsrAuthLastLoginNotifyAddrType,
              hpicfUsrAuthLastLoginNotifyAddr and table
              hpicfUsrAuthLastLoginEntry. Deprecated
              compliances hpicfUsrAuthCompliance1,
              hpicfUsrAuthCompliance1, 
              hpicfUsrAuthCompliance2,
              hpicfUsrAuthCompliance3,
              hpicfUsrAuthCompliance4,
              hpicfUsrAuthCompliance5.
              Deprecated groups
              hpicfNotificationConfigDataGroup and
              added hpicfNotificationConfigDataGroup1 "
        REVISION "201302250000Z"      -- Feb 25, 2013 at 00:00 GMT
	DESCRIPTION "Added hpicfUsrAuthLMAAdminStatus, hpicfUsrAuthPortsGroup1
		     hpicfUsrAuthCompliance8 and deprecated hpicfUsrAuthCompliance7,
		     hpicfUsrAuthPortsGroup."
        REVISION "201205010000Z"      -- May 1, 2012 at 00:00 GMT
        DESCRIPTION
            "Added hpSwitchUserLastLogin objects and
             hpicfUsrAuthLastLoginGroup."
        REVISION "201108290000Z"      -- August 29, 2011 at 00:00 GMT
        DESCRIPTION
            "This MIB module contains the definitions of Managed
            Objects for various subsystems that perform
            user authentication. The subsystems under control
            by this MIB are:
            'WebAuth' - Web-based login authentication
            'MacAuth' - MAC address-based authentication
            'CLI Password' - CLI-based login authentication"
        REVISION "201108290000Z"      -- August 29, 2011 at 00:00 GMT
        DESCRIPTION
            "Added description for hpicfUsrAuthMacAuthSessionTimeout in 
             HpicfUsrAuthMacAuthSessionStatsEntry and hpicfUsrAuthWebAuthSessionTimeout 
             in HpicfUsrAuthWebAuthSessionStatsEntry."
        REVISION "201107210000Z"      -- July 21, 2011 at 00:00 GMT
        DESCRIPTION
            "Added hpicfUsrAuthMacAuthSessionTimeout in HpicfUsrAuthMacAuthSessionStatsEntry
             and hpicfUsrAuthWebAuthSessionTimeout in HpicfUsrAuthWebAuthSessionStatsEntry."
        REVISION "201001280000Z"      -- January 28, 2010 at 00:00 GMT
        DESCRIPTION
            "Added hpicfUsrAuthWebAuthAccessDeniedMode and
             hpicfUsrAuthWebAuthAccessDeniedMessage objects."
        REVISION "200912150000Z"      -- December 15, 2009 at 00:00 GMT
        DESCRIPTION
             "Added hpicfUsrAuthWebAuthAccessDeniedMode and
              hpicfUsrAuthWebAuthAccessDeniedMessage objects."
        REVISION "200907080000Z"      -- July 08, 2009 at 00:00 GMT
        DESCRIPTION
            "Added hpicfUsrAuthMacAuthCachedReauthPeriod and 
             hpicfUsrAuthWebAuthCachedReauthPeriod objects."
        REVISION "200903090000Z"      -- March 09, 2009 at 00:00 GMT
        DESCRIPTION
            "Added hpicfUsrAuthMacAuthPassword object"
        REVISION "200808061200Z"      -- August 06, 2008 at 12:00 GMT
        DESCRIPTION
            "Added web reauthentication and user reauthentication objects."
        REVISION "200708290000Z"      -- August 29, 2007 at 00:00 GMT
        DESCRIPTION 
            "Added hpicfUsrAuthWMA failure notification and objects"
        REVISION "200706221200Z"      -- June 22, 2007 at 12:00 GMT
        DESCRIPTION 
            "Added hpicfUsrAuthNotifyConformance group and objects."
        REVISION "200508050000Z"      -- August 05, 2005 at 00:00 GMT
        DESCRIPTION 
            "Added import objects."
        REVISION "200305231020Z"      -- May 23, 2003 at 10:20 GMT
        DESCRIPTION 
            "Initial revision."
        ::= { hpSwitch 19 }

    
--
-- Node definitions
--

    -- 1.3.6.1.4.1.11.2.14.11.5.1.19.0
    hpicfUsrAuthNotifications OBJECT IDENTIFIER ::= { hpicfUsrAuthMIB 0 }

    
    -- 1.3.6.1.4.1.11.2.14.11.5.1.19.0.1
    hpicfUsrAuthCLIAuthFail NOTIFICATION-TYPE
        OBJECTS { hpicfUsrAuthCLIFailCnt,
                  hpicfUsrAuthCLIInterface
--          Optional objects sent by new-style notifications (not
--          in the definition to avoid redefining this object)
--                hpicfUsrAuthLastLoginNotifyStatus,
--                hpicfUsrAuthLastLoginGeneration,
--                hpicfUsrAuthLastLoginNotifyAddrType,
--                hpicfUsrAuthLastLoginNotifyAddr
                }
        STATUS current
        DESCRIPTION 
            "This notification signifies that CLI password
             authentication has failed. Operational control of this
             notification is provided using
             hpicfUsrAuthCliNotifyEnable. Agents complying with
             hpicfUsrAuthCompliance6 always additionally include
             hpicfUsrAuthLastLoginStatus. They may include
             hpicfUsrAuthLastLoginNotifyAddrType and
             hpicfUsrAuthLastLoginNotifyAddr to identify the source of
             the login attempt. They may also include an instance of
             hpicfUsrAuthLastLoginGeneration. The
             hpicfUsrAuthLastLoginEntry index in this object may be used
             to retrieve other objects in the row that identify the
             target user of this login attempt. If this index is zero,
             then the login attempt was to an unknown username. The
             value of hpicfUsrAuthLastLoginGeneration supplied in the
             notification should be compared to the retrieved object
             value to ensure that the row has not changed since the
             notification was sent."
        ::= { hpicfUsrAuthNotifications 1 }

    
    -- 1.3.6.1.4.1.11.2.14.11.5.1.19.0.2
    hpicfUsrAuthPasswdChng NOTIFICATION-TYPE
        OBJECTS { hpicfUsrAuthCLIPasswdSet, hpicfUsrAuthCLIPwdNotifyCnt }
        STATUS current
        DESCRIPTION 
            "An hpicfUsrAuthPasswdChng notification signifies that
                         the manager password has been changed.  The value of 
                         hpicfUsrAuthCLIPasswdSet can be used to determine
                         whether the password has been set or cleared by this action.
            "
        ::= { hpicfUsrAuthNotifications 2 }

    
    -- 1.3.6.1.4.1.11.2.14.11.5.1.19.0.3
    hpicfPortSecAuthFailure NOTIFICATION-TYPE
        OBJECTS { hpicfUsrAuthWMAFailCnt, 
            hpicfUsrAuthWMAFailVlan, 
            hpicfUsrAuthWMAFailPort, 
            hpicfUsrAuthWMAFailMAC }
        STATUS current
        DESCRIPTION 
            "This notification indicates a failed Port Security
            (network access) authentication event."
        ::= { hpicfUsrAuthNotifications 3 }


    -- 1.3.6.1.4.1.11.2.14.11.5.1.19.1
    hpicfUsrAuthSystem OBJECT IDENTIFIER ::= { hpicfUsrAuthMIB 1 }

    
    -- 1.3.6.1.4.1.11.2.14.11.5.1.19.1.1
    hpicfUsrAuthWebAuthDhcpBaseAddress OBJECT-TYPE
        SYNTAX IpAddress
        MAX-ACCESS read-write
        STATUS current
        DESCRIPTION
            "For all ports running with web authentication 
            enabled: Specifies the base address that should 
            be used by the switch DHCP server for web-based 
            authentication purposes."
        ::= { hpicfUsrAuthSystem 1 }

    
    -- 1.3.6.1.4.1.11.2.14.11.5.1.19.1.2
    hpicfUsrAuthWebAuthDhcpMask OBJECT-TYPE
        SYNTAX IpAddress
        MAX-ACCESS read-write
        STATUS current
        DESCRIPTION
            "For all ports running with web authentication
            enabled: Specifies the subnet mask to be used in 
            conjunction with the DHCP base address when 
            servicing DHCP requests.
            
            Allowable mask range is 255.255.240.0 (20) to 
            255.255.255.0 (24)."
        ::= { hpicfUsrAuthSystem 2 }

    
    -- 1.3.6.1.4.1.11.2.14.11.5.1.19.1.3
    hpicfUsrAuthWebAuthDhcpLease OBJECT-TYPE
        SYNTAX Integer32 (1..30)
        MAX-ACCESS read-write
        STATUS current
        DESCRIPTION
            "For all ports running with web authentication
            enabled: Specifies the DHCP lease length in 
            seconds."
        ::= { hpicfUsrAuthSystem 3 }

    
    -- 1.3.6.1.4.1.11.2.14.11.5.1.19.1.4
    hpicfUsrAuthMacAuthAddrFormat OBJECT-TYPE
        SYNTAX INTEGER
            {
            noDelimiter(1),
            singleDash(2),
            multiDash(3),
            multiColon(4),
            noDelimiterUppercase(5),
            singleDashUppercase(6),
            multiDashUppercase(7),
            multiColonUppercase(8)
            }
        MAX-ACCESS read-write
        STATUS current
        DESCRIPTION
            "For all ports running with MAC authentication
            enabled: Specifies the MAC address format to use
            in the RADIUS access-request, as follows:
                    'noDelimiter'  - Sends MAC address in  aabbccddeeff format
                    'singleDash'   - Sends MAC address in aabbcc-ddeeff format
                    'multiDash'    - Sends MAC address in aa-bb-cc-dd-ee-ff format
                    'multiColon'   - Sends MAC address in aa:bb:cc:dd:ee:ff format
                    'noDelimiterUppercase'  - Sends MAC address in AABBCCDDEEFF format
                    'singleDashUppercase'   - Sends MAC address in AABBCC-DDEEFF format
                    'multiDashUppercase'    - Sends MAC address in AA-BB-CC-DD-EE-FF format
                    'multiColonUppercase'   - Sends MAC address in AA:BB:CC:DD:EE:FF format
            The default value is noDelimiter(1)."
        ::= { hpicfUsrAuthSystem 4 }

    
    -- 1.3.6.1.4.1.11.2.14.11.5.1.19.1.5
    hpicfUsrAuthCliNotifyEnable OBJECT-TYPE
        SYNTAX INTEGER
            {
            enabled(1),
            disabled(2)
            }
        MAX-ACCESS read-write
        STATUS current
        DESCRIPTION
            "The operational status of hpicfUsrAuthCliAuthFail notifications.
            The default value is 1 (Enabled).  A value of 2 represents
            Disabled.  Writing this object requires authentication, such 
            as provided by SNMPv3.
            "
        ::= { hpicfUsrAuthSystem 5 }

    
    -- 1.3.6.1.4.1.11.2.14.11.5.1.19.1.6
    hpicfUsrAuthCLIInterface OBJECT-TYPE
        SYNTAX INTEGER
            {
            serial(1),
            telnet(2),
            ssh(3),
            sshPublicKey(4),
            webui(5),
            portAccess(6),
            other(9)
            }
        MAX-ACCESS accessible-for-notify
        STATUS current
        DESCRIPTION
            "The physical interface, network protocol, or other
             authentication type that is associated with this
             notification."
        ::= { hpicfUsrAuthSystem 6 }

    
--  
    -- 1.3.6.1.4.1.11.2.14.11.5.1.19.1.7
    hpicfUsrAuthCLIPasswdSet OBJECT-TYPE
        SYNTAX TruthValue
        MAX-ACCESS accessible-for-notify
        STATUS current
        DESCRIPTION
            "Indicates whether the CLI manager password
            is set.  1 indicates True while 2
            indicates False.
            "
        ::= { hpicfUsrAuthSystem 7 }

    
    -- 1.3.6.1.4.1.11.2.14.11.5.1.19.1.8
    hpicfUsrAuthCLIFailCnt OBJECT-TYPE
        SYNTAX Integer32
        MAX-ACCESS accessible-for-notify
        STATUS current
        DESCRIPTION
            "The count of hpicfUsrAuthPasswdFail notifications sent by the hpicfUsrAuth
            entity to the SNMP entity.  The actual count of notifications sent by SNMP
            may be lower due to rate limiting or configuration."
        ::= { hpicfUsrAuthSystem 8 }

    
    -- 1.3.6.1.4.1.11.2.14.11.5.1.19.1.9
    hpicfUsrAuthCLIPwdNotifyCnt OBJECT-TYPE
        SYNTAX Unsigned32
        MAX-ACCESS accessible-for-notify
        STATUS current
        DESCRIPTION
            "A count of CLI password change notifications
            sent from the Auth entity to the SNMP entity
            within the switch.  This count may therefore differ from
            the count of notifications actually sent by the SNMP
            entity due to switch configuration (e.g., the value
            of hpicfUsrAuthNotifyEnable.)"
        ::= { hpicfUsrAuthSystem 9 }

    
    -- 1.3.6.1.4.1.11.2.14.11.5.1.19.1.10
    hpicfUsrAuthWMAFailCnt OBJECT-TYPE
        SYNTAX Unsigned32
        MAX-ACCESS accessible-for-notify
        STATUS current
        DESCRIPTION
            "The count of hpicfPortSecAuthFailure notifications sent by the hpicfUsrAuth
            entity to the SNMP entity.  The actual count of notifications sent by SNMP
            may be lower due to rate limiting or configuration."
        ::= { hpicfUsrAuthSystem 10 }

    
    -- 1.3.6.1.4.1.11.2.14.11.5.1.19.1.11
    hpicfUsrAuthWMAFailMAC OBJECT-TYPE
        SYNTAX MacAddress
        MAX-ACCESS accessible-for-notify
        STATUS current
        DESCRIPTION
            "The MAC address supplied in the failed authentication request."
        ::= { hpicfUsrAuthSystem 11 }

    
    -- 1.3.6.1.4.1.11.2.14.11.5.1.19.1.12
    hpicfUsrAuthWMAFailPort OBJECT-TYPE
        SYNTAX Integer32
        MAX-ACCESS accessible-for-notify
        STATUS current
        DESCRIPTION
            "The port index of the failed authentication request."
        ::= { hpicfUsrAuthSystem 12 }

    
    -- 1.3.6.1.4.1.11.2.14.11.5.1.19.1.13
    hpicfUsrAuthWMAFailVlan OBJECT-TYPE
        SYNTAX Integer32
        MAX-ACCESS accessible-for-notify
        STATUS current
        DESCRIPTION
            "The VLAN ID associated with the failed authentication request."
        ::= { hpicfUsrAuthSystem 13 }


    -- 1.3.6.1.4.1.11.2.14.11.5.1.19.1.14
    hpicfUsrAuthPortSecNotifyEnable OBJECT-TYPE
        SYNTAX INTEGER
            {
            enabled(1),
            disabled(2)
            }
        MAX-ACCESS read-write
        STATUS current
        DESCRIPTION
            "Provides operational control of hpicfPortSecAuthFailure 
            notification.  When enabled (1), the notification will
            be sent.  When disabled (2), the notification will not 
            be sent.  Setting this object requires authentication,
            such as provided by SNMPv3.
            "
        ::= { hpicfUsrAuthSystem 14 }

   
    -- 1.3.6.1.4.1.11.2.14.11.5.1.19.1.15
    hpicfUsrAuthPasswdNotifyEnable OBJECT-TYPE
        SYNTAX INTEGER
            {
            enabled(1),
            disabled(2)
            }
        MAX-ACCESS read-write
        STATUS current
        DESCRIPTION
            "Provides operational control of hpicfUsrAuthPasswdChng notification.  
            When enabled (1), the notification will be sent.  
            When disabled (2), the notification will not be sent.
            Setting this object requires authentication, such
            as provided by SNMPv3."
        ::= { hpicfUsrAuthSystem 15 }


    -- 1.3.6.1.4.1.11.2.14.11.5.1.19.1.16
    --
    -- EWA Server Table
    -- 
    hpicfUsrAuthWMAEWAServerTable OBJECT-TYPE
        SYNTAX SEQUENCE OF HpicfUsrAuthWMAEWAServerEntry
        MAX-ACCESS not-accessible
        STATUS current
        DESCRIPTION
            "A table of the Enhanced Web Auth servers." 
        ::= { hpicfUsrAuthSystem 16 } 


    -- 1.3.6.1.4.1.11.2.14.11.5.1.19.1.16.1
    hpicfUsrAuthWMAEWAServerEntry OBJECT-TYPE
              SYNTAX      HpicfUsrAuthWMAEWAServerEntry
              MAX-ACCESS  not-accessible
              STATUS      current
              DESCRIPTION
                "Addresses for an Enhanced Web Auth server."
              INDEX { hpicfUsrAuthWMAeWAServerIndex }
              ::= { hpicfUsrAuthWMAEWAServerTable 1 }


    HpicfUsrAuthWMAEWAServerEntry ::= SEQUENCE {
              hpicfUsrAuthWMAeWAServerIndex                  Integer32,
              hpicfUsrAuthWMAeWAServerIPAddressType          InetAddressType,
              hpicfUsrAuthWMAeWAServerIPAddress              InetAddress,
              hpicfUsrAuthWMAeWAServerPath                   OCTET STRING,           
              hpicfUsrAUthWMAeWAServerRowStatus              RowStatus
      }


    hpicfUsrAuthWMAeWAServerIndex OBJECT-TYPE
              SYNTAX      Integer32 
              MAX-ACCESS  not-accessible
              STATUS      current
              DESCRIPTION
                "Index into hpicfUsrAuthWMAEWAServerTable."
              ::= { hpicfUsrAuthWMAEWAServerEntry 1 }


    hpicfUsrAuthWMAeWAServerIPAddressType OBJECT-TYPE
              SYNTAX      InetAddressType
              MAX-ACCESS  read-create
              STATUS      current
              DESCRIPTION
                "The type of Enhanced Web Auth Server Address."
              DEFVAL { unknown }
              ::= { hpicfUsrAuthWMAEWAServerEntry 2 }


    hpicfUsrAuthWMAeWAServerIPAddress OBJECT-TYPE
              SYNTAX      InetAddress
              MAX-ACCESS  read-create
              STATUS      current
              DESCRIPTION
                "The IP address of the Enhanced Web Auth Server.
                 If set to 0.0.0.0 or URL not configured
                 no Enhanced Web Auth Server will run."
              ::= { hpicfUsrAuthWMAEWAServerEntry 3 }


    hpicfUsrAuthWMAeWAServerPath    OBJECT-TYPE
              SYNTAX       OCTET STRING 
              MAX-ACCESS   read-create
              STATUS       current
              DESCRIPTION 
                "The Enhanced Web Auth Server Path for the location
                 of the Enhanced Web Auth Pages.  If not configured 
                 the default path will be used." 
              ::= { hpicfUsrAuthWMAEWAServerEntry 4 }


    hpicfUsrAUthWMAeWAServerRowStatus OBJECT-TYPE
              SYNTAX       RowStatus
              MAX-ACCESS   read-create
              STATUS       current
              DESCRIPTION 
                "This marks the row as active/inactive." 
              ::= { hpicfUsrAuthWMAEWAServerEntry 5 }
    
     -- 1.3.6.1.4.1.11.2.14.11.5.1.19.1.17
    --
    -- WMA Redirect Server Table
    --

    -- 1.3.6.1.4.1.11.2.14.11.5.1.19.1.17
    hpicfUsrAuthRedirectServerTable OBJECT-TYPE
         SYNTAX      SEQUENCE OF HpicfUsrAuthRedirectServerEntry 
         MAX-ACCESS  not-accessible
         STATUS      current
         DESCRIPTION
             "A table of the authentication Redirect Servers." 
         ::= { hpicfUsrAuthSystem 17 }

    -- 1.3.6.1.4.1.11.2.14.11.5.1.19.1.17.X
    hpicfUsrAuthRedirectServerEntry OBJECT-TYPE
         SYNTAX      HpicfUsrAuthRedirectServerEntry 
         MAX-ACCESS  not-accessible
         STATUS      current
         DESCRIPTION
            "Attributes of an authentication Redirect Server."
         INDEX { hpicfUsrAuthRedirectServerIndex }
         ::= { hpicfUsrAuthRedirectServerTable 1 }
  
    HpicfUsrAuthRedirectServerEntry ::= SEQUENCE {
         hpicfUsrAuthRedirectServerIndex             Integer32, 
         hpicfUsrAuthRedirectServerURL               OCTET STRING,
         hpicfUsrAuthRedirectServerRowStatus         RowStatus 
    }

    hpicfUsrAuthRedirectServerIndex OBJECT-TYPE
         SYNTAX      Integer32
         MAX-ACCESS  not-accessible
         STATUS      current
         DESCRIPTION
            "Index into hpicfUsrAuthRedirectServerTable."
         ::= { hpicfUsrAuthRedirectServerEntry 1 }
         
    hpicfUsrAuthRedirectServerURL OBJECT-TYPE
         SYNTAX       OCTET STRING
         MAX-ACCESS   read-create
         STATUS       current
         DESCRIPTION
            "This object represents the authentication 
             Redirect Server's complete URL for the location
             of the redirect server login or warning page. This 
             value must begin with 'http://' or 'https://' and
             should include the DNS name, TCP port of the server
             if not 80 or SSL's 443, and the page path, if necessary."
          ::= { hpicfUsrAuthRedirectServerEntry 2 }
    
    hpicfUsrAuthRedirectServerRowStatus  OBJECT-TYPE
         SYNTAX       RowStatus
         MAX-ACCESS   read-create
         STATUS       current
         DESCRIPTION
            "This object indicates the status of this entry.
             Must NOT be active in order to modify some other 
             column of this config entry."
         ::= { hpicfUsrAuthRedirectServerEntry 3 }

    -- 1.3.6.1.4.1.11.2.14.11.5.1.19.1.18
    hpicfUsrAuthRedirectServerRestrictiveFilter OBJECT-TYPE
         SYNTAX      INTEGER {
                       enabled(1),
                       disabled(2)
                     }
         MAX-ACCESS   read-write
         STATUS       current
         DESCRIPTION
            "If enabled, only the configured initial
             web page will be returned for all client requests. The enabled state would
             generally be used to simply display an informative warning
             message to failed macAuth clients.  If disabled, all
             client/redirect-server http traffic will be permitted."
         DEFVAL { disabled }
         ::= { hpicfUsrAuthSystem 18 }

    -- 1.3.6.1.4.1.11.2.14.11.5.1.19.1.19
    hpicfUsrAuthRedirectServerClientTimeout OBJECT-TYPE
         SYNTAX      Integer32
         MAX-ACCESS  read-write
         STATUS      current
         DESCRIPTION
            "The time (in seconds) that a client will be left in the
             unauthorized authentication redirection state before 
             being removed from the state tables, temporarily 
             suspending further client/redirect-server http 
             traffic. After state table removal, client is 
             free to initiate authentication."
         DEFVAL { 180 }
         ::= { hpicfUsrAuthSystem 19 }

    -- 1.3.6.1.4.1.11.2.14.11.5.1.19.1.20
    hpicfUsrAuthRedirectServerAuthFailureStats OBJECT-TYPE
         SYNTAX      Counter32 
         MAX-ACCESS  read-only
         STATUS      current
         DESCRIPTION
            "The total number of times clients fail authentication 
             and initiate the authentication Redirect Server process 
             since reboot. A single client can be counted multiple 
             times."
         ::= { hpicfUsrAuthSystem 20 }

    -- 1.3.6.1.4.1.11.2.14.11.5.1.19.1.21
    hpicfUsrAuthCacheCredTimeOut OBJECT-TYPE
        SYNTAX Integer32
        MAX-ACCESS read-write
        STATUS current
        DESCRIPTION
            "Specifies the time in seconds, that the
             switch should remove the credentials.
             Reauthentication should take place with in
             small amount of time."
        DEFVAL { 600 }
        ::= { hpicfUsrAuthSystem 21 }

    -- 1.3.6.1.4.1.11.2.14.11.5.1.19.1.22
    hpicfUsrAuthClientReauthenticateTable OBJECT-TYPE
         SYNTAX     SEQUENCE OF HpicfUsrAuthClientReauthenticateEntry
         MAX-ACCESS not-accessible
         STATUS     current
         DESCRIPTION
            "A table containing configuration/control variables
             indexed by port and client MAC."
        ::= { hpicfUsrAuthSystem 22 }

   -- 1.3.6.1.4.1.11.2.14.11.5.1.19.1.22.1
    hpicfUsrAuthClientReauthenticateEntry OBJECT-TYPE
         SYNTAX     HpicfUsrAuthClientReauthenticateEntry
         MAX-ACCESS not-accessible
         STATUS     current
         DESCRIPTION
            "The table entry provides the means by which a
             client on an authentication interface can be forced to
             reauthenticate."
        INDEX { hpicfUsrAuthClientReauthenticateInterfaceIndex,
                hpicfUsrAuthClientReauthenticateMacAddress}
        ::= { hpicfUsrAuthClientReauthenticateTable 1 }

    HpicfUsrAuthClientReauthenticateEntry ::= SEQUENCE {
         hpicfUsrAuthClientReauthenticateInterfaceIndex
             InterfaceIndex,
         hpicfUsrAuthClientReauthenticateMacAddress
              MacAddress,
         hpicfUsrAuthClientReauthenticate
              TruthValue
    }

    -- 1.3.6.1.4.1.11.2.14.11.5.1.19.1.22.1.1
    hpicfUsrAuthClientReauthenticateInterfaceIndex OBJECT-TYPE
         SYNTAX     InterfaceIndex
         MAX-ACCESS not-accessible
         STATUS     current
         DESCRIPTION
            "Index of client interfaces."
         ::= { hpicfUsrAuthClientReauthenticateEntry 1 }

    -- 1.3.6.1.4.1.11.2.14.11.5.1.19.1.22.1.2
    hpicfUsrAuthClientReauthenticateMacAddress OBJECT-TYPE
         SYNTAX      MacAddress
         MAX-ACCESS  not-accessible
         STATUS      current
         DESCRIPTION
            "Specifies the MAC address of the client."
         ::= { hpicfUsrAuthClientReauthenticateEntry 2 }

    -- 1.3.6.1.4.1.11.2.14.11.5.1.19.1.22.1.3
    hpicfUsrAuthClientReauthenticate  OBJECT-TYPE
         SYNTAX      TruthValue
         MAX-ACCESS  read-write
         STATUS      current
         DESCRIPTION
            "The reauthentication control for this client on this
             authentication interface. Setting this attribute TRUE
             forces this authenticated client to
             re-authenticate. That is, the client is deauthenticated
             and must transmit traffic in order to trigger
             reauthentication. Setting this attribute FALSE has no
             effect."
         ::= { hpicfUsrAuthClientReauthenticateEntry 3 }

    -- 1.3.6.1.4.1.11.2.14.11.5.1.19.1.23
    hpicfUsrAuthMacAuthPassword OBJECT-TYPE
         SYNTAX OCTET STRING
	 MAX-ACCESS   read-write
	 STATUS       current
	 DESCRIPTION
	    "This object represents the secret password value used by all
	     MAC auth clients. The default value of password is NULL. The
	     password if set(non NULL) will be used instead of MAC address
	     while constructing Radius request packet. The current maximum
	     length of password is 16."

         ::= { hpicfUsrAuthSystem 23 }

    -- 1.3.6.1.4.1.11.2.14.11.5.1.19.1.24
    hpicfUsrAuthWebAuthAccessDeniedMode OBJECT-TYPE
         SYNTAX       INTEGER {
                         disabled (1),
                         custom (2),
                         radius (3)
                      }
         MAX-ACCESS   read-write
         STATUS       current
         DESCRIPTION
           "Specifies the access denied mode that applies to the
            custom message embedded into the login failure page.
            The values:
            disabled (1) - the feature is disabled.
            custom   (2) - use the string configured by
            administrator via CLI or SNMP.
            radius   (3) - use the string in the 'reply-message'
            attribute of the received RADIUS response message."
         DEFVAL       {1}
         ::=  { hpicfUsrAuthSystem 24}
 
    -- 1.3.6.1.4.1.11.2.14.11.5.1.19.1.25
    hpicfUsrAuthWebAuthAccessDeniedMessage OBJECT-TYPE
         SYNTAX       OCTET STRING (SIZE (1..1024))
         MAX-ACCESS   read-write
         STATUS       current
         DESCRIPTION
           "Text of the access denied message that will be embedded
            into the custom web auth login failure page. This message
            will only be used when the access denied mode is set to
            'custom'. It can take up to 250 characters"
         ::=  { hpicfUsrAuthSystem 25}

    -- 1.3.6.1.4.1.11.2.14.11.5.1.19.1.26
    hpicfUsrAuthMacAuthUsrNumberCnt OBJECT-TYPE
         SYNTAX       Counter32 
         MAX-ACCESS   read-only 
         STATUS       current
         DESCRIPTION
            "This object specifies the total number of authenticated clients
             currently present in the switch. This does not include the 
             clients which are under process of authentication." 
         ::=  { hpicfUsrAuthSystem 26}

    -- 1.3.6.1.4.1.11.2.14.11.5.1.19.1.27
    hpicfUsrAuthLastLoginNotifyStatus OBJECT-TYPE
        SYNTAX      INTEGER { unknown(0),
                              successful(1),
                              failed(2),
                              failedLockOut(3),
                              lockedOut(4),
                              tableFull(5) }
        MAX-ACCESS  accessible-for-notify
        STATUS      current
        DESCRIPTION "The status of the failed login attempt.
                     successful(1) is not currently used. failed(2)
                     indicates a regular failure that did not cause
                     user lockout. failedLockOut(3) indicates a failure
                     that caused user lockout. lockedOut(4) indicates
                     that the user was locked out before the attempt was
                     made. tableFull(5) indicates lockout due to a full
                     lockout table, likely an indication of a serious
                     attack."
        ::= { hpicfUsrAuthSystem 27 }

    -- 1.3.6.1.4.1.11.2.14.11.5.1.19.1.28
    hpicfUsrAuthLastLoginNotifyAddrType OBJECT-TYPE
        SYNTAX      InetAddressType
        MAX-ACCESS  accessible-for-notify
        STATUS      current
        DESCRIPTION "The type of IP address from which the user's most
                     recent login attempt occurred. Unknown(0) indicates
                     the console."
        ::= { hpicfUsrAuthSystem 28 }

    -- 1.3.6.1.4.1.11.2.14.11.5.1.19.1.29
    hpicfUsrAuthLastLoginNotifyAddr OBJECT-TYPE
        SYNTAX      InetAddress
        MAX-ACCESS  accessible-for-notify
        STATUS      current
        DESCRIPTION "The IP address from which the user's most recent
                     login attempt occurred."
        ::= { hpicfUsrAuthSystem 29 }

    -- 1.3.6.1.4.1.11.2.14.11.5.1.19.2
    hpicfUsrAuthPorts OBJECT IDENTIFIER ::= { hpicfUsrAuthMIB 2 }

    
    -- 1.3.6.1.4.1.11.2.14.11.5.1.19.2.1
    hpicfUsrAuthPortTable OBJECT-TYPE
        SYNTAX SEQUENCE OF HpicfUsrAuthPortEntry
        MAX-ACCESS not-accessible
        STATUS current
        DESCRIPTION
            "A table of system level information about Web-
            MAC-based authentication for each port in the 
            switch."
        ::= { hpicfUsrAuthPorts 1 }

    
    -- 1.3.6.1.4.1.11.2.14.11.5.1.19.2.1.1
    hpicfUsrAuthPortEntry OBJECT-TYPE
        SYNTAX HpicfUsrAuthPortEntry
        MAX-ACCESS not-accessible
        STATUS current
        DESCRIPTION
            "The port number, operational mode and 
            re-authentication control for each switch port."
        INDEX { hpicfUsrAuthPortNumber }
        ::= { hpicfUsrAuthPortTable 1 }

    
    HpicfUsrAuthPortEntry ::=
        SEQUENCE { 
            hpicfUsrAuthPortNumber
                InterfaceIndex,
            hpicfUsrAuthWebAuthAdminStatus
                TruthValue,
            hpicfUsrAuthMacAuthAdminStatus
                TruthValue,
            hpicfUsrAuthPortReauthenticate
                TruthValue,
	    hpicfUsrAuthLMAAdminStatus
                TruthValue
         }

    -- 1.3.6.1.4.1.11.2.14.11.5.1.19.2.1.1.1
    hpicfUsrAuthPortNumber OBJECT-TYPE
        SYNTAX InterfaceIndex
        MAX-ACCESS accessible-for-notify
        STATUS current
        DESCRIPTION
            "The port number associated with this switch port."
        ::= { hpicfUsrAuthPortEntry 1 }

    
    -- 1.3.6.1.4.1.11.2.14.11.5.1.19.2.1.1.2
    hpicfUsrAuthWebAuthAdminStatus OBJECT-TYPE
        SYNTAX TruthValue
        MAX-ACCESS read-write
        STATUS current
        DESCRIPTION
            "Setting this attribute TRUE enables web-based
            authentication services.  A value of FALSE
            disabled web-based authentication.  This attribute
            cannot be set TRUE concurrently with 
            hpicfUsrAuthMacAuthAdminStatus."
        ::= { hpicfUsrAuthPortEntry 2 }

    
    -- 1.3.6.1.4.1.11.2.14.11.5.1.19.2.1.1.3
    hpicfUsrAuthMacAuthAdminStatus OBJECT-TYPE
        SYNTAX TruthValue
        MAX-ACCESS read-write
        STATUS current
        DESCRIPTION
            "Setting this attribute TRUE enables MAC-based
            authentication services.  A value of FALSE
            disabled MAC-based authentication.  This attribute
            cannot be set TRUE concurrently with 
            hpicfUsrAuthWebAuthAdminStatus."
        ::= { hpicfUsrAuthPortEntry 3 }

    
    -- 1.3.6.1.4.1.11.2.14.11.5.1.19.2.1.1.4
    hpicfUsrAuthPortReauthenticate OBJECT-TYPE
        SYNTAX TruthValue
        MAX-ACCESS read-write
        STATUS current
        DESCRIPTION
            "The reauthentication control for this port. Setting this 
            attribute TRUE forces all authenticated clients to 
            re-authenticate themselves. Setting this attribute FALSE
            has no effect. This attribute always returns FALSE
            when read."
        ::= { hpicfUsrAuthPortEntry 4 }

      -- 1.3.6.1.4.1.11.2.14.11.5.1.19.2.1.1.5
    hpicfUsrAuthLMAAdminStatus OBJECT-TYPE
        SYNTAX TruthValue
        MAX-ACCESS read-write
        STATUS current
        DESCRIPTION
            "Setting this attribute TRUE enables Local MAC-based
            authentication services.  A value of FALSE
            disabled MAC-based authentication.  This attribute
            cannot be set TRUE concurrently with
            hpicfUsrAuthWebAuthAdminStatus."
        ::= { hpicfUsrAuthPortEntry 5 }

    
    -- 1.3.6.1.4.1.11.2.14.11.5.1.19.3
    hpicfUsrAuthWebAuthConfig OBJECT IDENTIFIER ::= { hpicfUsrAuthMIB 3 }

    
    -- 1.3.6.1.4.1.11.2.14.11.5.1.19.3.1
    hpicfUsrAuthWebAuthConfigTable OBJECT-TYPE
        SYNTAX SEQUENCE OF HpicfUsrAuthWebAuthConfigEntry
        MAX-ACCESS not-accessible
        STATUS current
        DESCRIPTION
            "A table that contains the configuration objects for 
            Web-based Authentication associated with each port. An entry
            appears in this table for each port that may authenticate
            access to itself."
        ::= { hpicfUsrAuthWebAuthConfig 1 }

    
    -- 1.3.6.1.4.1.11.2.14.11.5.1.19.3.1.1
    hpicfUsrAuthWebAuthConfigEntry OBJECT-TYPE
        SYNTAX HpicfUsrAuthWebAuthConfigEntry
        MAX-ACCESS not-accessible
        STATUS current
        DESCRIPTION
            "The configuration information for Web-based authentication."
        INDEX { hpicfUsrAuthPortNumber }
        ::= { hpicfUsrAuthWebAuthConfigTable 1 }

    
    HpicfUsrAuthWebAuthConfigEntry ::=
        SEQUENCE { 
            hpicfUsrAuthWebAuthClientLimit
                Integer32,
            hpicfUsrAuthWebAuthClientMoves
                INTEGER,
            hpicfUsrAuthWebAuthSSLState
                INTEGER,
            hpicfUsrAuthWebAuthRedirectUrl
                OCTET STRING,
            hpicfUsrAuthWebAuthQuietPeriod
                Integer32,
            hpicfUsrAuthWebAuthServerTimeout
                Integer32,
            hpicfUsrAuthWebAuthServerMaxReq
                Integer32,
            hpicfUsrAuthWebAuthMaxRetries
                Integer32,
            hpicfUsrAuthWebAuthLogoffPeriod
                Integer32,
            hpicfUsrAuthWebAuthReAuthPeriod
                Integer32,
            hpicfUsrAuthWebAuthAuthVid
                VlanIndex,
            hpicfUsrAuthWebAuthUnauthVid
                VlanIndex,
            hpicfUsrAuthWebAuthCacheCredentials
                INTEGER,
            hpicfUsrAuthWebAuthCachedReauthPeriod
                Unsigned32
         }

    -- 1.3.6.1.4.1.11.2.14.11.5.1.19.3.1.1.1
    hpicfUsrAuthWebAuthClientLimit OBJECT-TYPE
        SYNTAX Integer32 (1..256)
        MAX-ACCESS read-write
        STATUS current
        DESCRIPTION
            "The maximum number of authenticated clients to allow on 
            the port."
        DEFVAL { 1 }
        ::= { hpicfUsrAuthWebAuthConfigEntry 1 }

    
    -- 1.3.6.1.4.1.11.2.14.11.5.1.19.3.1.1.2
    hpicfUsrAuthWebAuthClientMoves OBJECT-TYPE
        SYNTAX INTEGER
            {
            disabled(1),
            enabled(2)
            }
        MAX-ACCESS read-write
        STATUS current
        DESCRIPTION
            "Specifies whether client may roam across ports under
            web authentication control. Setting this attribute 
            'enabled'allows authenticated clients to roam to other 
            ports under web authentication control (that also have 
            this attribute set to 'enabled') without requiring a 
            re-authentication.  
            
            Setting this attribute 'disabled' disallows authenticated
            clients from roaming to other ports (regardless of that 
            port's attribute value).  The client has to re-
            authenticate, if it attempts to roam."
        DEFVAL { 1 }
        ::= { hpicfUsrAuthWebAuthConfigEntry 2 }

    
    -- 1.3.6.1.4.1.11.2.14.11.5.1.19.3.1.1.3
    hpicfUsrAuthWebAuthSSLState OBJECT-TYPE
        SYNTAX INTEGER
            {
            disabled(1),
            enabled(2)
            }
        MAX-ACCESS read-write
        STATUS current
        DESCRIPTION
            "Specifies whether web-based authentication should use an 
            SSL connection (i.e. https://) to switch to collect client  
            credentials.
            Note: A valid certificate must be configured on switch
            before SSL connections are enabled."
        DEFVAL { 1 }
        ::= { hpicfUsrAuthWebAuthConfigEntry 3 }

    
    -- 1.3.6.1.4.1.11.2.14.11.5.1.19.3.1.1.4
    hpicfUsrAuthWebAuthRedirectUrl OBJECT-TYPE
        SYNTAX OCTET STRING (SIZE (0..127))
        MAX-ACCESS read-write
        STATUS current
        DESCRIPTION
            "Specifies the URL, to which an authenticated client should
            be re-directed, after successful authentication."
        ::= { hpicfUsrAuthWebAuthConfigEntry 4 }

    
    -- 1.3.6.1.4.1.11.2.14.11.5.1.19.3.1.1.5
    hpicfUsrAuthWebAuthQuietPeriod OBJECT-TYPE
        SYNTAX Integer32 (1..65535)
        MAX-ACCESS read-write
        STATUS current
        DESCRIPTION
            "Specifies the time, in seconds, that the switch should 
            refrain from re-attempting an authentication request for
            a client whose credentials were rejected."
        DEFVAL { 60 }
        ::= { hpicfUsrAuthWebAuthConfigEntry 5 }

    
    -- 1.3.6.1.4.1.11.2.14.11.5.1.19.3.1.1.6
    hpicfUsrAuthWebAuthServerTimeout OBJECT-TYPE
        SYNTAX Integer32 (1..300)
        MAX-ACCESS read-write
        STATUS current
        DESCRIPTION
            "Specifies the time, in seconds, that the switch should 
            wait for an authentication reply to return before 
            considering it as timed out."
        DEFVAL { 30 }
        ::= { hpicfUsrAuthWebAuthConfigEntry 6 }

    
    -- 1.3.6.1.4.1.11.2.14.11.5.1.19.3.1.1.7
    hpicfUsrAuthWebAuthServerMaxReq OBJECT-TYPE
        SYNTAX Integer32 (1..10)
        MAX-ACCESS read-write
        STATUS current
        DESCRIPTION
            "Specifies the number of authentication requests that 
            must time out before failing authentication."
        DEFVAL { 3 }
        ::= { hpicfUsrAuthWebAuthConfigEntry 7 }

    
    -- 1.3.6.1.4.1.11.2.14.11.5.1.19.3.1.1.8
    hpicfUsrAuthWebAuthMaxRetries OBJECT-TYPE
        SYNTAX Integer32 (1..10)
        MAX-ACCESS read-write
        STATUS current
        DESCRIPTION
            "Specifies the number of authentication requests that
            must fail (i.e. invalid credentials) before failing 
            authentication."
        DEFVAL { 3 }
        ::= { hpicfUsrAuthWebAuthConfigEntry 8 }

    
    -- 1.3.6.1.4.1.11.2.14.11.5.1.19.3.1.1.9
    hpicfUsrAuthWebAuthLogoffPeriod OBJECT-TYPE
        SYNTAX Integer32 (1..999999999)
        MAX-ACCESS read-write
        STATUS current
        DESCRIPTION
            "Specifies the period, in seconds, at which an 
            authenticated client will be considered unauthenticated
            for a lack of activity (i.e. traffic originating 
            from client)."
        DEFVAL { 300 }
        ::= { hpicfUsrAuthWebAuthConfigEntry 9 }

    
    -- 1.3.6.1.4.1.11.2.14.11.5.1.19.3.1.1.10
    hpicfUsrAuthWebAuthReAuthPeriod OBJECT-TYPE
        SYNTAX Integer32 (0..999999999)
        MAX-ACCESS read-write
        STATUS current
        DESCRIPTION
            "Specifies the period, in seconds, at which an 
            authenticated client must re-authenticate. A value of 
            0 signifies that an authenticated client will never have 
            to re-authenticate."
        DEFVAL { 0 }
        ::= { hpicfUsrAuthWebAuthConfigEntry 10 }

    
    -- 1.3.6.1.4.1.11.2.14.11.5.1.19.3.1.1.11
    hpicfUsrAuthWebAuthAuthVid OBJECT-TYPE
        SYNTAX VlanIndex
        MAX-ACCESS read-write
        STATUS current
        DESCRIPTION
            "Specifies the port VID (PVID) that should be used for 
            an authenticated client."
        ::= { hpicfUsrAuthWebAuthConfigEntry 11 }

    
    -- 1.3.6.1.4.1.11.2.14.11.5.1.19.3.1.1.12
    hpicfUsrAuthWebAuthUnauthVid OBJECT-TYPE
        SYNTAX VlanIndex
        MAX-ACCESS read-write
        STATUS current
        DESCRIPTION
            "Specifies the port VID (PVID) that should be used for 
            an unauthenticated client."
        ::= { hpicfUsrAuthWebAuthConfigEntry 12 }

    -- 1.3.6.1.4.1.11.2.14.11.5.1.19.3.1.1.13
    hpicfUsrAuthWebAuthCacheCredentials OBJECT-TYPE
        SYNTAX INTEGER
            {
            disabled(1),
            enabled(2)
            }
        MAX-ACCESS read-write
        STATUS current
        DESCRIPTION
            "Specifies whether to cache client credentials or not.
             Setting this variable 'enabled' allows to cache
             authenticated clients credentials.
             Setting this variable 'disabled' disallows to cache
             authenticated clients credentials."
        DEFVAL { 1 }
        ::= { hpicfUsrAuthWebAuthConfigEntry 13 }

    -- 1.3.6.1.4.1.11.2.14.11.5.1.19.3.1.1.14
    hpicfUsrAuthWebAuthCachedReauthPeriod OBJECT-TYPE
        SYNTAX Unsigned32 (0..2147483647)
        UNITS "seconds"
        MAX-ACCESS read-write
        STATUS current
        DESCRIPTION
            "The value indicates the period in seconds, during which
             cached re-authentication is allowed on the port.If value is
             zero then the period of cached re-authentication is unlimited."
        DEFVAL { 0 }
        ::= { hpicfUsrAuthWebAuthConfigEntry 14 }

    -- 1.3.6.1.4.1.11.2.14.11.5.1.19.3.2
    hpicfUsrAuthWebAuthClientReauthenticateTable OBJECT-TYPE
         SYNTAX     SEQUENCE OF HpicfUsrAuthWebAuthClientReauthenticateEntry
         MAX-ACCESS not-accessible
         STATUS     current
         DESCRIPTION
            "A table containing WebAuth configuration/control variables
             indexed by port and client MAC."
        ::= { hpicfUsrAuthWebAuthConfig 2 }

    hpicfUsrAuthWebAuthClientReauthenticateEntry OBJECT-TYPE
         SYNTAX     HpicfUsrAuthWebAuthClientReauthenticateEntry
         MAX-ACCESS not-accessible
         STATUS     current
         DESCRIPTION
            "The table entry provides the means by which a WebAuth
             client on an authentication interface can be forced to
             reauthenticate."
        INDEX { hpicfUsrAuthWebAuthClientReauthenticateInterfaceIndex,
                hpicfUsrAuthWebAuthClientReauthenticateMacAddress}
        ::= { hpicfUsrAuthWebAuthClientReauthenticateTable 1 }

    -- 1.3.6.1.4.1.11.2.14.11.5.1.19.3.2.1
    HpicfUsrAuthWebAuthClientReauthenticateEntry ::= SEQUENCE {
         hpicfUsrAuthWebAuthClientReauthenticateInterfaceIndex
             InterfaceIndex,
         hpicfUsrAuthWebAuthClientReauthenticateMacAddress
              MacAddress,
         hpicfUsrAuthWebAuthClientReauthenticate
              TruthValue
    }

    -- 1.3.6.1.4.1.11.2.14.11.5.1.19.3.2.1.1
    hpicfUsrAuthWebAuthClientReauthenticateInterfaceIndex OBJECT-TYPE
         SYNTAX     InterfaceIndex
         MAX-ACCESS not-accessible
         STATUS     current
         DESCRIPTION
            "Index of WebAuth client interfaces."
         ::= { hpicfUsrAuthWebAuthClientReauthenticateEntry 1 }

    -- 1.3.6.1.4.1.11.2.14.11.5.1.19.3.2.1.2
   hpicfUsrAuthWebAuthClientReauthenticateMacAddress OBJECT-TYPE
         SYNTAX      MacAddress
         MAX-ACCESS  not-accessible
         STATUS      current
         DESCRIPTION
            "Specifies the MAC address of the client."
         ::= { hpicfUsrAuthWebAuthClientReauthenticateEntry 2 }

    -- 1.3.6.1.4.1.11.2.14.11.5.1.19.3.2.1.3
   hpicfUsrAuthWebAuthClientReauthenticate  OBJECT-TYPE
         SYNTAX      TruthValue
         MAX-ACCESS  read-write
         STATUS      current
         DESCRIPTION
            "The reauthentication control for this client on this
             authentication interface. Setting this attribute TRUE
             forces this authenticated WebAuth client to
             re-authenticate. That is, the client is deauthenticated
             and must transmit traffic in order to trigger
             reauthentication. Setting this attribute FALSE has no
             effect."
         ::= { hpicfUsrAuthWebAuthClientReauthenticateEntry 3 }
    
-- 
-- 
    -- 1.3.6.1.4.1.11.2.14.11.5.1.19.4
    hpicfUsrAuthMacAuthConfig OBJECT IDENTIFIER ::= { hpicfUsrAuthMIB 4 }

    
    -- 1.3.6.1.4.1.11.2.14.11.5.1.19.4.1
    hpicfUsrAuthMacAuthConfigTable OBJECT-TYPE
        SYNTAX SEQUENCE OF HpicfUsrAuthMacAuthConfigEntry
        MAX-ACCESS not-accessible
        STATUS current
        DESCRIPTION
            "A table that contains the configuration objects for 
            Mac-based Authentication associated with each port. An entry
            appears in this table for each port that may authenticate
            access to itself."
        ::= { hpicfUsrAuthMacAuthConfig 1 }

    
    -- 1.3.6.1.4.1.11.2.14.11.5.1.19.4.1.1
    hpicfUsrAuthMacAuthConfigEntry OBJECT-TYPE
        SYNTAX HpicfUsrAuthMacAuthConfigEntry
        MAX-ACCESS not-accessible
        STATUS current
        DESCRIPTION
            "The configuration information for Mac-based authentication."
        INDEX { hpicfUsrAuthPortNumber }
        ::= { hpicfUsrAuthMacAuthConfigTable 1 }

    
    HpicfUsrAuthMacAuthConfigEntry ::=
        SEQUENCE { 
            hpicfUsrAuthMacAuthClientLimit
                Integer32,
            hpicfUsrAuthMacAuthClientMoves
                INTEGER,
            hpicfUsrAuthMacAuthQuietPeriod
                Integer32,
            hpicfUsrAuthMacAuthServerTimeout
                Integer32,
            hpicfUsrAuthMacAuthServerMaxReq
                Integer32,
            hpicfUsrAuthMacAuthLogoffPeriod
                Integer32,
            hpicfUsrAuthMacAuthReAuthPeriod
                Integer32,
            hpicfUsrAuthMacAuthAuthVid
                VlanIndex,
            hpicfUsrAuthMacAuthUnauthVid
                VlanIndex,
            hpicfUsrAuthMacAuthUnAuthPeriod
                Integer32,
            hpicfUsrAuthMacAuthCachedReauthPeriod
                Unsigned32,
            hpicfUsrAuthMacAuthUnAuthPeriod
                Integer32
         }

    -- 1.3.6.1.4.1.11.2.14.11.5.1.19.4.1.1.1
    hpicfUsrAuthMacAuthClientLimit OBJECT-TYPE
        SYNTAX Integer32 (1..256)
        MAX-ACCESS read-write
        STATUS current
        DESCRIPTION
            "The maximum number of authenticated clients to allow on 
            the port."
        DEFVAL { 1 }
        ::= { hpicfUsrAuthMacAuthConfigEntry 1 }

    
    -- 1.3.6.1.4.1.11.2.14.11.5.1.19.4.1.1.2
    hpicfUsrAuthMacAuthClientMoves OBJECT-TYPE
        SYNTAX INTEGER
            {
            disabled(1),
            enabled(2)
            }
        MAX-ACCESS read-write
        STATUS current
        DESCRIPTION
            "Specifies whether client may roam across ports under
            web authentication control. Setting this attribute 
            'enabled'allows authenticated clients to roam to other 
            ports under web authentication control (that also have 
            this attribute set to 'enabled') without requiring a 
            re-authentication.  
            
            Setting this attribute 'disabled' disallows authenticated
            clients from roaming to other ports (regardless of that 
            port's attribute value).  The client has to re-
            authenticate, if it attempts to roam."
        DEFVAL { 1 }
        ::= { hpicfUsrAuthMacAuthConfigEntry 2 }

    
    -- 1.3.6.1.4.1.11.2.14.11.5.1.19.4.1.1.3
    hpicfUsrAuthMacAuthQuietPeriod OBJECT-TYPE
        SYNTAX Integer32 (1..65535)
        MAX-ACCESS read-write
        STATUS current
        DESCRIPTION
            "Specifies the time, in seconds, that the switch should 
            refrain from re-attempting an authentication request for
            a client whose credentials were rejected."
        DEFVAL { 60 }
        ::= { hpicfUsrAuthMacAuthConfigEntry 3 }

    
    -- 1.3.6.1.4.1.11.2.14.11.5.1.19.4.1.1.4
    hpicfUsrAuthMacAuthServerTimeout OBJECT-TYPE
        SYNTAX Integer32 (1..300)
        MAX-ACCESS read-write
        STATUS current
        DESCRIPTION
            "Specifies the time, in seconds, that the switch should 
            wait for an authentication reply to return before 
            considering it as timed out."
        DEFVAL { 30 }
        ::= { hpicfUsrAuthMacAuthConfigEntry 4 }

    
    -- 1.3.6.1.4.1.11.2.14.11.5.1.19.4.1.1.5
    hpicfUsrAuthMacAuthServerMaxReq OBJECT-TYPE
        SYNTAX Integer32 (1..10)
        MAX-ACCESS read-write
        STATUS current
        DESCRIPTION
            "Specifies the number of authentication requests that 
            must time out before failing authentication."
        DEFVAL { 3 }
        ::= { hpicfUsrAuthMacAuthConfigEntry 5 }

    
    -- 1.3.6.1.4.1.11.2.14.11.5.1.19.4.1.1.6
    hpicfUsrAuthMacAuthLogoffPeriod OBJECT-TYPE
        SYNTAX Integer32 (1..999999999)
        MAX-ACCESS read-write
        STATUS current
        DESCRIPTION
            "Specifies the period, in seconds, at which an 
            authenticated client will be considered unauthenticated
            for a lack of activity (i.e. traffic originating 
            from client)."
        DEFVAL { 300 }
        ::= { hpicfUsrAuthMacAuthConfigEntry 6 }

    
    -- 1.3.6.1.4.1.11.2.14.11.5.1.19.4.1.1.7
    hpicfUsrAuthMacAuthReAuthPeriod OBJECT-TYPE
        SYNTAX Integer32 (0..999999999)
        MAX-ACCESS read-write
        STATUS current
        DESCRIPTION
            "Specifies the period, in seconds, at which an 
            authenticated client must re-authenticate. A value of 
            0 signifies that an authenticated client will never have 
            to re-authenticate."
        DEFVAL { 0 }
        ::= { hpicfUsrAuthMacAuthConfigEntry 7 }

    
    -- 1.3.6.1.4.1.11.2.14.11.5.1.19.4.1.1.8
    hpicfUsrAuthMacAuthAuthVid OBJECT-TYPE
        SYNTAX VlanIndex
        MAX-ACCESS read-write
        STATUS current
        DESCRIPTION
            "Specifies the port VID (PVID) that should be used for 
            an authenticated client."
        ::= { hpicfUsrAuthMacAuthConfigEntry 8 }

    
    -- 1.3.6.1.4.1.11.2.14.11.5.1.19.4.1.1.9
    hpicfUsrAuthMacAuthUnauthVid OBJECT-TYPE
        SYNTAX VlanIndex
        MAX-ACCESS read-write
        STATUS current
        DESCRIPTION
            "Specifies the port VID (PVID) that should be used for 
            an unauthenticated client."
        ::= { hpicfUsrAuthMacAuthConfigEntry 9 }

    -- 1.3.6.1.4.1.11.2.14.11.5.1.19.4.1.1.10
    hpicfUsrAuthMacAuthCachedReauthPeriod OBJECT-TYPE
         SYNTAX Unsigned32 (0..2147483647)
         UNITS "seconds"
         MAX-ACCESS read-write
         STATUS current
         DESCRIPTION
            "The value indicates the period in seconds, during which
             cached re-authentication is allowed on the port.If value 
             is zero then the period of cached re-authentication is
             unlimited."
         DEFVAL { 0 } 
         ::= { hpicfUsrAuthMacAuthConfigEntry 10 }               

     hpicfUsrAuthMacAuthUnAuthPeriod OBJECT-TYPE
         SYNTAX Integer32 (0..65535)
         UNITS "seconds"
         MAX-ACCESS read-write
         STATUS current
         DESCRIPTION
             "Specifies the period, in seconds, at which an
             authenticated client must re-authenticate. A value of
             0 signifies that an authenticated client will never have
             to re-authenticate."
         DEFVAL { 0 }
         ::= { hpicfUsrAuthMacAuthConfigEntry 11 }

        -- 1.3.6.1.4.1.11.2.14.11.5.1.19.4.2
    hpicfUsrAuthMacAuthClientReauthenticateTable OBJECT-TYPE
         SYNTAX     SEQUENCE OF HpicfUsrAuthMacAuthClientReauthenticateEntry 
         MAX-ACCESS not-accessible
         STATUS     current
         DESCRIPTION
            "A table containing macAuth configuration/control variables
             indexed by port and client MAC." 
        ::= { hpicfUsrAuthMacAuthConfig 2 }

    hpicfUsrAuthMacAuthClientReauthenticateEntry OBJECT-TYPE
         SYNTAX     HpicfUsrAuthMacAuthClientReauthenticateEntry 
         MAX-ACCESS not-accessible
         STATUS     current
         DESCRIPTION
            "The table entry provides the means by which a macAuth 
             client on an authentication interface can be forced to 
             reauthenticate."
        INDEX { hpicfUsrAuthMacAuthClientReauthenticateInterfaceIndex, 
                hpicfUsrAuthMacAuthClientReauthenticateMacAddress}
        ::= { hpicfUsrAuthMacAuthClientReauthenticateTable 1 }

    HpicfUsrAuthMacAuthClientReauthenticateEntry ::= SEQUENCE {
         hpicfUsrAuthMacAuthClientReauthenticateInterfaceIndex
             InterfaceIndex,
         hpicfUsrAuthMacAuthClientReauthenticateMacAddress
              MacAddress,
         hpicfUsrAuthMacAuthClientReauthenticate
              TruthValue 
    }

    hpicfUsrAuthMacAuthClientReauthenticateInterfaceIndex OBJECT-TYPE
         SYNTAX     InterfaceIndex 
         MAX-ACCESS not-accessible
         STATUS     current
         DESCRIPTION
            "Index of macAuth client interfaces."
         ::= { hpicfUsrAuthMacAuthClientReauthenticateEntry 1 }

   hpicfUsrAuthMacAuthClientReauthenticateMacAddress OBJECT-TYPE 
         SYNTAX      MacAddress
         MAX-ACCESS  not-accessible 
         STATUS      current
         DESCRIPTION
            "Specifies the MAC address of the client."
         ::= { hpicfUsrAuthMacAuthClientReauthenticateEntry 2 }

   hpicfUsrAuthMacAuthClientReauthenticate  OBJECT-TYPE
         SYNTAX      TruthValue 
         MAX-ACCESS  read-write 
         STATUS      current
         DESCRIPTION
            "The reauthentication control for this client on this 
             authentication interface. Setting this attribute TRUE 
             forces this authenticated macAuth client to 
             re-authenticate. That is, the client is deauthenticated 
             and must transmit traffic in order to trigger 
             reauthentication. Setting this attribute FALSE has no 
             effect." 
         ::= { hpicfUsrAuthMacAuthClientReauthenticateEntry 3 }

    -- 1.3.6.1.4.1.11.2.14.11.5.1.19.5
    hpicfUsrAuthWebAuthStats OBJECT IDENTIFIER ::= { hpicfUsrAuthMIB 5 }

    
    -- 1.3.6.1.4.1.11.2.14.11.5.1.19.5.1
    hpicfUsrAuthWebAuthSessionStatsTable OBJECT-TYPE
        SYNTAX SEQUENCE OF HpicfUsrAuthWebAuthSessionStatsEntry
        MAX-ACCESS not-accessible
        STATUS current
        DESCRIPTION
            "A table that contains session statistic objects
            for each client (i.e. user) attempting to 
            authenticate to a port with Web-authentication 
            enabled. An entry appears in this table for each 
            port in the switch."
        ::= { hpicfUsrAuthWebAuthStats 1 }

    
    -- 1.3.6.1.4.1.11.2.14.11.5.1.19.5.1.1
    hpicfUsrAuthWebAuthSessionStatsEntry OBJECT-TYPE
        SYNTAX HpicfUsrAuthWebAuthSessionStatsEntry
        MAX-ACCESS not-accessible
        STATUS current
        DESCRIPTION
            "The session statistics information for a port with
            Web-based authentication enabled. This shows
            the current values being collected for active sessions."
        INDEX { hpicfUsrAuthPortNumber, hpicfUsrAuthWebAuthSessionMacAddr }
        ::= { hpicfUsrAuthWebAuthSessionStatsTable 1 }

    
    HpicfUsrAuthWebAuthSessionStatsEntry ::=
        SEQUENCE { 
            hpicfUsrAuthWebAuthSessionMacAddr
                MacAddress,
            hpicfUsrAuthWebAuthSessionName
                SnmpAdminString,
            hpicfUsrAuthWebAuthSessionState
                INTEGER,
            hpicfUsrAuthWebAuthSessionStateTime
                Unsigned32,
            hpicfUsrAuthWebAuthSessionAuthVid
                VlanIndex,
            hpicfUsrAuthWebAuthSessionUnauthVid
                VlanIndex,
            hpicfUsrAuthWebAuthSessionTimeout
                Unsigned32
         }

    -- 1.3.6.1.4.1.11.2.14.11.5.1.19.5.1.1.1
    hpicfUsrAuthWebAuthSessionMacAddr OBJECT-TYPE
        SYNTAX MacAddress
        MAX-ACCESS read-only
        STATUS current
        DESCRIPTION
            "Specifies the MAC address of the client."
        ::= { hpicfUsrAuthWebAuthSessionStatsEntry 1 }

    
    -- 1.3.6.1.4.1.11.2.14.11.5.1.19.5.1.1.2
    hpicfUsrAuthWebAuthSessionName OBJECT-TYPE
        SYNTAX SnmpAdminString
        MAX-ACCESS read-only
        STATUS current
        DESCRIPTION
            "Specifies the username of the client."
        ::= { hpicfUsrAuthWebAuthSessionStatsEntry 2 }

    
    -- 1.3.6.1.4.1.11.2.14.11.5.1.19.5.1.1.3
    hpicfUsrAuthWebAuthSessionState OBJECT-TYPE
        SYNTAX INTEGER
            {
            authenticated(1),
            unauthenticated(2),
            authenticating(3),
            authReqRejectNoVlan(4),
            authReqRejectUnauthVlan(5),
            authReqTimeoutNoVlan(6),
            authReqTimeoutUnauthVlan(7)
            }
        MAX-ACCESS read-only
        STATUS current
        DESCRIPTION
            "Specifies the state of the client as follows:
            'authenticated'            - authenticated client
            'unauthenticated'          - unauthenticated client,  
                                         waiting for credentials
            'authenticating'           - credentials have been sent
                                         for verification, waiting for
                                         response
            'authReqRejectNoVlan'      - credentials invalid; client
                                         does not have access to 
                                         unauthenticated VLAN
            'authReqRejectUnauthVlan   - credentials invalid; client
                                         does have access to 
                                         unauthenticated VLAN
            'authReqTimeoutNoVlan'     - credentials could not be 
                                         verified; client is still 
                                         unauthenticated and does 
                                         not have access to 
                                         unauthenticated VLAN
            'authReqTimeoutUnauthVlan' - credentials could not be 
                                         verified; client is still 
                                         unauthenticated, but has 
                                         access to unauthenticated
                                         VLAN"
        ::= { hpicfUsrAuthWebAuthSessionStatsEntry 3 }

    
    -- 1.3.6.1.4.1.11.2.14.11.5.1.19.5.1.1.4
    hpicfUsrAuthWebAuthSessionStateTime OBJECT-TYPE
        SYNTAX Unsigned32
        MAX-ACCESS read-only
        STATUS current
        DESCRIPTION
            "The duration, in seconds, a client has spent in the
            state specified by hpicfUsrAuthSessionState."
        ::= { hpicfUsrAuthWebAuthSessionStatsEntry 4 }

    
    -- 1.3.6.1.4.1.11.2.14.11.5.1.19.5.1.1.5
    hpicfUsrAuthWebAuthSessionAuthVid OBJECT-TYPE
        SYNTAX VlanIndex
        MAX-ACCESS read-only
        STATUS current
        DESCRIPTION
            "Specifies the PVID that the authenticated client is
            utilizing. If client is unauthenticated, this object 
            has no meaning."
        ::= { hpicfUsrAuthWebAuthSessionStatsEntry 5 }

    
    -- 1.3.6.1.4.1.11.2.14.11.5.1.19.5.1.1.6
    hpicfUsrAuthWebAuthSessionUnauthVid OBJECT-TYPE
        SYNTAX VlanIndex
        MAX-ACCESS read-only
        STATUS current
        DESCRIPTION
            "Specifies the PVID that the unauthenticated client is
            utilizing. If client is authenticated, this object 
            has no meaning."
        ::= { hpicfUsrAuthWebAuthSessionStatsEntry 6 }

    -- 1.3.6.1.4.1.11.2.14.11.5.1.19.5.1.1.7
    hpicfUsrAuthWebAuthSessionTimeout OBJECT-TYPE
        SYNTAX Unsigned32 (0..4294967295)
        UNITS "seconds"
        MAX-ACCESS read-only
        STATUS current
        DESCRIPTION
            "Specifies the RADIUS Server set session timeout for
             reauthentication of the user. When ST = 0, user gets
             reauthenticated at reauth-period secs, ST < 60 it is
             set to 60 secs and then user is reauthenticated, ST > 60
             user is reauthenticated at ST secs."
        DEFVAL { 0 }
        ::= { hpicfUsrAuthWebAuthSessionStatsEntry 7 }
    
    -- 1.3.6.1.4.1.11.2.14.11.5.1.19.6
    hpicfUsrAuthMacAuthStats OBJECT IDENTIFIER ::= { hpicfUsrAuthMIB 6 }

    
    -- 1.3.6.1.4.1.11.2.14.11.5.1.19.6.1
    hpicfUsrAuthMacAuthSessionStatsTable OBJECT-TYPE
        SYNTAX SEQUENCE OF HpicfUsrAuthMacAuthSessionStatsEntry
        MAX-ACCESS not-accessible
        STATUS current
        DESCRIPTION
            "A table that contains session statistic objects
            for each client (i.e. user) attempting to 
            authenticate to a port with MAC-authentication 
            enabled. An entry appears in this table for each 
            port in the switch."
        ::= { hpicfUsrAuthMacAuthStats 1 }

    
    -- 1.3.6.1.4.1.11.2.14.11.5.1.19.6.1.1
    hpicfUsrAuthMacAuthSessionStatsEntry OBJECT-TYPE
        SYNTAX HpicfUsrAuthMacAuthSessionStatsEntry
        MAX-ACCESS not-accessible
        STATUS current
        DESCRIPTION
            "The session statistics information for a port with
            Mac-based authentication enabled. This shows
            the current values being collected for active sessions."
        INDEX { hpicfUsrAuthPortNumber, hpicfUsrAuthMacAuthSessionMacAddr }
        ::= { hpicfUsrAuthMacAuthSessionStatsTable 1 }

    
    HpicfUsrAuthMacAuthSessionStatsEntry ::=
        SEQUENCE { 
            hpicfUsrAuthMacAuthSessionMacAddr
                MacAddress,
            hpicfUsrAuthMacAuthSessionState
                INTEGER,
            hpicfUsrAuthMacAuthSessionStateTime
                Unsigned32,
            hpicfUsrAuthMacAuthSessionAuthVid
                VlanIndex,
            hpicfUsrAuthMacAuthSessionUnauthVid
                VlanIndex,
            hpicfUsrAuthMacAuthSessionTimeout
                Unsigned32,
            hpicfUsrAuthMacAuthSessionUsrNumberCnt
                Counter32            
         }

    -- 1.3.6.1.4.1.11.2.14.11.5.1.19.6.1.1.1
    hpicfUsrAuthMacAuthSessionMacAddr OBJECT-TYPE
        SYNTAX MacAddress
        MAX-ACCESS read-only
        STATUS current
        DESCRIPTION
            "Specifies the MAC address of the client."
        ::= { hpicfUsrAuthMacAuthSessionStatsEntry 1 }

    
    -- 1.3.6.1.4.1.11.2.14.11.5.1.19.6.1.1.2
    hpicfUsrAuthMacAuthSessionState OBJECT-TYPE
        SYNTAX INTEGER
            {
            authenticated(1),
            unauthenticated(2),
            authenticating(3),
            authReqRejectNoVlan(4),
            authReqRejectUnauthVlan(5),
            authReqTimeoutNoVlan(6),
            authReqTimeoutUnauthVlan(7)
            }
        MAX-ACCESS read-only
        STATUS current
        DESCRIPTION
            "Specifies the state of the client as follows:
            'authenticated'            - authenticated client
            'unauthenticated'          - unauthenticated client,  
                                         waiting for credentials
            'authenticating'           - credentials have been sent
                                         for verification, waiting for
                                         response
            'authReqRejectNoVlan'      - credentials invalid; client
                                         does not have access to 
                                         unauthenticated VLAN
            'authReqRejectUnauthVlan   - credentials invalid; client
                                         does have access to 
                                         unauthenticated VLAN
            'authReqTimeoutNoVlan'     - credentials could not be 
                                         verified; client is still 
                                         unauthenticated and does 
                                         not have access to 
                                         unauthenticated VLAN
            'authReqTimeoutUnauthVlan' - credentials could not be 
                                         verified; client is still 
                                         unauthenticated, but has 
                                         access to unauthenticated
                                         VLAN"
        ::= { hpicfUsrAuthMacAuthSessionStatsEntry 2 }

    
    -- 1.3.6.1.4.1.11.2.14.11.5.1.19.6.1.1.3
    hpicfUsrAuthMacAuthSessionStateTime OBJECT-TYPE
        SYNTAX Unsigned32
        MAX-ACCESS read-only
        STATUS current
        DESCRIPTION
            "The duration, in seconds, a client has spent in the
            state specified by hpicfUsrAuthSessionState."
        ::= { hpicfUsrAuthMacAuthSessionStatsEntry 3 }

    
    -- 1.3.6.1.4.1.11.2.14.11.5.1.19.6.1.1.4
    hpicfUsrAuthMacAuthSessionAuthVid OBJECT-TYPE
        SYNTAX VlanIndex
        MAX-ACCESS read-only
        STATUS current
        DESCRIPTION
            "Specifies the PVID that the authenticated client is
            utilizing. If client is unauthenticated, this object 
            has no meaning."
        ::= { hpicfUsrAuthMacAuthSessionStatsEntry 4 }

    
    -- 1.3.6.1.4.1.11.2.14.11.5.1.19.6.1.1.5
    hpicfUsrAuthMacAuthSessionUnauthVid OBJECT-TYPE
        SYNTAX VlanIndex
        MAX-ACCESS read-only
        STATUS current
        DESCRIPTION
            "Specifies the PVID that the unauthenticated client is
            utilizing. If client is authenticated, this object 
            has no meaning."
        ::= { hpicfUsrAuthMacAuthSessionStatsEntry 5 }

    -- 1.3.6.1.4.1.11.2.14.11.5.1.19.6.1.1.6
    hpicfUsrAuthMacAuthSessionTimeout OBJECT-TYPE
        SYNTAX Unsigned32 (0..4294967295)
        UNITS "seconds"
        MAX-ACCESS read-only
        STATUS current
        DESCRIPTION
            "Specifies the RADIUS Server set session timeout for
             reauthentication of the user. When ST = 0, user gets
             reauthenticated at reauth-period secs, ST < 60 it is
             set to 60 secs and then user is reauthenticated, ST > 60
             user is reauthenticated at ST secs."
        DEFVAL { 0 }
        ::= { hpicfUsrAuthMacAuthSessionStatsEntry 6 }

    -- 1.3.6.1.4.1.11.2.14.11.5.1.19.6.1.1.8
    hpicfUsrAuthMacAuthSessionUsrNumberCnt OBJECT-TYPE
        SYNTAX Counter32
        MAX-ACCESS read-only
        STATUS current
        DESCRIPTION
            "This object Specifies the number of authenticated client 
             currently present on this port. This does not include the 
             clients which are under process of authentication."
        DEFVAL { 0 }
        ::= { hpicfUsrAuthMacAuthSessionStatsEntry 7 }

-- ------------------------------------------------------------
-- User Last Login
-- ------------------------------------------------------------

    hpicfUsrAuthLastLogin
        OBJECT IDENTIFIER ::= { hpicfUsrAuthMIB 12 }

    hpicfUsrAuthLastLoginCurrentGeneration OBJECT-TYPE
        SYNTAX      Unsigned32
        MAX-ACCESS  read-only
        STATUS      current
        DESCRIPTION "The current generation number of the rows in
                     hpicfUsrAuthLastLoginTable. To obtain a consistent
                     table view, first read this object, then enumerate
                     the table (reading hpicfUsrAuthLastLoginGeneration
                     last), discarding any rows with
                     hpicfUsrAuthLastLoginGeneration greater than this
                     value."
        ::= { hpicfUsrAuthLastLogin 1 }

    hpicfUsrAuthLastLoginTable OBJECT-TYPE
        SYNTAX      SEQUENCE OF HpicfUsrAuthLastLoginEntry
        MAX-ACCESS  not-accessible
        STATUS      current
        DESCRIPTION "This table records, per-username, the most recent
                     login and login attempts. A record is created by
                     the switch upon the first successful login to a
                     username, and updated upon each subsequent login
                     or login attempt."
        ::= { hpicfUsrAuthLastLogin 2 }

-- ------------------------------------------------------------
-- User Last Login table entry
-- ------------------------------------------------------------

    hpicfUsrAuthLastLoginEntry OBJECT-TYPE
        SYNTAX      HpicfUsrAuthLastLoginEntry
        MAX-ACCESS  not-accessible
        STATUS      current
        DESCRIPTION "User last login table entry."
        INDEX { hpicfUsrAuthLastLoginIndex }
        ::= { hpicfUsrAuthLastLoginTable 1 }

    HpicfUsrAuthLastLoginEntry ::=
        SEQUENCE {
            hpicfUsrAuthLastLoginIndex                  Unsigned32,
            hpicfUsrAuthLastLoginName                   DisplayString,
            hpicfUsrAuthLastLoginPrivilege              INTEGER,
            hpicfUsrAuthLastLoginSuccTime               DateAndTime,
            hpicfUsrAuthLastLoginSuccAddrType           InetAddressType,
            hpicfUsrAuthLastLoginSuccAddr               InetAddress,
            hpicfUsrAuthLastLoginUnsuccTime             DateAndTime,
            hpicfUsrAuthLastLoginUnsuccCount            Counter32,
            hpicfUsrAuthLastLoginGeneration             Unsigned32
        }

    hpicfUsrAuthLastLoginIndex OBJECT-TYPE
        SYNTAX      Unsigned32 (1..64511)
        MAX-ACCESS  not-accessible
        STATUS      current
        DESCRIPTION "The index value which uniquely identifies a row in
                     the user last-login table."
        ::= { hpicfUsrAuthLastLoginEntry 1 }

    hpicfUsrAuthLastLoginName OBJECT-TYPE
        SYNTAX      DisplayString (SIZE(1..64))
        MAX-ACCESS  read-only
        STATUS      current
        DESCRIPTION "The user's login name."
        ::= { hpicfUsrAuthLastLoginEntry 2 }

    hpicfUsrAuthLastLoginPrivilege OBJECT-TYPE
        SYNTAX      INTEGER {
                        operator(1),
                        manager(2),
                        superuser(3)
                    }
        MAX-ACCESS  read-only
        STATUS      current
        DESCRIPTION "The privilege level assigned to the user at the most
                     recent login."
        ::= { hpicfUsrAuthLastLoginEntry 3 }

    hpicfUsrAuthLastLoginSuccTime OBJECT-TYPE
        SYNTAX      DateAndTime
        MAX-ACCESS  read-only
        STATUS      current
        DESCRIPTION "The time of the user's most recent successful login."
        ::= { hpicfUsrAuthLastLoginEntry 4 }

    hpicfUsrAuthLastLoginSuccAddrType OBJECT-TYPE
        SYNTAX      InetAddressType
        MAX-ACCESS  read-only
        STATUS      current
        DESCRIPTION "The type of IP address from which the user's most recent
                     successful login occurred. Unknown(0) indicates a console
                     login."
        ::= { hpicfUsrAuthLastLoginEntry 5 }

    hpicfUsrAuthLastLoginSuccAddr OBJECT-TYPE
        SYNTAX      InetAddress
        MAX-ACCESS  read-only
        STATUS      current
        DESCRIPTION "The IP address from which the user's most recent
                     successful login occurred."
        ::= { hpicfUsrAuthLastLoginEntry 6 }

    hpicfUsrAuthLastLoginUnsuccTime OBJECT-TYPE
        SYNTAX      DateAndTime
        MAX-ACCESS  read-only
        STATUS      current
        DESCRIPTION "The time of the user's most recent unsuccessful
                     login attempt. This will be zero length if there
                     have been no unsuccessful login attempts since the
                     most recent successful login."
        ::= { hpicfUsrAuthLastLoginEntry 7 }

    hpicfUsrAuthLastLoginUnsuccCount OBJECT-TYPE
        SYNTAX      Counter32
        MAX-ACCESS  read-only
        STATUS      current
        DESCRIPTION "The count of the user's unsuccessful login attempts since
                     the most recent successful login. This counter is reset to
                     zero whenever hpicfUsrAuthLastLoginSuccTime changes."
        ::= { hpicfUsrAuthLastLoginEntry 8 }

    hpicfUsrAuthLastLoginGeneration OBJECT-TYPE
        SYNTAX      Unsigned32
        MAX-ACCESS  read-only
        STATUS      current
        DESCRIPTION "The generation number of the objects in this row.
                     This object should be tested after reading other
                     objects in a row to ensure it has not changed from
                     hpicfUsrAuthLastLoginCurrentGeneration, or from
                     the value of hpicfUsrAuthLastLoginGeneration sent
                     in an hpicfUsrAuthCLIAuthFail notification."
        ::= { hpicfUsrAuthLastLoginEntry 9 }
--

    hpicfUsrAuthLastLoginDeleteAll OBJECT-TYPE
        SYNTAX      TruthValue
        MAX-ACCESS  read-write
        STATUS      current
        DESCRIPTION "When set to true(1), all rows of the last-login table
                     are deleted. Always reads as false(2)."
        DEFVAL { false }
        ::= { hpicfUsrAuthLastLogin 3 }

-- ------------------------------------------------------------
-- Conformance
-- ------------------------------------------------------------

    -- 1.3.6.1.4.1.11.2.14.11.5.1.19.7
    hpicfUsrAuthConformance OBJECT IDENTIFIER ::= { hpicfUsrAuthMIB 7 }

    
    -- 1.3.6.1.4.1.11.2.14.11.5.1.19.7.2
    hpicfUsrAuthGroups OBJECT IDENTIFIER ::= { hpicfUsrAuthConformance 2 }

    
    -- 1.3.6.1.4.1.11.2.14.11.5.1.19.7.2.1
    hpicfUsrAuthSystemGroup OBJECT-GROUP
        OBJECTS { hpicfUsrAuthWebAuthDhcpBaseAddress, 
            hpicfUsrAuthWebAuthDhcpMask, 
            hpicfUsrAuthWebAuthDhcpLease, 
            hpicfUsrAuthMacAuthAddrFormat, 
            hpicfUsrAuthCLIPasswdSet, 
            hpicfUsrAuthCLIInterface,
            hpicfUsrAuthCacheCredTimeOut }
        STATUS current
        DESCRIPTION 
            "A collection of objects providing system 
            information about, and control over, Web- and 
            MAC-based authentication."
        ::= { hpicfUsrAuthGroups 1 }

    
    -- 1.3.6.1.4.1.11.2.14.11.5.1.19.7.2.2
    hpicfUsrAuthPortsGroup OBJECT-GROUP
        OBJECTS { hpicfUsrAuthPortNumber, 
            hpicfUsrAuthWebAuthAdminStatus, 
            hpicfUsrAuthMacAuthAdminStatus, 
            hpicfUsrAuthPortReauthenticate }
        STATUS deprecated
        DESCRIPTION 
            "A collection of objects providing system level
            information about Web and MAC based authentication
            for each port in the switch."
        ::= { hpicfUsrAuthGroups 2 }

    
    -- 1.3.6.1.4.1.11.2.14.11.5.1.19.7.2.3
    hpicfUsrAuthWebAuthConfigGroup OBJECT-GROUP
        OBJECTS { hpicfUsrAuthWebAuthClientLimit, 
            hpicfUsrAuthWebAuthClientMoves, 
            hpicfUsrAuthWebAuthSSLState, 
            hpicfUsrAuthWebAuthRedirectUrl, 
            hpicfUsrAuthWebAuthQuietPeriod, 
            hpicfUsrAuthWebAuthServerTimeout, 
            hpicfUsrAuthWebAuthServerMaxReq, 
            hpicfUsrAuthWebAuthMaxRetries, 
            hpicfUsrAuthWebAuthLogoffPeriod, 
            hpicfUsrAuthWebAuthReAuthPeriod, 
            hpicfUsrAuthWebAuthAuthVid, 
            hpicfUsrAuthWebAuthUnauthVid,
            hpicfUsrAuthWebAuthCacheCredentials }
        STATUS current
        DESCRIPTION 
            "A collection of objects providing configuration
            objects for Web-based authentication associated with 
            each port."
        ::= { hpicfUsrAuthGroups 3 }

    
    -- 1.3.6.1.4.1.11.2.14.11.5.1.19.7.2.4
    hpicfUsrAuthMacAuthConfigGroup OBJECT-GROUP
        OBJECTS { hpicfUsrAuthMacAuthClientLimit, 
            hpicfUsrAuthMacAuthClientMoves, 
            hpicfUsrAuthMacAuthQuietPeriod, 
            hpicfUsrAuthMacAuthServerTimeout, 
            hpicfUsrAuthMacAuthServerMaxReq, 
            hpicfUsrAuthMacAuthLogoffPeriod, 
            hpicfUsrAuthMacAuthReAuthPeriod, 
            hpicfUsrAuthMacAuthAuthVid, 
            hpicfUsrAuthMacAuthUnauthVid }
        STATUS current
        DESCRIPTION 
            "A collection of objects providing configuration
            objects for MAC-based authentication associated with 
            each port."
        ::= { hpicfUsrAuthGroups 4 }

    
    -- 1.3.6.1.4.1.11.2.14.11.5.1.19.7.2.5
    hpicfUsrAuthWebAuthSessionStatsGroup OBJECT-GROUP
        OBJECTS { hpicfUsrAuthWebAuthSessionMacAddr, 
            hpicfUsrAuthWebAuthSessionName, 
            hpicfUsrAuthWebAuthSessionState, 
            hpicfUsrAuthWebAuthSessionStateTime, 
            hpicfUsrAuthWebAuthSessionAuthVid, 
            hpicfUsrAuthWebAuthSessionUnauthVid }
        STATUS current
        DESCRIPTION 
            "A collection of objects providing statistics about 
            current sessions for Web-based authentication."
        ::= { hpicfUsrAuthGroups 5 }

    
    -- 1.3.6.1.4.1.11.2.14.11.5.1.19.7.2.6
    hpicfUsrAuthMacAuthSessionStatsGroup OBJECT-GROUP
        OBJECTS { hpicfUsrAuthMacAuthSessionMacAddr, 
            hpicfUsrAuthMacAuthSessionState, 
            hpicfUsrAuthMacAuthSessionStateTime, 
            hpicfUsrAuthMacAuthSessionAuthVid, 
            hpicfUsrAuthMacAuthSessionUnauthVid
             }
        STATUS current
        DESCRIPTION 
            "A collection of objects providing statistics about 
            current sessions for MAC-based authentication."
        ::= { hpicfUsrAuthGroups 6 }

    -- 1.3.6.1.4.1.11.2.14.11.5.1.19.7.2.7
    hpicfUsrAuthWebAuthConfigGroup1 OBJECT-GROUP
        OBJECTS { hpicfUsrAuthWebAuthClientLimit, 
            hpicfUsrAuthWebAuthClientMoves, 
            hpicfUsrAuthWebAuthSSLState, 
            hpicfUsrAuthWebAuthRedirectUrl, 
            hpicfUsrAuthWebAuthQuietPeriod, 
            hpicfUsrAuthWebAuthServerTimeout, 
            hpicfUsrAuthWebAuthServerMaxReq, 
            hpicfUsrAuthWebAuthMaxRetries, 
            hpicfUsrAuthWebAuthLogoffPeriod, 
            hpicfUsrAuthWebAuthReAuthPeriod, 
            hpicfUsrAuthWebAuthAuthVid, 
            hpicfUsrAuthWebAuthUnauthVid,
            hpicfUsrAuthWebAuthCacheCredentials,
            hpicfUsrAuthWebAuthCachedReauthPeriod }
        STATUS current
        DESCRIPTION 
            "A collection of objects providing configuration
            objects for Web-based authentication associated with 
            each port."
        ::= { hpicfUsrAuthGroups 7 }

    
    -- 1.3.6.1.4.1.11.2.14.11.5.1.19.7.2.8
    hpicfUsrAuthMacAuthConfigGroup1 OBJECT-GROUP
        OBJECTS { hpicfUsrAuthMacAuthClientLimit, 
            hpicfUsrAuthMacAuthClientMoves, 
            hpicfUsrAuthMacAuthQuietPeriod, 
            hpicfUsrAuthMacAuthServerTimeout, 
            hpicfUsrAuthMacAuthServerMaxReq, 
            hpicfUsrAuthMacAuthLogoffPeriod, 
            hpicfUsrAuthMacAuthReAuthPeriod, 
            hpicfUsrAuthMacAuthAuthVid, 
            hpicfUsrAuthMacAuthUnauthVid,
            hpicfUsrAuthMacAuthCachedReauthPeriod } 
        STATUS current
        DESCRIPTION 
            "A collection of objects providing configuration
            objects for MAC-based authentication associated with 
            each port."
        ::= { hpicfUsrAuthGroups 8 }

     hpicfUsrAuthMacAuthConfigGroup2 OBJECT-GROUP
         OBJECTS { hpicfUsrAuthMacAuthClientLimit,
             hpicfUsrAuthMacAuthClientMoves,
             hpicfUsrAuthMacAuthQuietPeriod,
             hpicfUsrAuthMacAuthServerTimeout,
             hpicfUsrAuthMacAuthServerMaxReq,
             hpicfUsrAuthMacAuthLogoffPeriod,
             hpicfUsrAuthMacAuthReAuthPeriod,
             hpicfUsrAuthMacAuthAuthVid,
             hpicfUsrAuthMacAuthUnauthVid,
             hpicfUsrAuthMacAuthUnAuthPeriod,
             hpicfUsrAuthMacAuthCachedReauthPeriod }
         STATUS current
         DESCRIPTION
             "A collection of objects providing configuration
             objects for MAC-based authentication associated with
             each port."
         ::= { hpicfUsrAuthGroups 9 }

    hpicfUsrAuthRedirectServerGroup OBJECT-GROUP
         OBJECTS { hpicfUsrAuthRedirectServerURL,
             hpicfUsrAuthRedirectServerRestrictiveFilter ,
             hpicfUsrAuthRedirectServerClientTimeout,
             hpicfUsrAuthRedirectServerAuthFailureStats,
             hpicfUsrAuthRedirectServerRowStatus }
         STATUS current
         DESCRIPTION
             "A collection of objects for authentication 
             Redirect Server."
         ::= { hpicfUsrAuthGroups 10 }
     
    hpicfUsrAuthWMAeWAServerGroup OBJECT-GROUP
         OBJECTS { hpicfUsrAuthWMAeWAServerIPAddressType,
             hpicfUsrAuthWMAeWAServerIPAddress,
             hpicfUsrAuthWMAeWAServerPath,
             hpicfUsrAUthWMAeWAServerRowStatus}
         STATUS current
         DESCRIPTION
             "A collection of objects for Enhanced 
              Web Auth servers."
         ::= { hpicfUsrAuthGroups 11 }
    
    hpicfUsrAuthClientReauthenticateGroup OBJECT-GROUP
         OBJECTS { hpicfUsrAuthClientReauthenticate,
             hpicfUsrAuthWebAuthClientReauthenticate,
             hpicfUsrAuthMacAuthClientReauthenticate}
         STATUS current
         DESCRIPTION
             "A collection of objects for Reauthentication 
             settings ."
         ::= { hpicfUsrAuthGroups 12 }

    hpicfUsrAuthMacAuthSessionStatsGroup1 OBJECT-GROUP
         OBJECTS { hpicfUsrAuthMacAuthSessionTimeout }
         STATUS      current
         DESCRIPTION "A collection of objects providing RADIUS server
                      set session timeout for MAC-based user
                      reauthentication."
         ::= { hpicfUsrAuthGroups 13 }

    hpicfUsrAuthWebAuthSessionStatsGroup1 OBJECT-GROUP
         OBJECTS { hpicfUsrAuthWebAuthSessionTimeout }
         STATUS      current
         DESCRIPTION "A collection of objects providing RADIUS server
                      set session timeout for Web-based user
                      reauthentication."
         ::= { hpicfUsrAuthGroups 14 }

    hpicfUsrAuthLastLoginGroup OBJECT-GROUP
        OBJECTS   { hpicfUsrAuthLastLoginCurrentGeneration,
                    hpicfUsrAuthLastLoginDeleteAll,
                    hpicfUsrAuthLastLoginName,
                    hpicfUsrAuthLastLoginPrivilege,
                    hpicfUsrAuthLastLoginSuccTime,
                    hpicfUsrAuthLastLoginSuccAddrType,
                    hpicfUsrAuthLastLoginSuccAddr,
                    hpicfUsrAuthLastLoginUnsuccTime,
                    hpicfUsrAuthLastLoginUnsuccCount,
                    hpicfUsrAuthLastLoginGeneration
                  }
        STATUS    current
        DESCRIPTION "A collection of objects for viewing the most recent
                     logins to the switch by users, and for deleting the
                     table."
        ::= { hpicfUsrAuthGroups 15 }

      -- 1.3.6.1.4.1.11.2.14.11.5.1.19.7.2.16
    hpicfUsrAuthPortsGroup1 OBJECT-GROUP
        OBJECTS    { hpicfUsrAuthPortNumber,
            	     hpicfUsrAuthWebAuthAdminStatus,
            	     hpicfUsrAuthMacAuthAdminStatus,
            	     hpicfUsrAuthPortReauthenticate,
            	     hpicfUsrAuthLMAAdminStatus 
		    }
        STATUS current
        DESCRIPTION
            "A collection of objects providing system level
            information about Web and MAC based authentication
            for each port in the switch."
        ::= { hpicfUsrAuthGroups 16 }

   
    -- 1.3.6.1.4.1.11.2.14.11.5.1.19.7.4
    hpicfUsrAuthCompliances OBJECT IDENTIFIER ::= { hpicfUsrAuthConformance 4 }

    
    -- 1.3.6.1.4.1.11.2.14.11.5.1.19.7.4.1
    hpicfUsrAuthCompliance MODULE-COMPLIANCE
        STATUS deprecated
        DESCRIPTION 
            "********* THIS COMPLIANCE IS DEPRECATED *********
            The compliance statement for devices support of
            HP-USER-AUTH MIB."
        MODULE -- this module
            MANDATORY-GROUPS { hpicfUsrAuthSystemGroup, 
                hpicfUsrAuthPortsGroup, 
                hpicfUsrAuthWebAuthConfigGroup, 
                hpicfUsrAuthMacAuthConfigGroup, 
                hpicfUsrAuthWebAuthSessionStatsGroup, 
                hpicfUsrAuthMacAuthSessionStatsGroup }
        ::= { hpicfUsrAuthCompliances 1 }

    -- 1.3.6.1.4.1.11.2.14.11.5.1.19.7.4.2
    hpicfUsrAuthCompliance1 MODULE-COMPLIANCE
        STATUS deprecated
        DESCRIPTION 
            "The compliance statement for devices support of
            HP-USER-AUTH MIB."
        MODULE -- this module
            MANDATORY-GROUPS { hpicfUsrAuthSystemGroup, 
                hpicfUsrAuthPortsGroup, 
                hpicfUsrAuthWebAuthConfigGroup1, 
                hpicfUsrAuthMacAuthConfigGroup1, 
                hpicfUsrAuthWebAuthSessionStatsGroup, 
                hpicfUsrAuthMacAuthSessionStatsGroup }
        ::= { hpicfUsrAuthCompliances 2 }

     hpicfUsrAuthCompliance2 MODULE-COMPLIANCE
         STATUS deprecated
         DESCRIPTION
             "The compliance statement for devices support of
             HP-USER-AUTH MIB."
         MODULE -- this module
             MANDATORY-GROUPS { hpicfUsrAuthSystemGroup,
                 hpicfUsrAuthPortsGroup,
                 hpicfUsrAuthWebAuthSessionStatsGroup,
                 hpicfUsrAuthMacAuthSessionStatsGroup,
                 hpicfUsrAuthWebAuthConfigGroup1,
                 hpicfUsrAuthMacAuthConfigGroup2 }
         ::= { hpicfUsrAuthCompliances 3 }

    hpicfUsrAuthCompliance3 MODULE-COMPLIANCE
         STATUS deprecated
         DESCRIPTION
             "The compliance statement for devices support of
             HP-USER-AUTH MIB."
         MODULE -- this module
             MANDATORY-GROUPS { hpicfUsrAuthRedirectServerGroup,
                 hpicfUsrAuthWMAeWAServerGroup,
                 hpicfUsrAuthClientReauthenticateGroup }
         ::= { hpicfUsrAuthCompliances 4 }
    
    hpicfUsrAuthCompliance4 MODULE-COMPLIANCE
         STATUS deprecated
         DESCRIPTION
             "The compliance statement for devices support of
             HP-USER-AUTH MIB."
         MODULE -- this module
             MANDATORY-GROUPS { hpicfUsrAuthMacGroup,
                 hpicfNotifcationConfigDataGroup, 
                 hpicfUsrAuthNotificationGroup,
                 hpicfUsrAuthWebAuthAccessDeniedGroup}
         ::= { hpicfUsrAuthCompliances 5 }
    

    hpicfUsrAuthCompliance5 MODULE-COMPLIANCE
         STATUS deprecated
         DESCRIPTION
             "The compliance statement for devices support of
             HP-USER-AUTH MIB."
         MODULE -- this module
             MANDATORY-GROUPS { hpicfUsrAuthMacAuthSessionStatsGroup1,
                 hpicfUsrAuthWebAuthSessionStatsGroup1}
         ::= { hpicfUsrAuthCompliances 6 }

    hpicfUsrAuthCompliance6 MODULE-COMPLIANCE
         STATUS current
         DESCRIPTION
             "The compliance statement for devices support of
             HP-USER-AUTH MIB."
         MODULE -- this module
             MANDATORY-GROUPS { hpicfUsrAuthMacAuthUsrNumberGroup
                 }
         ::= { hpicfUsrAuthCompliances 7 }

    hpicfUsrAuthCompliance7 MODULE-COMPLIANCE
         STATUS deprecated
         DESCRIPTION
             "The compliance statement for device support of
              HP-USER-AUTH MIB."
         MODULE -- this module
             MANDATORY-GROUPS { hpicfUsrAuthSystemGroup,
                 hpicfUsrAuthPortsGroup,
                 hpicfUsrAuthMacAuthConfigGroup2,
                 hpicfUsrAuthMacGroup,
                 hpicfUsrAuthMacAuthSessionStatsGroup1,
                 hpicfUsrAuthWebAuthConfigGroup1,
                 hpicfUsrAuthWebAuthSessionStatsGroup1,
                 hpicfUsrAuthWebAuthAccessDeniedGroup,
                 hpicfUsrAuthClientReauthenticateGroup,
                 hpicfUsrAuthRedirectServerGroup,
                 hpicfUsrAuthWMAeWAServerGroup,
                 hpicfUsrAuthNotificationGroup1,
                 hpicfNotificationConfigDataGroup1,
                 hpicfUsrAuthLastLoginGroup }
         ::= { hpicfUsrAuthCompliances 8 }

     hpicfUsrAuthCompliance8 MODULE-COMPLIANCE
         STATUS current
         DESCRIPTION
             "The compliance statement for device support of
              HP-USER-AUTH MIB."
         MODULE -- this module
             MANDATORY-GROUPS { hpicfUsrAuthSystemGroup,
                 hpicfUsrAuthPortsGroup1,
                 hpicfUsrAuthMacAuthConfigGroup2,
                 hpicfUsrAuthMacGroup,
                 hpicfUsrAuthMacAuthSessionStatsGroup1,
                 hpicfUsrAuthWebAuthConfigGroup1,
                 hpicfUsrAuthWebAuthSessionStatsGroup1,
                 hpicfUsrAuthWebAuthAccessDeniedGroup,
                 hpicfUsrAuthClientReauthenticateGroup,
                 hpicfUsrAuthRedirectServerGroup,
                 hpicfUsrAuthWMAeWAServerGroup,
                 hpicfUsrAuthNotificationGroup1,
                 hpicfNotificationConfigDataGroup1,
                 hpicfUsrAuthLastLoginGroup }
         ::= { hpicfUsrAuthCompliances 9 }

    -- 1.3.6.1.4.1.11.2.14.11.5.1.19.8
    hpicfUsrAuthNotifyConformance OBJECT IDENTIFIER ::= { hpicfUsrAuthMIB 8 }

    
    -- 1.3.6.1.4.1.11.2.14.11.5.1.19.8.1
    hpicfUsrAuthNotificationGroup NOTIFICATION-GROUP
        NOTIFICATIONS { hpicfUsrAuthCLIAuthFail, 
            hpicfUsrAuthPasswdChng, 
            hpicfPortSecAuthFailure }
        STATUS current
        DESCRIPTION 
            "A group of authorization notifications."
        ::= { hpicfUsrAuthNotifyConformance 1 }

    
    -- 1.3.6.1.4.1.11.2.14.11.5.1.19.8.2
    hpicfNotifcationConfigDataGroup OBJECT-GROUP
        OBJECTS { hpicfUsrAuthCLIFailCnt, 
            hpicfUsrAuthCLIPwdNotifyCnt, 
            hpicfUsrAuthWMAFailCnt, 
            hpicfUsrAuthWMAFailMAC, 
            hpicfUsrAuthWMAFailPort, 
            hpicfUsrAuthWMAFailVlan, 
            hpicfUsrAuthPasswdNotifyEnable, 
            hpicfUsrAuthCliNotifyEnable, 
            hpicfUsrAuthPortSecNotifyEnable }
        STATUS deprecated
        DESCRIPTION 
            "A group of notification data and configuration objects."
        ::= { hpicfUsrAuthNotifyConformance 2 }

    -- 1.3.6.1.4.1.11.2.14.11.5.1.19.8.3
    hpicfNotificationConfigDataGroup1 OBJECT-GROUP
        OBJECTS { hpicfUsrAuthCLIFailCnt,
            hpicfUsrAuthCLIInterface,
            hpicfUsrAuthLastLoginNotifyStatus,
            hpicfUsrAuthLastLoginNotifyAddrType,
            hpicfUsrAuthLastLoginNotifyAddr,
            hpicfUsrAuthCLIPwdNotifyCnt,
            hpicfUsrAuthWMAFailCnt,
            hpicfUsrAuthWMAFailMAC,
            hpicfUsrAuthWMAFailPort,
            hpicfUsrAuthWMAFailVlan,
            hpicfUsrAuthPasswdNotifyEnable,
            hpicfUsrAuthCliNotifyEnable,
            hpicfUsrAuthPortSecNotifyEnable }
        STATUS current
        DESCRIPTION
            "A group of notification data and configuration objects."
        ::= { hpicfUsrAuthNotifyConformance 3 }

   -- 1.3.6.1.4.1.11.2.14.11.5.1.19.9
   hpicfUsrAuthMacGlobalConformance OBJECT IDENTIFIER ::= { hpicfUsrAuthMIB 9 }

   -- 1.3.6.1.4.1.11.2.14.11.5.1.19.9.1
   hpicfUsrAuthMacGroup OBJECT-GROUP
       OBJECTS { hpicfUsrAuthMacAuthPassword }
       STATUS current
       DESCRIPTION
           "A group of Mac auth global configuration objects."
       ::= { hpicfUsrAuthMacGlobalConformance 1}

    -- 1.3.6.1.4.1.11.2.14.11.5.1.19.10
    hpicfUsrAuthWebAuthAccessDeniedConformance OBJECT IDENTIFIER ::= { hpicfUsrAuthMIB 10 }
 
    -- 1.3.6.1.4.1.11.2.14.11.5.1.19.10.1
    hpicfUsrAuthWebAuthAccessDeniedGroup OBJECT-GROUP
        OBJECTS { hpicfUsrAuthWebAuthAccessDeniedMode,
                  hpicfUsrAuthWebAuthAccessDeniedMessage }
        STATUS current
        DESCRIPTION
             "A group of web-auth access denied configuration objects."
        ::= { hpicfUsrAuthWebAuthAccessDeniedConformance 1}
   -- 1.3.6.1.4.1.11.2.14.11.5.1.19.11
   hpicfUsrAuthMacAuthUsrNumberConformance OBJECT IDENTIFIER ::= { hpicfUsrAuthMIB 11 }

   -- 1.3.6.1.4.1.11.2.14.11.5.1.19.11.1
   hpicfUsrAuthMacAuthUsrNumberGroup OBJECT-GROUP
       OBJECTS { hpicfUsrAuthMacAuthUsrNumberCnt,
                 hpicfUsrAuthMacAuthSessionUsrNumberCnt }
       STATUS current
       DESCRIPTION
           "Number of Mac authenticated client objects in the switch and port."
       ::= { hpicfUsrAuthMacAuthUsrNumberConformance 1}

END
