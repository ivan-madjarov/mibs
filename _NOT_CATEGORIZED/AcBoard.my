AcBoard DEFINITIONS ::= BEGIN


    IMPORTS
       
       OBJECT-TYPE, 
       MODULE-IDENTITY                             FROM SNMPv2-SMI
       TAddress, 
       DisplayString, 
       DateAndTime, TEXTUAL-CONVENTION             FROM SNMPv2-TC
       IpAddress                                   FROM RFC1155-SMI
       enterprises                                 FROM SNMPv2-SMI;

	audioCodes       OBJECT IDENTIFIER ::= {enterprises 5003}
	acRegistrations  OBJECT IDENTIFIER ::= {audioCodes 7}
	acGeneric        OBJECT IDENTIFIER ::= {audioCodes 8}
	acProducts       OBJECT IDENTIFIER ::= {audioCodes 9}	
        acBoardMibs     OBJECT IDENTIFIER ::= {acProducts 10}

       
acBoard        MODULE-IDENTITY       
    LAST-UPDATED "201208131137Z"          --Monday, August 13, 2012
    ORGANIZATION "AudioCodes Ltd"
    CONTACT-INFO
    "Postal: Support
	     AudioCodes LTD
             1 Hayarden Street
             Airport City 
	     Lod, ISRAEL 70151
     Tel:    972-3-9764000
     Fax:    972-3-9764040
     Email:  support@audiocodes.com
     Web:    www.audiocodes.com"		

    DESCRIPTION       
    "AudioCodes Proprietary MIB 
     Contains The managed objects of AudioCodes systems.
     Through this MIB, the User can set up the board configuration parameters, reset the board, 
	 and monitor the board's operational robustness and quality of service during run-time. 

    This MIB has the following Groups: 
	    boardConfiguration     
	    boardInformation   
	    channelConfiguration 
	    channelStatus 
	    notifications    
	    reset

    boardConfiguration:     
        When The user Get Parameter from most of sub-groups in boardConfiguration group, 
	    he gets the value that should be burned to the board after the next Remote Reset. 
	    He can Set new values to many parameters, and these values will burned to the board after the next remote Reset 
        In the sub-group mGCPDefaultChannelSettings the parameters are the actual parameters, 
	    that will take place when opening channel. (Reset is not needed for that sub-group).

    BoardInformation: 
        Contains Read-only parameters like: board name, serial number, number of channels, software version.

    ChannelConfiguration:
        Read-only Parameters to see the configuratin of each channel: voice settings, fax settings, etc.         

    ChannelStatus:
        Read-only parameters about the status of channel, like: Is the channle active, is it in Silence Period, 
		is it in Fax mode, ON/Off hook, etc. 
        This group contains also counters: packets to DSP, errors, lost packets, underruns, etc.

    Notifications:
        In this version, the notification we have are: acEvBoardStarted, and acEvResetingBoard. 
        The board should send these notifications to its manager 
		that the user defined in INI file with the parameter: NMPManagerIP = (IP address). 

    Reset:
        To remote reset the board, the user should set an integer value to the parameter remoteReset.
		Then he should get the trap acEvResettingBoard. 
        Note: Before Reset, The current boardConfiguration parameters will be burned  to the board. 
		      The user should not use INI file, if he wants these parameters to take place.

		To set the default values, the user should set an integer value to the parameter acSetDefaults.
		"

    REVISION    "200401261153Z"          --Monday, January 26, 2004

    DESCRIPTION  " Update mib  for version 4.4  - obsolete atmSetting   and ss7Setting  families  "

    ::= {acBoardMibs 1}  

 
      -- ****************************************
     -- boardConfiguration Configuration
     -- ****************************************
     boardConfiguration            OBJECT IDENTIFIER ::= {acBoard 1}


     -- ****************************************
     -- boardTDMBusSettings Configuration
     -- ****************************************
     boardTDMBusSettings           OBJECT IDENTIFIER ::= {boardConfiguration 1}


     pCMLawSelect OBJECT-TYPE
       SYNTAX INTEGER {
                  muLaw(3)
,
                  aLaw(1)

                  }
       MAX-ACCESS read-write
       STATUS obsolete
       DESCRIPTION
           "Selects the type of PCM companding law in input/output TDM bus (TDM bus is defined using the TDMBusType parameter). "
       ::= {boardTDMBusSettings 1}



     tDMBusClockSource OBJECT-TYPE
       SYNTAX INTEGER {
                  acTDMBusClockSource-Internal(1)
,
                  acTDMBusClockSource-MVIP(3)
,
                  acTDMBusClockSource-Network(4)
,
                  acTDMBusClockSource-H110-A(8)
,
                  acTDMBusClockSource-H110-B(9)
,
                  acTDMBusClockSource-NetReference1(10)
,
                  acTDMBusClockSource-NetReference2(11)
,
                  acTDMBusClockSource-SC-2M(12)
,
                  acTDMBusClockSource-SC-4M(13)
,
                  acTDMBusClockSource-SC-8M(14)
,
                  acTDMBusClockSource-BITS(15)
,
                  acTDMBusClockSource-Network-B(16)
,
                  acTDMBusClockSource-ATM-OC3(17)
,
                  acTDMBusClockSource-ATM-OC3-B(18)
,
                  acTDMBusClockSource-ATM-OC12(19)

                  }
       MAX-ACCESS read-write
       STATUS obsolete
       DESCRIPTION
           "Selects the clock source on which the board synchronizes"
       ::= {boardTDMBusSettings 2}



     tDMBusEnableFallBack OBJECT-TYPE
       SYNTAX INTEGER {
                  disable(0) 
,
                  enable(1)

                  }
       MAX-ACCESS read-write
       STATUS obsolete
       DESCRIPTION
           "Enable/Disable clock fallback. The Fall Back clock is determined by BSPTDMBusFallbackClock"
       ::= {boardTDMBusSettings 3}



     tDMBusLocalReference OBJECT-TYPE
       SYNTAX INTEGER (0..27)
       MAX-ACCESS read-write
       STATUS obsolete
       DESCRIPTION
           "When ClockSource is set to acH110BusClockSource_Network this parameter selects the TrunkID to be used as the clock synchronization source of the board.
When using H.110/H.100 bus this parameter also selects the trunk which is used as the clock source for the NETREF clock generation (in this case ClockSource might not be set to acH110BusClockSource_Network)."
       ::= {boardTDMBusSettings 4}



     idlePCMPattern OBJECT-TYPE
       SYNTAX INTEGER (0..255)
       MAX-ACCESS read-write
       STATUS obsolete
       DESCRIPTION
           "PCM Pattern applied to E1/T1 timeslot (B-channel) when channel is idle. "
       ::= {boardTDMBusSettings 5}



     idleABCD OBJECT-TYPE
       SYNTAX INTEGER (0..15)
       MAX-ACCESS read-write
       STATUS obsolete
       DESCRIPTION
           "ABCD (CAS) Pattern to be applied to CAS signaling bus before changed by the user or PSTN protocol. This is only relevant when using PSTN interface with CAS protocols."
       ::= {boardTDMBusSettings 6}



     tDMBusMasterSlaveSelection OBJECT-TYPE
       SYNTAX INTEGER {
                  acTDMBusSlaveMode(0)
,
                  acTDMBusMasterMode(1)
,
                  acH110BusSecondaryMasterMode(2)

                  }
       MAX-ACCESS read-write
       STATUS obsolete
       DESCRIPTION
           "Set SC/MVIP/H.110 to either: Master mode (the board is the clock source for the TDM bus) or Slave mode (some other board in the system must supply the clock to the TDM bus)."
       ::= {boardTDMBusSettings 7}



     tDMBusNetRefSpeed OBJECT-TYPE
       SYNTAX INTEGER {
                  acTH110BusNetReferenceSpeed-8khz(0)
,
                  acTH110BusNetReferenceSpeed-20488khz(2)

                  }
       MAX-ACCESS read-write
       STATUS obsolete
       DESCRIPTION
           "Determine the NetRef frequency (for both generation and synchronization). "
       ::= {boardTDMBusSettings 8}



     tDMBusOutputStartingChannel OBJECT-TYPE
       SYNTAX INTEGER (0..127)
       MAX-ACCESS read-write
       STATUS obsolete
       DESCRIPTION
           "Defines the outgoing TDM Timeslot of the first channel (ChannelId=0). The remaining channels are organized sequentially."
       ::= {boardTDMBusSettings 9}



     boardTDMBusOutputPort OBJECT-TYPE
       SYNTAX INTEGER (0..31)
       MAX-ACCESS read-write
       STATUS obsolete
       DESCRIPTION
           "Defines the SC/MVIP/H.100/H.110 port to be used for board's channel #0. All other channels then occupy the next timeslots sequentially"
       ::= {boardTDMBusSettings 10}



     tDMBusSpeed OBJECT-TYPE
       SYNTAX INTEGER {
                  acTDMBusSpeed-2Mbps(0)
,
                  acTDMBusSpeed-4Mbps(2)
,
                  acTDMBusSpeed-8Mbps(3)
,
                  acTDMBusSpeed-16Mbps(4)

                  }
       MAX-ACCESS read-write
       STATUS obsolete
       DESCRIPTION
           "Selects the TDM Bus Speed. Speed is set according to the Bus Type. The following are allowed speeds for each bus type: SC = 0/2/3
H.110/H.100 = 3
MVIP = 0"
       ::= {boardTDMBusSettings 11}



     tDMBusType OBJECT-TYPE
       SYNTAX INTEGER {
                  mVIP-BUS(0)
,
                  sC-BUS(1)
,
                  uSE-FRAMERS(2)
,
                  qSLAC-BUS(3)
,
                  uSE-H110-BUS(4)
,
                  uSE-EXT-BUS(5)
,
                  aNALOG-BUS(6)
,
                  uSE-PSTN-SW-ONLY(8)

                  }
       MAX-ACCESS read-write
       STATUS obsolete
       DESCRIPTION
           "Selects the TDM bus interface to be used (only one TDM bus interface can be enabled at one time although more than one can physically exist on the board)."
       ::= {boardTDMBusSettings 12}



     acOverrideDefaultIdlePCMPattern OBJECT-TYPE
       SYNTAX INTEGER {
                  useDefaults(0) 
,
                  useIdlePCMPattern(1)

                  }
       MAX-ACCESS read-write
       STATUS obsolete
       DESCRIPTION
           "Override Default Idle PCM Pattern.
  0 - use defaults (0xff-Mulaw, 0x55-Alaw)
  1 - use IdlePCMPattern."
       ::= {boardTDMBusSettings 13}



     acOverrideDefaultIdleABCDPattern OBJECT-TYPE
       SYNTAX INTEGER {
                  useDefaults(0)
,
                  useIdleABCDPattern(1)

                  }
       MAX-ACCESS read-write
       STATUS obsolete
       DESCRIPTION
           "Description: Override Default Idle ABCD Pattern.
  0 - use defaults (0xf)
  1 - use IdleABCDPattern."
       ::= {boardTDMBusSettings 14}



     -- ****************************************
     -- networkSettings Configuration
     -- ****************************************
     networkSettings               OBJECT IDENTIFIER ::= {boardConfiguration 2}


     baseUDPPort OBJECT-TYPE
       SYNTAX INTEGER (0..64000)
       MAX-ACCESS read-write
       STATUS obsolete
       DESCRIPTION
           "Lower boundary of UDP ports to be used by the board. The upper boundary is BoardBaseUDPPort+10*(Number of Channels). Must be a multiple of 10."
       ::= {networkSettings 1}



     defaultGatewayAddr OBJECT-TYPE
       SYNTAX IpAddress
       MAX-ACCESS read-only
       STATUS obsolete
       DESCRIPTION
           "Default Gateway Address.
 Board's Default Gateway IP address. 
 (in host byte order e.g. 192.10.1.255 = 0xc00a01ff)."
       ::= {networkSettings 2}



     boardIPAddr OBJECT-TYPE
       SYNTAX IpAddress
       MAX-ACCESS read-only
       STATUS obsolete
       DESCRIPTION
           "Board IP Address. 
 in host byte order e.g. 192.10.1.2 = 0xc00a0102). 
  Users should set the subnet mask to a valid value per the IP address."
       ::= {networkSettings 3}



     boardSubNetAddr OBJECT-TYPE
       SYNTAX IpAddress
       MAX-ACCESS read-only
       STATUS obsolete
       DESCRIPTION
           "Board SubNet Address.
  (in host byte order e.g. 255.255.255.0 = 0xffffff00). 
  default =255.255.255.0."
       ::= {networkSettings 4}



     acSyslogServerIP OBJECT-TYPE
       SYNTAX IpAddress
       MAX-ACCESS read-write
       STATUS obsolete
       DESCRIPTION
           "IP address in dotted format notation, e.g., 192.10.1.255"
       ::= {networkSettings 5}



     acMGControlProtocolType OBJECT-TYPE
       SYNTAX INTEGER {
                  controlProtocol-None(0)
,
                  controlProtocol-MGCP(1)
,
                  controlProtocol-MEGACO(2)
,
                  controlProtocol-H323(4)
,
                  controlProtocol-SIP(8)

                  }
       MAX-ACCESS read-write
       STATUS obsolete
       DESCRIPTION
           "This parameter defines the control protocol type
 0 = none, 1 = MGCP, 2 = MEGACO, 4 = H323, 8 = SIP"
       ::= {networkSettings 6}



     acSNMPManagerIP OBJECT-TYPE
       SYNTAX IpAddress
       MAX-ACCESS read-write
       STATUS obsolete
       DESCRIPTION
           "SNMP manager server IP address"
       ::= {networkSettings 7}



     acDisableWEBConfig OBJECT-TYPE
       SYNTAX INTEGER {
                  enable(0)
,
                  disable(1)

                  }
       MAX-ACCESS read-write
       STATUS obsolete
       DESCRIPTION
           "Enables or disables Web Configuration 0-Read & Write mode(default) 1-Read Only mode"
       ::= {networkSettings 8}



     acEnableSyslog OBJECT-TYPE
       SYNTAX INTEGER {
                  disable(0)
,
                  enable(1)

                  }
       MAX-ACCESS read-write
       STATUS obsolete
       DESCRIPTION
           "Enable SysLog protocol log."
       ::= {networkSettings 9}



     acContrlProtocolTransportType OBJECT-TYPE
       SYNTAX INTEGER {
                  acCPTransport-UDP-IP(0)
,
                  acCPTransport-TCP-IP(1)
,
                  acCPTransport-SCTP-IP(2)

                  }
       MAX-ACCESS read-write
       STATUS obsolete
       DESCRIPTION
           "Defines the transport type for the control: 0 - UDP, 1 - TCP  (SCTP on road map)."
       ::= {networkSettings 10}



     acCPControlDiffServ OBJECT-TYPE
       SYNTAX INTEGER (0..63)
       MAX-ACCESS read-write
       STATUS obsolete
       DESCRIPTION
           "Defines the value of the 'DiffServ' field in the IP header for the control session."
       ::= {networkSettings 11}



     -- ****************************************
     -- snmpManagers Configuration
     -- ****************************************
     snmpManagers                  OBJECT IDENTIFIER ::= {networkSettings 21}


     -- ****************************************
     -- snmpManagers table decleration
     -- ****************************************
     snmpManagersTable OBJECT-TYPE
       SYNTAX SEQUENCE OF SnmpManagersEntry
       MAX-ACCESS not-accessible
       STATUS obsolete
       DESCRIPTION
           "Snmp Managers Table"
       ::= {snmpManagers 1}



     -- ****************************************
     -- snmpManagers table entry
     -- ****************************************
     snmpManagersEntry OBJECT-TYPE
       SYNTAX SnmpManagersEntry
       MAX-ACCESS not-accessible
       STATUS obsolete
       DESCRIPTION
           ""
       INDEX {snmpManagerIndex}
       ::= {snmpManagersTable 1}



     -- ****************************************
     -- snmpManagers TABLE
     -- ****************************************
     SnmpManagersEntry ::= SEQUENCE {
       snmpManagerIndex                                INTEGER,
       snmpManagerIsUsed                               INTEGER,
       snmpManagerIp                                   IpAddress,
       snmpManagerTrapPort                             INTEGER,
       snmpManagerTrapSendingEnable                    INTEGER
     }



     snmpManagerIndex OBJECT-TYPE
       SYNTAX INTEGER (0..2)
       MAX-ACCESS read-only
       STATUS obsolete
       DESCRIPTION
           "Snmp Manager Index"
       ::= {snmpManagersEntry 1}



     snmpManagerIsUsed OBJECT-TYPE
       SYNTAX INTEGER {
                  no(0)
,
                  yes(1)

                  }
       MAX-ACCESS read-write
       STATUS obsolete
       DESCRIPTION
           "Enable the SNMP Manager to recieve traps."
       ::= {snmpManagersEntry 2}



     snmpManagerIp OBJECT-TYPE
       SYNTAX IpAddress
       MAX-ACCESS read-write
       STATUS obsolete
       DESCRIPTION
           "IP address of default SNMP manager in dotted notation format: xxx.xxx.xxx.xxx. SNMP traps are sent to this manager."
       ::= {snmpManagersEntry 3}



     snmpManagerTrapPort OBJECT-TYPE
       SYNTAX INTEGER (0..65535)
       MAX-ACCESS read-write
       STATUS obsolete
       DESCRIPTION
           "Sets the trap ports to be used by the different managers."
       ::= {snmpManagersEntry 4}



     snmpManagerTrapSendingEnable OBJECT-TYPE
       SYNTAX INTEGER {
                  disable(0) 
,
                  enable(1)

                  }
       MAX-ACCESS read-write
       STATUS obsolete
       DESCRIPTION
           "Enable the SNMP Manager to recieve traps."
       ::= {snmpManagersEntry 5}



     -- ****************************************
     -- acNTPSettings Configuration
     -- ****************************************
     acNTPSettings                 OBJECT IDENTIFIER ::= {networkSettings 22}


     acNTPServerIPAddress OBJECT-TYPE
       SYNTAX IpAddress
       MAX-ACCESS read-write
       STATUS obsolete
       DESCRIPTION
           "NTP Server IP address."
       ::= {acNTPSettings 1}



     acNTPUtcOffset OBJECT-TYPE
       SYNTAX INTEGER (-43200..43200)
       MAX-ACCESS read-write
       STATUS deprecated
       DESCRIPTION
           "NTP time to offset in seconds. Default is 0. Range - Between -43200 ot 43200 seconds."
       ::= {acNTPSettings 2}



     acNTPUpdateInterval OBJECT-TYPE
       SYNTAX INTEGER (0..2147483647)
       MAX-ACCESS read-write
       STATUS deprecated
       DESCRIPTION
           "NTPupdate interval in seconds. Default is 86400 (24 hours). Not recommended to be set beyond one month (2592000 sec)."
       ::= {acNTPSettings 3}



     -- ****************************************
     -- acWEBAccess Configuration
     -- ****************************************
     acWEBAccess                   OBJECT IDENTIFIER ::= {networkSettings 23}


     -- ****************************************
     -- acWEBAccess table decleration
     -- ****************************************
     acWEBAccessTable OBJECT-TYPE
       SYNTAX SEQUENCE OF AcWEBAccessEntry
       MAX-ACCESS not-accessible
       STATUS obsolete
       DESCRIPTION
           ""
       ::= {acWEBAccess 1}



     -- ****************************************
     -- acWEBAccess table entry
     -- ****************************************
     acWEBAccessEntry OBJECT-TYPE
       SYNTAX AcWEBAccessEntry
       MAX-ACCESS not-accessible
       STATUS obsolete
       DESCRIPTION
           ""
       INDEX {acWEBAccessIndex}
       ::= {acWEBAccessTable 1}



     -- ****************************************
     -- acWEBAccess TABLE
     -- ****************************************
     AcWEBAccessEntry ::= SEQUENCE {
       acWEBAccessRowStatus                            INTEGER,
       acWEBAccessAction                               INTEGER,
       acWEBAccessActionResult                         INTEGER,
       acWEBAccessIndex                                INTEGER,
       acWEBAccessUserName                             OCTET STRING,
       acWEBAccessUserCode                             OCTET STRING
     }



     acWEBAccessRowStatus OBJECT-TYPE
       SYNTAX INTEGER (1..1)
       MAX-ACCESS read-write
       STATUS obsolete
       DESCRIPTION
           "WEB Access row-status"
       ::= {acWEBAccessEntry 1}



     acWEBAccessAction OBJECT-TYPE
       SYNTAX INTEGER (0..0)
       MAX-ACCESS read-write
       STATUS obsolete
       DESCRIPTION
           "WEB Access action"
       ::= {acWEBAccessEntry 2}



     acWEBAccessActionResult OBJECT-TYPE
       SYNTAX INTEGER (0..0)
       MAX-ACCESS read-only
       STATUS obsolete
       DESCRIPTION
           "WEB Access action result"
       ::= {acWEBAccessEntry 3}



     acWEBAccessIndex OBJECT-TYPE
       SYNTAX INTEGER (0..0)
       MAX-ACCESS read-only
       STATUS obsolete
       DESCRIPTION
           "WEB Access index"
       ::= {acWEBAccessEntry 4}



     acWEBAccessUserName OBJECT-TYPE
       SYNTAX OCTET STRING (SIZE (0..26))
       MAX-ACCESS read-write
       STATUS obsolete
       DESCRIPTION
           "WEB Access user name"
       ::= {acWEBAccessEntry 5}



     acWEBAccessUserCode OBJECT-TYPE
       SYNTAX OCTET STRING (SIZE (0..26))
       MAX-ACCESS read-write
       STATUS obsolete
       DESCRIPTION
           "WEB Access user code"
       ::= {acWEBAccessEntry 6}



     -- ****************************************
     -- auxiliarySettings Configuration
     -- ****************************************
     auxiliarySettings             OBJECT IDENTIFIER ::= {boardConfiguration 3}


     enableDiagnostics OBJECT-TYPE
       SYNTAX INTEGER {
                  acDiagnostics-Disabled(0)
,
                  acDiagnostics-BuiltInTest(1)
,
                  acDiagnostics-BuiltInTestwithPartialFlash(2)
,
                  acDiagnostics-BuiltInTestWithSDRAM(3)

                  }
       MAX-ACCESS read-write
       STATUS obsolete
       DESCRIPTION
           "The EnableDiagnostics checks the correct functionality of different hardware components on the board. Upon completion, the board sends EV_END_BIT which contains information on the results of the test of each hardware component. "
       ::= {auxiliarySettings 1}



     -- ****************************************
     -- trunkSettings Configuration
     -- ****************************************
     trunkSettings                 OBJECT IDENTIFIER ::= {boardConfiguration 4}


     -- ****************************************
     -- trunkSettings table decleration
     -- ****************************************
     trunkSettingsTable OBJECT-TYPE
       SYNTAX SEQUENCE OF TrunkSettingsEntry
       MAX-ACCESS not-accessible
       STATUS obsolete
       DESCRIPTION
           "Trunks Table"
       ::= {trunkSettings 1}



     -- ****************************************
     -- trunkSettings table entry
     -- ****************************************
     trunkSettingsEntry OBJECT-TYPE
       SYNTAX TrunkSettingsEntry
       MAX-ACCESS not-accessible
       STATUS obsolete
       DESCRIPTION
           ""
       INDEX {trunkId}
       ::= {trunkSettingsTable 1}



     -- ****************************************
     -- trunkSettings TABLE
     -- ****************************************
     TrunkSettingsEntry ::= SEQUENCE {
       trunkId                                         INTEGER,
       clockMaster                                     INTEGER,
       framingMethod                                   INTEGER,
       protocolType                                    INTEGER,
       terminationSide                                 INTEGER,
       dchConfig                                       INTEGER,
       lineCode                                        INTEGER,
       lineBuildOutLoss                                INTEGER,
       lineBuildOutOverwrite                           INTEGER,
       lineBuildOutXPM0                                INTEGER,
       lineBuildOutXPM1                                INTEGER,
       lineBuildOutXPM2                                INTEGER,
       traceLevel                                      INTEGER,
       acV5InterfaceTrunkGroupId                       INTEGER,
       acV5LinkIdOld                                      INTEGER,
       acPMStatus                                      INTEGER,
       acLedStatusColor                                INTEGER,
       acLedStatusRate                                 INTEGER,
       acIsdnNfasInterfaceId                           INTEGER,
       acTrunkCasTableIndex                            INTEGER,
       acTrunkAdminState                               INTEGER,
       acPSTNIuaInterfaceId                            INTEGER,
       acIsdnQ931LayerResponseBehavior                 INTEGER,
       acIsdnIncomingCallsBehavior                     INTEGER,
       acIsdnOutgoingCallsBehavior                     INTEGER,
       acIsdnGeneralCCBehavior                         INTEGER,
       acIsdnNfasGroupNumber                           INTEGER
     }



     trunkId OBJECT-TYPE
       SYNTAX INTEGER (0..32)
       MAX-ACCESS read-only
       STATUS obsolete
       DESCRIPTION
           "Trunk ID at board in which the call is taking place "
       ::= {trunkSettingsEntry 1}



     clockMaster OBJECT-TYPE
       SYNTAX INTEGER {
                  acCLOCK-MASTER-OFF(0)
,
                  acCLOCK-MASTER-ON(1)

                  }
       MAX-ACCESS read-write
       STATUS obsolete
       DESCRIPTION
           "Selects the trunk clock source.
When choosing acCLOCK_MASTER_OFF (= 0) the clock is recovered from the line.
When choosing acCLOCK_MASTER_ON (= 1) the trunk clock source is provided by the internal/TDM bus clock source depending on the TDMBusClockSource parameter."
       ::= {trunkSettingsEntry 2}



     framingMethod OBJECT-TYPE
       SYNTAX INTEGER {
                  eXTENDED-SUPER-FRAME(0)
,
                  sUPER-FRAME(1)
,
                  e1-FRAMING-DDF(2)
,
                  e1-FRAMING-MFF-CRC4(3)
,
                  e1-FRAMING-MFF-CRC4-EXT(4)
,
                  e1-FRAMING-NIL(5)
,
                  t1-FRAMING-F4(6)
,
                  t1-FRAMING-F12(7)
,
                  t1-FRAMING-ESF(8)
,
                  t1-FRAMING-ESF-CRC6 (9)
,
                  t1-FRAMING-F72(10)
,
                  t1-FRAMING-ESF-CRC6-JT(11)
,
                  t1-FRAMING-NIL(12) 

                  }
       MAX-ACCESS read-write
       STATUS obsolete
       DESCRIPTION
           "Selects the Framing method to be used for this trunk."
       ::= {trunkSettingsEntry 3}



     protocolType OBJECT-TYPE
       SYNTAX INTEGER {
                  nONE(0)
,
                  e1EuroISDN(1)
,
                  t1Cas(2)
,
                  t1RawCas(3)
,
                  t1Transparent(4)
,
                  e1Transparent31(5)
,
                  e1Transparent30(6)
,
                  e1Mfcr2(7)
,
                  e1CasR2(8)
,
                  e1RawCAS(9)
,
                  t1-NI2ISDN(10)
,
                  t1-4EssISDN(11)
,
                  t1-5Ess-9-ISDN(12)
,
                  t1-5Ess-10-ISDN(13)
,
                  t1-Dms100-ISDN(14)
,
                  j1-TRANSPARENT(15)
,
                  pROTOCOL-TYPE-T1-NTT-ISDN(16)
,
                  pROTOCOL-TYPE-E1-AUSTEL-ISDN(17)
,
                  pROTOCOL-TYPE-E1-HKT-ISDN(18)
,
                  pROTOCOL-TYPE-E1-KOR-ISDN(19)
,
                  pROTOCOL-TYPE-T1-HKT-ISDN(20)
,
                  pROTOCOL-TYPE-E1-QSIG(21)
,
                  pROTOCOL-TYPE-E1-TNZ-22(22)
,
                  pROTOCOL-TYPE-T1-EXTRA-23(23)
,
                  pROTOCOL-TYPE-V5-1-AN(24)
,
                  pROTOCOL-TYPE-V5-1-LE(25)
,
                  pROTOCOL-TYPE-V5-2-AN(26)
,
                  pROTOCOL-TYPE-V5-2-LE(27)
,
                  pROTOCOL-TYPE-T1-IUA(28)
,
                  pROTOCOL-TYPE-E1-IUA(29)
,
                  pROTOCOL-TYPE-E1-EXTRA-30(30)
,
                  pROTOCOL-TYPE-E1-EXTRA-31(31)
,
                  pROTOCOL-TYPE-T1-EXTRA-32(32)
,
                  pROTOCOL-TYPE-T1-EXTRA-33(33)
,
                  pROTOCOL-TYPE-T1-EURO-ISDN(34)
,
                  pROTOCOL-TYPE-T1-DMS100-MERIDIAN-ISDN(35)
,
                  pROTOCOL-TYPE-T1-NI1-ISDN(36)

                  }
       MAX-ACCESS read-write
       STATUS obsolete
       DESCRIPTION
           "Protocol Type.  Sets the PSTN protocol to be used for this trunk. 
The protocol type parameter defines the interface 
  and the specific telephony protocol. 
 Each protocol defines the following:
              1. E1 or T1 physical line configuration.
              2. Fixed connection of the relevant time-slots, 
              which are the Trunks' B-channels, mapping to the 60 
        (128 for TrunkPack®-VoIP/400) DSP channels. 
        This limitation is about to change in versions higher than 3.4.
              3. Layer 3 specific telephony protocol or transparent mode of operation.
Currently only identical configurations (protocol type, framing method, etc.) 
  for the two trunks are supported.(see at the TrunkPack®-VoIP User Manual 
  for available protocols families)  relevant only when TDMBusType=FRAMERS. 
"
       ::= {trunkSettingsEntry 4}



     terminationSide OBJECT-TYPE
       SYNTAX INTEGER {
                  acUSER-TERMINATION-SIDE(0)
,
                  acNETWORK-TERMINATION-SIDE(1)

                  }
       MAX-ACCESS read-write
       STATUS obsolete
       DESCRIPTION
           "For ISDN only. select the ISDN Termination side (layer 2)"
       ::= {trunkSettingsEntry 5}



     dchConfig OBJECT-TYPE
       SYNTAX INTEGER {
                  acDCH-CONFIG-PRIMARY(0)
,
                  acDCH-CONFIG-BACKUP(1)
,
                  acDCH-CONFIG-NFAS(2)
,
                  acDCH-NOT-ISDN-TRUNK(3)

                  }
       MAX-ACCESS read-write
       STATUS obsolete
       DESCRIPTION
           "Defines D-channel configuration. This setting is only applicable to ISDN PRI protocols that support NFAS and/or D-channel backup procedures."
       ::= {trunkSettingsEntry 6}



     lineCode OBJECT-TYPE
       SYNTAX INTEGER {
                  acB8ZS(0)
,
                  acAMI(1)
,
                  acHDB3(2)

                  }
       MAX-ACCESS read-write
       STATUS obsolete
       DESCRIPTION
           "Use to select line code. B8ZS or AMI for T1 spans and HDB3 or AMI for E1 spans. "
       ::= {trunkSettingsEntry 7}



     lineBuildOutLoss OBJECT-TYPE
       SYNTAX INTEGER {
                  ac0DB(0)
,
                  ac7-5DB(1)
,
                  ac15DB(2)
,
                  ac22-5DB(3)

                  }
       MAX-ACCESS read-write
       STATUS obsolete
       DESCRIPTION
           "Selects the line build out loss to be used for this trunk"
       ::= {trunkSettingsEntry 8}



     lineBuildOutOverwrite OBJECT-TYPE
       SYNTAX INTEGER {
                  acNO-OVER-WRITE(0)
,
                  acOVER-WRITE(1)

                  }
       MAX-ACCESS read-write
       STATUS obsolete
       DESCRIPTION
           "Overwrite the framer's XPM registers values (these registers control the line pulse shape)."
       ::= {trunkSettingsEntry 9}



     lineBuildOutXPM0 OBJECT-TYPE
       SYNTAX INTEGER (0..255)
       MAX-ACCESS read-write
       STATUS obsolete
       DESCRIPTION
           "Controls the Framer's XPM0 register value (line pulse shape control). Applicable only when TrunkConfig.LineBuildOut.Overwrite=1.Should be used only by expert Users."
       ::= {trunkSettingsEntry 10}



     lineBuildOutXPM1 OBJECT-TYPE
       SYNTAX INTEGER (0..255)
       MAX-ACCESS read-write
       STATUS obsolete
       DESCRIPTION
           "Controls the Framer's XPM1 register value (line pulse shape control).
Applicable only when TrunkConfig.LineBuildOut.Overwrite=1.
Should be used only by expert Users."
       ::= {trunkSettingsEntry 11}



     lineBuildOutXPM2 OBJECT-TYPE
       SYNTAX INTEGER (0..255)
       MAX-ACCESS read-write
       STATUS obsolete
       DESCRIPTION
           "Controls the Framer's XPM2 register value (line pulse shape control). Applicable only when TrunkConfig.LineBuildOut.Overwrite=1.Should be used only by expert Users."
       ::= {trunkSettingsEntry 12}



     traceLevel OBJECT-TYPE
       SYNTAX INTEGER {
                  acNO-TRACE(0)
,
                  acFULL-ISDN-TRACE(1)
,
                  acLAYER3-ISDN-TRACE(2)
,
                  acONLY-ISDN-Q931-MSGS-TRACE(3)
,
                  acLAYER3-ISDN-TRACE-NO-DUPLICATION(4)
,
                  acFULL-ISDN-TRACE-WITH-DUPLICATION(5)
,
                  acISDN-Q931-RAW-DATA-TRACE(6)
,
                  acISDN-Q921-RAW-DATA-TRACE(7)
,
                  acISDN-Q931-Q921-RAW-DATA-TRACE(8)
,
                  acSS7-MTP2(10)
,
                  acSS7-MTP2-AND-APPLI(11)
,
                  acSS7-MTP2-SL-L3-NO-MSU(12)
,
                  acSS7-AAL(15)

                  }
       MAX-ACCESS read-write
       STATUS obsolete
       DESCRIPTION
           "Defines the Protocol Trace level "
       ::= {trunkSettingsEntry 13}



     acV5InterfaceTrunkGroupId OBJECT-TYPE
       SYNTAX INTEGER (0..31)
       MAX-ACCESS read-only
       STATUS obsolete
       DESCRIPTION
           "copy from Table 8-1 in LIB manual 4.2beta"
       ::= {trunkSettingsEntry 14}



     acV5LinkIdOld OBJECT-TYPE
       SYNTAX INTEGER (0..255)
       MAX-ACCESS read-write
       STATUS obsolete
       DESCRIPTION
           "copy from Table 8-1 in LIB manual 4.2beta"
       ::= {trunkSettingsEntry 15}



     acPMStatus OBJECT-TYPE
       SYNTAX INTEGER {
                  disable(0)
,
                  enable(1)

                  }
       MAX-ACCESS read-write
       STATUS obsolete
       DESCRIPTION
           "performance Monitoring Enable/Disable."
       ::= {trunkSettingsEntry 16}



     acLedStatusColor OBJECT-TYPE
       SYNTAX INTEGER {
                  off(0)
,
                  red(1)
,
                  green(2)

                  }
       MAX-ACCESS read-only
       STATUS obsolete
       DESCRIPTION
           "Trunk led status color"
       ::= {trunkSettingsEntry 17}



     acLedStatusRate OBJECT-TYPE
       SYNTAX INTEGER {
                  steady(0)
,
                  blink(1)

                  }
       MAX-ACCESS read-only
       STATUS obsolete
       DESCRIPTION
           "Trunk led status blinking rate"
       ::= {trunkSettingsEntry 18}



     acIsdnNfasInterfaceId OBJECT-TYPE
       SYNTAX INTEGER (0..255)
       MAX-ACCESS read-write
       STATUS obsolete
       DESCRIPTION
           "Defines the Interface ID
works with NS_EXPLICIT_INTERFACE_ID bit. Refer to the Appendix A.8 'ISDN Flexible Behavior' in the VoPLib Reference Library User's Manual Document #: LTRT-00740. "
       ::= {trunkSettingsEntry 19}



     acTrunkCasTableIndex OBJECT-TYPE
       SYNTAX INTEGER (0..7)
       MAX-ACCESS read-write
       STATUS obsolete
       DESCRIPTION
           "Index of Cas Table used by this Trunk"
       ::= {trunkSettingsEntry 20}



     acTrunkAdminState OBJECT-TYPE
       SYNTAX INTEGER {
                  lock(0)
,
                  unLock(1)

                  }
       MAX-ACCESS read-write
       STATUS obsolete
       DESCRIPTION
           "Trunk Administrative State"
       ::= {trunkSettingsEntry 21}



     acPSTNIuaInterfaceId OBJECT-TYPE
       SYNTAX INTEGER (-1..2147483647)
       MAX-ACCESS read-write
       STATUS obsolete
       DESCRIPTION
           "IUA trunk interface ID value"
       ::= {trunkSettingsEntry 22}



     acIsdnQ931LayerResponseBehavior OBJECT-TYPE
       SYNTAX INTEGER (-2147483647..2147483647)
       MAX-ACCESS read-write
       STATUS obsolete
       DESCRIPTION
           "Bit-field used to determine several behavior options, which influence how the Q.931 protocol behaves."
       ::= {trunkSettingsEntry 23}



     acIsdnIncomingCallsBehavior OBJECT-TYPE
       SYNTAX INTEGER (0..2147483647)
       MAX-ACCESS read-write
       STATUS obsolete
       DESCRIPTION
           "This is the bit-field used to determine several behavior options that influence how the ISDN Stack INCOMING calls behave. Refer to the Appendix A.8 'ISDN Flexible Behavior' in the VoPLib Reference Library User's Manual Document #: LTRT-00740."
       ::= {trunkSettingsEntry 24}



     acIsdnOutgoingCallsBehavior OBJECT-TYPE
       SYNTAX INTEGER (0..65535)
       MAX-ACCESS read-write
       STATUS obsolete
       DESCRIPTION
           "This is the bit-field used to determine several behavior options that influence how the ISDN Stack OUTGOING calls behave. Refer to Appendix A.8 in the 'VoPLib Reference Library User's Manual. "
       ::= {trunkSettingsEntry 25}



     acIsdnGeneralCCBehavior OBJECT-TYPE
       SYNTAX INTEGER (0..65535)
       MAX-ACCESS read-write
       STATUS obsolete
       DESCRIPTION
           "This is the bit-field used to determine several general ISDN behavior options. Refer to the Appendix A.8 'ISDN Flexible Behavior' in the VoPLib Reference Library User's Manual Document #: LTRT-00740."
       ::= {trunkSettingsEntry 26}



     acIsdnNfasGroupNumber OBJECT-TYPE
       SYNTAX INTEGER (0..4)
       MAX-ACCESS read-write
       STATUS obsolete
       DESCRIPTION
           "Relevant only for T1 ISDN NFAS trunks indicates the group number of the NFAS group. ;Valid NFAS group numbers are only 1 to 4, 0 indicating that this trunk is not NFAS (in this case the ISDNNFASInterfaceID and DchConfig parameters are ignored)."
       ::= {trunkSettingsEntry 27}



     -- ****************************************
     -- mGCPSettings Configuration
     -- ****************************************
     mGCPSettings                  OBJECT IDENTIFIER ::= {boardConfiguration 5}


     callAgentIP OBJECT-TYPE
       SYNTAX IpAddress
       MAX-ACCESS read-write
       STATUS obsolete
       DESCRIPTION
           "MGCP Call Agent IP address to be used for the initial RestartInProgress MGCP message (RSIP)
(e.g., 192.10.1.255). Set to 0.0.0.0 to avoid sending RSIP. This parameter if in use overrides the Call Agent IP address provided in BootP."
       ::= {mGCPSettings 1}



     callAgentPort OBJECT-TYPE
       SYNTAX INTEGER (0..65534)
       MAX-ACCESS read-write
       STATUS obsolete
       DESCRIPTION
           "Gate Way will use CallAgentPort as default UDP Port of MGCP Call Agent."
       ::= {mGCPSettings 2}



     callAgentDomainName OBJECT-TYPE
       SYNTAX OCTET STRING (SIZE (0..64))
       MAX-ACCESS read-write
       STATUS obsolete
       DESCRIPTION
           "MGCP Call Agent domain name."
       ::= {mGCPSettings 3}



     redundantAgentIP OBJECT-TYPE
       SYNTAX IpAddress
       MAX-ACCESS read-write
       STATUS obsolete
       DESCRIPTION
           "Redundant MGCP call agent IP address for initial RestartInProgress MGCP message (RSIP) e.g. 192.10.1.255. Set to 0 to avoid sending RSIP."
       ::= {mGCPSettings 4}



     redundantAgentPort OBJECT-TYPE
       SYNTAX INTEGER (0..65534)
       MAX-ACCESS read-write
       STATUS obsolete
       DESCRIPTION
           "UDP Port of Redundant MGCP call agent."
       ::= {mGCPSettings 5}



     redundantCallAgentDomainName OBJECT-TYPE
       SYNTAX OCTET STRING (SIZE (0..64))
       MAX-ACCESS read-write
       STATUS obsolete
       DESCRIPTION
           "Redundant MGCP Call Agent Domain name"
       ::= {mGCPSettings 6}



     dePopulatedChannelsNumber OBJECT-TYPE
       SYNTAX INTEGER (-1..2147483647)
       MAX-ACCESS read-write
       STATUS obsolete
       DESCRIPTION
           "This parameter can be used to enable MGCP call agent to access only subset of the on board channel bank. Set to -1 (or do not specify) to use all channels."
       ::= {mGCPSettings 7}



     gateWayName OBJECT-TYPE
       SYNTAX OCTET STRING (SIZE (0..64))
       MAX-ACCESS read-write
       STATUS obsolete
       DESCRIPTION
           "GateWay Name"
       ::= {mGCPSettings 8}



     endPointName OBJECT-TYPE
       SYNTAX OCTET STRING (SIZE (0..20))
       MAX-ACCESS read-write
       STATUS obsolete
       DESCRIPTION
           "MGCP: Gateway's end point name. This is a prefix used to identify the endpoint, i.e., 'ACgw' in the following example: 'ACgw5@acl.com'. MEGACO: Prefix of the endpoint part of the termination name"
       ::= {mGCPSettings 9}



     mGCPCommunicationLayerTimeout OBJECT-TYPE
       SYNTAX INTEGER (0..999)
       MAX-ACCESS read-write
       STATUS obsolete
       DESCRIPTION
           "Assumed delay of the communication layer. It is used in retransmission."
       ::= {mGCPSettings 10}



     -- ****************************************
     -- acDefaultChannelSettings Configuration
     -- ****************************************
     acDefaultChannelSettings      OBJECT IDENTIFIER ::= {boardConfiguration 6}


     acChDefaultDJBufMinDelay OBJECT-TYPE
       SYNTAX INTEGER (0..150)
       MAX-ACCESS read-write
       STATUS obsolete
       DESCRIPTION
           "Dynamic Jitter Buffer Minimum Delay (msec)"
       ::= {acDefaultChannelSettings 1}



     acChDefaultDJBufOptFactor OBJECT-TYPE
       SYNTAX INTEGER (0..13)
       MAX-ACCESS read-write
       STATUS obsolete
       DESCRIPTION
           "Dynamic Jitter Buffer frame error/delay optimization."
       ::= {acDefaultChannelSettings 2}



     acChDefaultCallerIDType OBJECT-TYPE
       SYNTAX INTEGER {
                  callerIDStandard-Bellcore(0)
,
                  callerIDStandard-ETSI(1)
,
                  callerIDStandard-NTT(2)
,
                  callerIDStandard-DTMF-Based-ETSI(16)
,
                  callerIDStandard-Denmark(17)
,
                  callerIDStandard-Indian(18)

                  }
       MAX-ACCESS read-write
       STATUS obsolete
       DESCRIPTION
           "The supported caller ID standard types"
       ::= {acDefaultChannelSettings 3}



     acChDefaultFaxModemBypassM OBJECT-TYPE
       SYNTAX INTEGER (1..12)
       MAX-ACCESS read-write
       STATUS obsolete
       DESCRIPTION
           "Number of basic frames to generating one RTP fax/modem bypass packet."
       ::= {acDefaultChannelSettings 4}



     acChDefaultFaxModemRelayVolume OBJECT-TYPE
       SYNTAX INTEGER (-18..-3)
       MAX-ACCESS read-write
       STATUS obsolete
       DESCRIPTION
           "Fax gain control. The range -18 to -3 relates to -18.5 dBm to -3.5 dBm in 1 dBm steps."
       ::= {acDefaultChannelSettings 5}



     acChDefaultFaxRelayECMEnable OBJECT-TYPE
       SYNTAX INTEGER {
                  disable(0)
,
                  enable(1)

                  }
       MAX-ACCESS read-write
       STATUS obsolete
       DESCRIPTION
           "Enables or disables the using of ECM mode during Fax Relay."
       ::= {acDefaultChannelSettings 6}



     acChDefaultFaxRelayMaxRate OBJECT-TYPE
       SYNTAX INTEGER {
                  acRate2400bps(0)
,
                  acRate4800bps(1)
,
                  acRate7200bps(2)
,
                  acRate9600bps(3)
,
                  acRate12000bps(4)
,
                  acRate14400bps(5)

                  }
       MAX-ACCESS read-write
       STATUS obsolete
       DESCRIPTION
           "Limits the maximum rate at which fax messages are transmitted. "
       ::= {acDefaultChannelSettings 7}



     acChDefaultFaxTransportMode OBJECT-TYPE
       SYNTAX INTEGER {
                  disable(0)
,
                  relayEnable(1)
,
                  byPassEnable(2)
,
                  eventsOnly(3)

                  }
       MAX-ACCESS read-write
       STATUS obsolete
       DESCRIPTION
           "Sets the Fax over IP transport method."
       ::= {acDefaultChannelSettings 8}



     acChDefaultModemRelayRedundancyDepth OBJECT-TYPE
       SYNTAX INTEGER {
                  disable(0)
,
                  enable(1)

                  }
       MAX-ACCESS read-write
       STATUS obsolete
       DESCRIPTION
           "Amount of redundancy for fax relay packets"
       ::= {acDefaultChannelSettings 9}



     acChDefaultModemRelayMaxRate OBJECT-TYPE
       SYNTAX INTEGER {
                  ac2400(0)
,
                  ac4800(1)
,
                  ac7200(2)
,
                  ac9600(3)
,
                  ac12000(4)
,
                  ac14400(5)

                  }
       MAX-ACCESS read-write
       STATUS obsolete
       DESCRIPTION
           " Default: Modem Relay Max Rate"
       ::= {acDefaultChannelSettings 10}



     acChDefaultUseT38orFRF11 OBJECT-TYPE
       SYNTAX INTEGER {
                  fRF11(0)
,
                  acT38(1)

                  }
       MAX-ACCESS read-write
       STATUS obsolete
       DESCRIPTION
           "Selects protocol to send/ receive fax relay."
       ::= {acDefaultChannelSettings 11}



     acChDefaultV21ModemTransportType OBJECT-TYPE
       SYNTAX INTEGER {
                  disable(0)
,
                  relayEnable(1)
,
                  byPassEnable(2)
,
                  eventsOnly(3)

                  }
       MAX-ACCESS read-write
       STATUS obsolete
       DESCRIPTION
           "Sets the V.21 modem transport method (must be set to 0 = disable)"
       ::= {acDefaultChannelSettings 12}



     acChDefaultV22ModemTransportType OBJECT-TYPE
       SYNTAX INTEGER {
                  disable(0)
,
                  relayEnable(1)
,
                  byPassEnable(2)
,
                  eventsOnly(3)

                  }
       MAX-ACCESS read-write
       STATUS obsolete
       DESCRIPTION
           "Sets the V.22 modem transport method "
       ::= {acDefaultChannelSettings 13}



     acChDefaultV23ModemTransportType OBJECT-TYPE
       SYNTAX INTEGER {
                  disable(0)
,
                  relayEnable(1)
,
                  byPassEnable(2)
,
                  eventsOnly(3)

                  }
       MAX-ACCESS read-write
       STATUS obsolete
       DESCRIPTION
           "Sets the V.23 modem transport method "
       ::= {acDefaultChannelSettings 14}



     acChDefaultV32ModemTransportType OBJECT-TYPE
       SYNTAX INTEGER {
                  disable(0)
,
                  relayEnable(1)
,
                  byPassEnable(2)
,
                  eventsOnly(3)

                  }
       MAX-ACCESS read-write
       STATUS obsolete
       DESCRIPTION
           "Sets the V.32 modem transport method "
       ::= {acDefaultChannelSettings 15}



     acChDefaultV34ModemTransportType OBJECT-TYPE
       SYNTAX INTEGER {
                  disable(0)
,
                  relayEnable(1)
,
                  byPassEnable(2)
,
                  eventsOnly(3)

                  }
       MAX-ACCESS read-write
       STATUS obsolete
       DESCRIPTION
           "Sets the V.34 modem transport method "
       ::= {acDefaultChannelSettings 16}



     acChDefaultFaxModemBypassCoderType OBJECT-TYPE
       SYNTAX INTEGER {
                  g711Alaw-64(0)
,
                  g711Mulaw(1)
,
                  g726-32(4)
,
                  g726-40(5)

                  }
       MAX-ACCESS read-write
       STATUS obsolete
       DESCRIPTION
           "The User can set the bypass coder (according to the known coders)"
       ::= {acDefaultChannelSettings 17}



     acChDefaultFaxRelayRedundancyDepth OBJECT-TYPE
       SYNTAX INTEGER (0..2)
       MAX-ACCESS read-write
       STATUS obsolete
       DESCRIPTION
           " Default: Fax Relay Redundancy Depth. 
  Number of repetitions to be applied to each fax relay payload 
  when transmitting to network."
       ::= {acDefaultChannelSettings 18}



     acChDefaultT38ProtectionMode OBJECT-TYPE
       SYNTAX INTEGER {
                  redundancyPackets(0)
,
                  fEC(1)

                  }
       MAX-ACCESS read-write
       STATUS obsolete
       DESCRIPTION
           " Default: T38 Protection Mode. 
  Use Forward Error Correction (FEC) algorithm 
  to protect T.38 fax relay stream."
       ::= {acDefaultChannelSettings 19}



     acChDefaultDTMFVolume OBJECT-TYPE
       SYNTAX INTEGER (-31..0)
       MAX-ACCESS read-write
       STATUS obsolete
       DESCRIPTION
           "DTMF generation Volume Control"
       ::= {acDefaultChannelSettings 20}



     acChDefaultDTMFTransportType OBJECT-TYPE
       SYNTAX INTEGER {
                  acMuteDTMF(0)
,
                  acRelayDTMF(1)
,
                  acTransparentDTMF(2)
,
                  acRFC2833RalayDTMF(3)
,
                  acRFC2833RelayDecoderMute(7)

                  }
       MAX-ACCESS read-write
       STATUS obsolete
       DESCRIPTION
           "0 = Mute = erases digit from voice stream does not relay to remote.
2 = Transparent = digits remains in voice stream.
3 = RFC 2833 relay = erase digit from voice stream relay to remote using RFC 2833 syntax. 
The other values as seen in the Value List (1 and 7) are not supported as of  version 4.4."
       ::= {acDefaultChannelSettings 21}



     acChDefaultMFTransportType OBJECT-TYPE
       SYNTAX INTEGER {
                  acMuteMF(0)
,
                  acRelayMF(1)
,
                  acTransparentMF(2)
,
                  acRFC2833RalayMF(3)

                  }
       MAX-ACCESS read-write
       STATUS obsolete
       DESCRIPTION
           "0 = erase MFs from voice transport not relayed to remote.
2 = MFs not erased not relayed to remote.
3 = MFs are muted from the voice stream & relayed according to RFC 2833."
       ::= {acDefaultChannelSettings 22}



     acChDefaultInputGain OBJECT-TYPE
       SYNTAX INTEGER (-32..31)
       MAX-ACCESS read-write
       STATUS obsolete
       DESCRIPTION
           "PCM input gain. The range is 31 dB to +31 dB in 1 dB steps."
       ::= {acDefaultChannelSettings 23}



     acChDefaultRTPRedundancyDepth OBJECT-TYPE
       SYNTAX INTEGER {
                  disable(0)
,
                  enable(1)

                  }
       MAX-ACCESS read-write
       STATUS obsolete
       DESCRIPTION
           "Enables or disables generation of RFC 2198 redundancy packets."
       ::= {acDefaultChannelSettings 24}



     acChDefaultTestMode OBJECT-TYPE
       SYNTAX INTEGER {
                  coderLoopback(0)
,
                  pCMLoopback(1)
,
                  toneInjection(2)
,
                  noLoopback(3)

                  }
       MAX-ACCESS read-write
       STATUS obsolete
       DESCRIPTION
           "Testing mode applied.
0 = Coder Loopback performs an encoder/decoder loopback inside DSP device.
1 = PCMLoopback loops back incoming PCM to the outgoing PCM.
2 = ToneInjection generates a 1000 Hz tone to outgoing PCM.
3 = NoLoopback sets the channel to work in normal mode. "
       ::= {acDefaultChannelSettings 25}



     acChDefaultVoiceVolume OBJECT-TYPE
       SYNTAX INTEGER (-32..31)
       MAX-ACCESS read-write
       STATUS obsolete
       DESCRIPTION
           "Voice  output gain control
the range is -31 dB to +31 dB in 1 dB steps
-32 = mute. "
       ::= {acDefaultChannelSettings 26}



     acChDefaultM OBJECT-TYPE
       SYNTAX INTEGER (1..12)
       MAX-ACCESS read-write
       STATUS obsolete
       DESCRIPTION
           "Number of DSP payloads for generating one RTP packet"
       ::= {acDefaultChannelSettings 27}



     acChDefaultFlashHookPeriod OBJECT-TYPE
       SYNTAX INTEGER (0..65535)
       MAX-ACCESS read-write
       STATUS obsolete
       DESCRIPTION
           "Flash hook period."
       ::= {acDefaultChannelSettings 28}



     acChDefaultDTMFDetectionPoint OBJECT-TYPE
       SYNTAX INTEGER (0..1)
       MAX-ACCESS read-write
       STATUS obsolete
       DESCRIPTION
           "Defines if the detection of DTMF events is notified at the end of DTMF or at the start of DTMF."
       ::= {acDefaultChannelSettings 29}



     acChDefaultRtpIpTos OBJECT-TYPE
       SYNTAX INTEGER (0..15)
       MAX-ACCESS read-write
       STATUS obsolete
       DESCRIPTION
           "Sets value of IP Type Of Service field in IP header for all packets generated from this channel. Follow the acTIPTOS enumeration."
       ::= {acDefaultChannelSettings 30}



     acChDefaultRtpIpPrecedence OBJECT-TYPE
       SYNTAX INTEGER (0..7)
       MAX-ACCESS read-write
       STATUS obsolete
       DESCRIPTION
           "Sets value of the IP precedence field in the IP header for all packets generated from this channel. Follow the acTIPPrecedence enumeration."
       ::= {acDefaultChannelSettings 31}



     acChDefaultEchoCancler OBJECT-TYPE
       SYNTAX INTEGER {
                  disable(0)
,
                  enable(1)

                  }
       MAX-ACCESS read-write
       STATUS obsolete
       DESCRIPTION
           "Controls the activation of the Echo Canceler (refer also to 'ForceEchoOff')"
       ::= {acDefaultChannelSettings 32}



     acChDefaultSilenceSuppression OBJECT-TYPE
       SYNTAX INTEGER {
                  sILENCE-COMPRESION-DISABLE(0)
,
                  sILENCE-COMPRESION-ENABLE(1)
,
                  sILENCE-COMPRESION-ENABLE-NOISE-ADAPTATION-DISABLE(2)

                  }
       MAX-ACCESS read-write
       STATUS obsolete
       DESCRIPTION
           "Silence Suppression mode"
       ::= {acDefaultChannelSettings 33}



     acChDefaultEchoCanclerHybridLoss OBJECT-TYPE
       SYNTAX INTEGER {
                  eCHybridLoss6DBM(0)
,
                  eCHybridLoss9DBM(1)
,
                  eCHybridLoss0DBM(2)
,
                  eCHybridLoss3DBM(3)

                  }
       MAX-ACCESS read-write
       STATUS obsolete
       DESCRIPTION
           "Sets worst case ratio between signal level transmitted to hybrid & echo level returning from hybrid. Set this per worst hybrid in the system in terms of echo return loss. Refer to acTECHybridLoss enumeration:"
       ::= {acDefaultChannelSettings 34}



     acChDefaultPacketizationPeriod OBJECT-TYPE
       SYNTAX INTEGER (5..80)
       MAX-ACCESS read-write
       STATUS obsolete
       DESCRIPTION
           "Packetization Period "
       ::= {acDefaultChannelSettings 35}



     -- ****************************************
     -- aTMSettings Configuration
     -- ****************************************
     aTMSettings                   OBJECT IDENTIFIER ::= {boardConfiguration 7}


     vPMask OBJECT-TYPE
       SYNTAX INTEGER (0..255)
       MAX-ACCESS read-write
       STATUS obsolete
       DESCRIPTION
           "VP masking bits used for address resolution"
       ::= {aTMSettings 1}



     vCMask OBJECT-TYPE
       SYNTAX INTEGER (0..2147483647)
       MAX-ACCESS read-write
       STATUS obsolete
       DESCRIPTION
           "VC masking bits used for address resolution"
       ::= {aTMSettings 2}



     externalClk OBJECT-TYPE
       SYNTAX INTEGER {
                  acATMUtopiaExternalClock(1)
,
                  acATMUtopiaInternalClock(0)

                  }
       MAX-ACCESS read-write
       STATUS obsolete
       DESCRIPTION
           "Source clock of on the board UTOPIA bus"
       ::= {aTMSettings 3}



     aTMLoopBack OBJECT-TYPE
       SYNTAX INTEGER {
                   loopbackDisabled(0) 
,
                  loopbackEnabled(1)

                  }
       MAX-ACCESS read-write
       STATUS obsolete
       DESCRIPTION
           "Phy loopback. The loopback can be used for testing purposes. The loopback direction is towards the PSTN side"
       ::= {aTMSettings 4}



     utopiaSlave OBJECT-TYPE
       SYNTAX INTEGER {
                  aTM-UTOPIA-MASTER(0)
,
                  aTM-UTOPIA-SLAVE(1)

                  }
       MAX-ACCESS read-write
       STATUS obsolete
       DESCRIPTION
           "UTOPIA interface mode of bus arbitration"
       ::= {aTMSettings 5}



     multyPhy OBJECT-TYPE
       SYNTAX INTEGER {
                  singlePhy(0) 
,
                  multiPhy(1) 

                  }
       MAX-ACCESS read-write
       STATUS obsolete
       DESCRIPTION
           "UTOPIA interface SinglePhy or MultiPhy mode"
       ::= {aTMSettings 6}



     slavePhyNum OBJECT-TYPE
       SYNTAX INTEGER (-1..31)
       MAX-ACCESS read-write
       STATUS obsolete
       DESCRIPTION
           "Provides the slave number for this device (board) in the UTOPIA system bus (Applies to slave mode only)"
       ::= {aTMSettings 7}



     utopiaBus16 OBJECT-TYPE
       SYNTAX INTEGER {
                  acATMUtopiaBusWidth16bit(0)
,
                  acATMUtopiaBusWidth8bit(1)

                  }
       MAX-ACCESS read-write
       STATUS obsolete
       DESCRIPTION
           "UTOPIA interface mode of bus width"
       ::= {aTMSettings 8}



     aTMPHYType OBJECT-TYPE
       SYNTAX INTEGER {
                  acOC3(0)
,
                  acUtopia(1)

                  }
       MAX-ACCESS read-write
       STATUS obsolete
       DESCRIPTION
           "External interface type of the board "
       ::= {aTMSettings 9}



     disablePayloadScrambling OBJECT-TYPE
       SYNTAX INTEGER {
                  enable(0)
,
                  disable(1) 

                  }
       MAX-ACCESS read-write
       STATUS obsolete
       DESCRIPTION
           "Disable/Enable Cell payload scrambling in the ATM PHY"
       ::= {aTMSettings 10}



     pHYClkSource OBJECT-TYPE
       SYNTAX INTEGER {
                  acPhyInternalClock(0)
,
                  acPhyExternalClock(1)

                  }
       MAX-ACCESS read-write
       STATUS obsolete
       DESCRIPTION
           "OC3 Tx clock source"
       ::= {aTMSettings 11}



     sendIdleCASUponLinkFail OBJECT-TYPE
       SYNTAX INTEGER {
                  acATMSendIdleCASUponLinkFail-Disabled(0)
,
                  acATMSendIdleCASUponLinkFail-Enabled(1)

                  }
       MAX-ACCESS read-write
       STATUS obsolete
       DESCRIPTION
           "This I.366.2 allows sending a special idle CAS packet which signals that the other side has a failure"
       ::= {aTMSettings 12}



     masterSlaveMode OBJECT-TYPE
       SYNTAX INTEGER {
                  acATM-MasterMode-CO-IWF(0)
,
                  acATM-SlaveMode-CP-IWF(1)

                  }
       MAX-ACCESS read-write
       STATUS obsolete
       DESCRIPTION
           "Loop Emulation Mode (vmoa145) Master/Slave mode"
       ::= {aTMSettings 13}



     vccProfile OBJECT-TYPE
       SYNTAX INTEGER {
                  ac240VCCs-8CIDsperVCC(0)
,
                  ac105VCCs-24CIDsperVCC(1)
,
                  ac84VCCs-32CIDsperVCC(2)
,
                  ac14VCCs-240CIDsperVCC(3)

                  }
       MAX-ACCESS read-write
       STATUS obsolete
       DESCRIPTION
           "Determine the required combination of Board's maximal number of VCC and maximal number of channels per VCC"
       ::= {aTMSettings 14}



     tPNCPVPI OBJECT-TYPE
       SYNTAX INTEGER (0..2147483647)
       MAX-ACCESS read-write
       STATUS obsolete
       DESCRIPTION
           "VPI used for transferring TPNCP command over AAL5 transport layer"
       ::= {aTMSettings 15}



     tPNCPVCI OBJECT-TYPE
       SYNTAX INTEGER (0..2147483647)
       MAX-ACCESS read-write
       STATUS obsolete
       DESCRIPTION
           "VCI used for transferring TPNCP command over AAL5 transport layer"
       ::= {aTMSettings 16}



     sAALLink0VPI OBJECT-TYPE
       SYNTAX INTEGER (0..2147483647)
       MAX-ACCESS read-write
       STATUS obsolete
       DESCRIPTION
           "VPI of the 1st SAAL link (number 0)"
       ::= {aTMSettings 17}



     sAALLink0VCI OBJECT-TYPE
       SYNTAX INTEGER (0..2147483647)
       MAX-ACCESS read-write
       STATUS obsolete
       DESCRIPTION
           "VCI of the 1st SAAL link (number 0)"
       ::= {aTMSettings 18}



     sAALLink1VPI OBJECT-TYPE
       SYNTAX INTEGER (0..2147483647)
       MAX-ACCESS read-write
       STATUS obsolete
       DESCRIPTION
           "VPI of the 2nd SAAL link (number 1)"
       ::= {aTMSettings 19}



     sAALLink1VCI OBJECT-TYPE
       SYNTAX INTEGER (0..2147483647)
       MAX-ACCESS read-write
       STATUS obsolete
       DESCRIPTION
           "VCI of the 1st SAAL link (number 1)"
       ::= {aTMSettings 20}



     -- ****************************************
     -- acSS7Settings Configuration
     -- ****************************************
     acSS7Settings                 OBJECT IDENTIFIER ::= {boardConfiguration 8}


     -- ****************************************
     -- acSS7Settings table decleration
     -- ****************************************
     acSS7SettingsTable OBJECT-TYPE
       SYNTAX SEQUENCE OF AcSS7SettingsEntry
       MAX-ACCESS not-accessible
       STATUS obsolete
       DESCRIPTION
           ""
       ::= {acSS7Settings 1}



     -- ****************************************
     -- acSS7Settings table entry
     -- ****************************************
     acSS7SettingsEntry OBJECT-TYPE
       SYNTAX AcSS7SettingsEntry
       MAX-ACCESS not-accessible
       STATUS obsolete
       DESCRIPTION
           ""
       INDEX {acSS7LinkId}
       ::= {acSS7SettingsTable 1}



     -- ****************************************
     -- acSS7Settings TABLE
     -- ****************************************
     AcSS7SettingsEntry ::= SEQUENCE {
       acSS7LinkId                                     INTEGER,
       acSS7traceLevel                                 INTEGER
     }



     acSS7LinkId OBJECT-TYPE
       SYNTAX INTEGER (0..8)
       MAX-ACCESS read-write
       STATUS obsolete
       DESCRIPTION
           "SS7 Link Id."
       ::= {acSS7SettingsEntry 1}



     acSS7traceLevel OBJECT-TYPE
       SYNTAX INTEGER {
                  acNO-TRACE(0)
,
                  acFULL-TRACE(1)
,
                  acISDN-IUA-TRACE(9)
,
                  acSS7-MTP2(10)
,
                  acSS7-MTP2-AND-APPLI(11)
,
                  acSS7-MTP2-SL-L3-NO-MSU(12)
,
                  acSS7-AAL(15)

                  }
       MAX-ACCESS read-write
       STATUS obsolete
       DESCRIPTION
           "."
       ::= {acSS7SettingsEntry 2}



     -- ****************************************
     -- acConfigFiles Configuration
     -- ****************************************
     acConfigFiles                 OBJECT IDENTIFIER ::= {boardConfiguration 11}


     acFxsCoefficients  OBJECT-TYPE
       SYNTAX OCTET STRING (SIZE (0..255))
       MAX-ACCESS read-only
       STATUS obsolete
       DESCRIPTION
           "The FXS coefficient file name."
       ::= {acConfigFiles 1}



     acFxoCoefficients OBJECT-TYPE
       SYNTAX OCTET STRING (SIZE (0..255))
       MAX-ACCESS read-only
       STATUS obsolete
       DESCRIPTION
           "The FXO coefficient file name."
       ::= {acConfigFiles 2}



     acCptFile OBJECT-TYPE
       SYNTAX OCTET STRING (SIZE (0..255))
       MAX-ACCESS read-only
       STATUS obsolete
       DESCRIPTION
           "."
       ::= {acConfigFiles 3}



     acVpFile OBJECT-TYPE
       SYNTAX OCTET STRING (SIZE (0..255))
       MAX-ACCESS read-only
       STATUS obsolete
       DESCRIPTION
           "The name (and path) of the file containing the voice prompts"
       ::= {acConfigFiles 4}



     -- ****************************************
     -- acCasTables Configuration
     -- ****************************************
     acCasTables                   OBJECT IDENTIFIER ::= {acConfigFiles 21}


     -- ****************************************
     -- acCasTables table decleration
     -- ****************************************
     acCasTablesTable OBJECT-TYPE
       SYNTAX SEQUENCE OF AcCasTablesEntry
       MAX-ACCESS not-accessible
       STATUS obsolete
       DESCRIPTION
           ""
       ::= {acCasTables 1}



     -- ****************************************
     -- acCasTables table entry
     -- ****************************************
     acCasTablesEntry OBJECT-TYPE
       SYNTAX AcCasTablesEntry
       MAX-ACCESS not-accessible
       STATUS obsolete
       DESCRIPTION
           ""
       INDEX {acCasTableIndex}
       ::= {acCasTablesTable 1}



     -- ****************************************
     -- acCasTables TABLE
     -- ****************************************
     AcCasTablesEntry ::= SEQUENCE {
       acCasTableIndex                                 INTEGER,
       acCasTabeName                                   OCTET STRING
     }



     acCasTableIndex OBJECT-TYPE
       SYNTAX INTEGER (0..7)
       MAX-ACCESS read-only
       STATUS obsolete
       DESCRIPTION
           "Cas Table Indexd"
       ::= {acCasTablesEntry 1}



     acCasTabeName OBJECT-TYPE
       SYNTAX OCTET STRING (SIZE (0..255))
       MAX-ACCESS read-only
       STATUS obsolete
       DESCRIPTION
           "Cas Table Name"
       ::= {acCasTablesEntry 2}



     -- ****************************************
     -- acFxs Configuration
     -- ****************************************
     acFxs                         OBJECT IDENTIFIER ::= {boardConfiguration 12}


     acPolarityReversalType OBJECT-TYPE
       SYNTAX INTEGER {
                  soft(0)
,
                  hard(1)

                  }
       MAX-ACCESS read-write
       STATUS obsolete
       DESCRIPTION
           "Sets the type of the polarity reversal signal used for the network far-end answer and disconnect indications. Smooth reversal prevents negative effects as non-required ringing."
       ::= {acFxs 1}



     -- ****************************************
     -- megacoSettings Configuration
     -- ****************************************
     megacoSettings                OBJECT IDENTIFIER ::= {boardConfiguration 13}


     megacoCurrentProfile OBJECT-TYPE
       SYNTAX INTEGER (1..8191)
       MAX-ACCESS read-write
       STATUS obsolete
       DESCRIPTION
           "Use this parameter to MGCP/MEGACO beheviour for specific compatibility. See user manual."
       ::= {megacoSettings 1}



     megacoGatewayName OBJECT-TYPE
       SYNTAX OCTET STRING (SIZE (0..64))
       MAX-ACCESS read-write
       STATUS obsolete
       DESCRIPTION
           "MGCP:Gateway's identification name towards the MGCP Call Agent. If empty Gateway name holds the IP address of the board
MEGACO: Prefix of the gateway part of the termination name"
       ::= {megacoSettings 2}



     megacoEndpointName OBJECT-TYPE
       SYNTAX OCTET STRING (SIZE (0..20))
       MAX-ACCESS read-write
       STATUS obsolete
       DESCRIPTION
           "Megaco Endpoint Name"
       ::= {megacoSettings 3}



     megacoTrunkName OBJECT-TYPE
       SYNTAX OCTET STRING (SIZE (0..20))
       MAX-ACCESS read-write
       STATUS obsolete
       DESCRIPTION
           "MGCP: Together with 'EndpointPrefix' field generates local endpoint name on trunk enabled gateways
MEGACO: Prefix of the trunk part of the termination name"
       ::= {megacoSettings 4}



     megacoActiveCallAgentIp OBJECT-TYPE
       SYNTAX OCTET STRING (SIZE (0..20))
       MAX-ACCESS read-only
       STATUS obsolete
       DESCRIPTION
           "Megaco Active Call Agent "
       ::= {megacoSettings 5}



     megacoActiveCallAgentPort OBJECT-TYPE
       SYNTAX INTEGER (0..32767)
       MAX-ACCESS read-only
       STATUS obsolete
       DESCRIPTION
           "Megaco Active Port"
       ::= {megacoSettings 6}



     megacoCheckLegalityOfMGC OBJECT-TYPE
       SYNTAX INTEGER {
                  disable(0)
,
                  enable(1)

                  }
       MAX-ACCESS read-write
       STATUS obsolete
       DESCRIPTION
           "This parameter specified if the MEGACO will reject commands from an MGC not in the provisioned list "
       ::= {megacoSettings 8}



     -- ****************************************
     -- megacoCallAgents Configuration
     -- ****************************************
     megacoCallAgents              OBJECT IDENTIFIER ::= {megacoSettings 7}


     -- ****************************************
     -- megacoCallAgents table decleration
     -- ****************************************
     megacoCallAgentsTable OBJECT-TYPE
       SYNTAX SEQUENCE OF MegacoCallAgentsEntry
       MAX-ACCESS not-accessible
       STATUS obsolete
       DESCRIPTION
           "Magaco Call agents Table"
       ::= {megacoCallAgents 1}



     -- ****************************************
     -- megacoCallAgents table entry
     -- ****************************************
     megacoCallAgentsEntry OBJECT-TYPE
       SYNTAX MegacoCallAgentsEntry
       MAX-ACCESS not-accessible
       STATUS obsolete
       DESCRIPTION
           ""
       INDEX {megacoCallAgentId}
       ::= {megacoCallAgentsTable 1}



     -- ****************************************
     -- megacoCallAgents TABLE
     -- ****************************************
     MegacoCallAgentsEntry ::= SEQUENCE {
       megacoCallAgentId                               INTEGER,
       megacoCallAgentIp                               OCTET STRING,
       megacoCallAgentPort                             INTEGER,
       megacoCallAgentIsUsed                           INTEGER
     }



     megacoCallAgentId OBJECT-TYPE
       SYNTAX INTEGER (0..4)
       MAX-ACCESS read-only
       STATUS obsolete
       DESCRIPTION
           "Megaco Call Agent Id"
       ::= {megacoCallAgentsEntry 1}



     megacoCallAgentIp OBJECT-TYPE
       SYNTAX OCTET STRING (SIZE (0..20))
       MAX-ACCESS read-write
       STATUS obsolete
       DESCRIPTION
           "Megaco CallAgent IP"
       ::= {megacoCallAgentsEntry 2}



     megacoCallAgentPort OBJECT-TYPE
       SYNTAX INTEGER (0..32767)
       MAX-ACCESS read-write
       STATUS obsolete
       DESCRIPTION
           "List of up to 10 UDP Ports of MEGACO Call Agent separated by , or ;."
       ::= {megacoCallAgentsEntry 3}



     megacoCallAgentIsUsed OBJECT-TYPE
       SYNTAX INTEGER {
                  no(0)
,
                  yes(1)

                  }
       MAX-ACCESS read-write
       STATUS obsolete
       DESCRIPTION
           "Is this index used"
       ::= {megacoCallAgentsEntry 4}



     -- ****************************************
     -- acPSTNParameters Configuration
     -- ****************************************
     acPSTNParameters              OBJECT IDENTIFIER ::= {boardConfiguration 14}


     acQ931RELAYMODE OBJECT-TYPE
       SYNTAX INTEGER {
                  none(0)
,
                  activateLAPDmessaging (1)
,
                  layer3-IS-IUA (3)

                  }
       MAX-ACCESS read-write
       STATUS obsolete
       DESCRIPTION
           "ISDN level 3 mode"
       ::= {acPSTNParameters 1}



     acIsdnDuplicateQ931BuffMode OBJECT-TYPE
       SYNTAX INTEGER (0..255)
       MAX-ACCESS read-write
       STATUS obsolete
       DESCRIPTION
           "Activates / de-activates delivery of raw Q.931 messages.
This Object is obsolete and is replaces by acTrunkISDNCommonDuplicateQ931BuffMode in the acPSTN-MIB."
       ::= {acPSTNParameters 2}



     acPSTNCASTableNum OBJECT-TYPE
       SYNTAX INTEGER (0..8)
       MAX-ACCESS read-only
       STATUS obsolete
       DESCRIPTION
           "Indicates how many CAS protocol configuration files are loaded, when 0 is no CAS table. It should match the number of fields."
       ::= {acPSTNParameters 3}



     -- ****************************************
     -- aMsConfiguration Configuration
     -- ****************************************
     aMsConfiguration              OBJECT IDENTIFIER ::= {boardConfiguration 51}


     amsNumOfConferencePorts  OBJECT-TYPE
       SYNTAX INTEGER (0..480)
       MAX-ACCESS read-write
       STATUS obsolete
       DESCRIPTION
           "Number Of Conference ports.  How many ports on the TPM are allocated to the conferencing service."
       ::= {aMsConfiguration 1}



     amsNumOfTestTrunkPorts OBJECT-TYPE
       SYNTAX INTEGER (0..480)
       MAX-ACCESS read-write
       STATUS obsolete
       DESCRIPTION
           "Number Of Test Trunk ports.  How many ports on the TPM are allocated to the Test Trunk service."
       ::= {aMsConfiguration 2}



     amsNumOfLawfulInterceptPorts OBJECT-TYPE
       SYNTAX INTEGER (0..480)
       MAX-ACCESS read-write
       STATUS obsolete
       DESCRIPTION
           "Number Of Test Trunk ports.  How many ports on the TPM are allocated to the Lawful Intercept service."
       ::= {aMsConfiguration 3}



     amsNumOfAnnouncementPorts OBJECT-TYPE
       SYNTAX INTEGER (0..480)
       MAX-ACCESS read-write
       STATUS obsolete
       DESCRIPTION
           "Number Of Test Trunk ports.  How many ports on the TPM are allocated to the Announcement service."
       ::= {aMsConfiguration 4}



     amsApsIpAddress OBJECT-TYPE
       SYNTAX IpAddress
       MAX-ACCESS read-write
       STATUS obsolete
       DESCRIPTION
           "Sets the destination IP to which the heartbeat packets are sent."
       ::= {aMsConfiguration 5}



     amsApsPort OBJECT-TYPE
       SYNTAX INTEGER (0..64000)
       MAX-ACCESS read-write
       STATUS obsolete
       DESCRIPTION
           "Sets the destination UDP port to which the heartbeat packets are sent."
       ::= {aMsConfiguration 6}



     amsPrimaryLanguage OBJECT-TYPE
       SYNTAX INTEGER {
                  isoLangBasque(15)
,
                  amsLangBelgianDutch(0)
,
                  amsLangCantonese(1)
,
                  isoLangCatalan(16)
,
                  isoLangCzech(19)
,
                  isoLangDutch(10)
,
                  isoLangEnglish(2)
,
                  isoLangFrench(3)
,
                  isoLangGallegan(17)
,
                  isoLangGerman(4)
,
                  isoLangGreek(20)
,
                  isoLangHebrew(18)
,
                  isoLangJapanese(6)
,
                  isoLangItalian(5)
,
                  isoLangKorean(7)
,
                  isoLangMalay(8)
,
                  isoLangMandarin(9)
,
                  isoLangPortuguese(11)
,
                  isoLangSpanish(12)
,
                  isoLangTagalog(13)
,
                  isoLangThai(14)
,
                  isoLangTurkish(21)
,
                  isoLangVietnamese(22)
,
                  amsLangBad(100)

                  }
       MAX-ACCESS read-write
       STATUS obsolete
       DESCRIPTION
           "Primary Language"
       ::= {aMsConfiguration 7}



     amsSecondaryLanguage OBJECT-TYPE
       SYNTAX INTEGER {
                  isoLangBasque(15)
,
                  amsLangBelgianDutch(0)
,
                  amsLangCantonese(1)
,
                  isoLangCatalan(16)
,
                  isoLangCzech(19)
,
                  isoLangDutch(10)
,
                  isoLangEnglish(2)
,
                  isoLangFrench(3)
,
                  isoLangGallegan(17)
,
                  isoLangGerman(4)
,
                  isoLangGreek(20)
,
                  isoLangHebrew(18)
,
                  isoLangJapanese(6)
,
                  isoLangItalian(5)
,
                  isoLangKorean(7)
,
                  isoLangMalay(8)
,
                  isoLangMandarin(9)
,
                  isoLangPortuguese(11)
,
                  isoLangSpanish(12)
,
                  isoLangTagalog(13)
,
                  isoLangThai(14)
,
                  isoLangTurkish(21)
,
                  isoLangVietnamese(22)
,
                  amsLangBad(100)

                  }
       MAX-ACCESS read-write
       STATUS obsolete
       DESCRIPTION
           "Secondary  Language"
       ::= {aMsConfiguration 8}



     amsProfile OBJECT-TYPE
       SYNTAX INTEGER (0..32)
       MAX-ACCESS read-write
       STATUS obsolete
       DESCRIPTION
           "AMS Profile Bit Mask: 
1'st bit - APS Audio Enable/Disable
2'nd bit - Trunks Interface On/Off
3'td bit - Board Operation State change on ATM Port failure Enable/Disable."
       ::= {aMsConfiguration 9}



     amsAASPackagesProfile OBJECT-TYPE
       SYNTAX INTEGER {
                  td5Starndard(0)
,
                   h2489Standard(1)

                  }
       MAX-ACCESS read-write
       STATUS obsolete
       DESCRIPTION
           "."
       ::= {aMsConfiguration 10}



     -- ****************************************
     -- acFeatureKey Configuration
     -- ****************************************
     acFeatureKey                  OBJECT IDENTIFIER ::= {boardConfiguration 90}


     acFeatureKeyString OBJECT-TYPE
       SYNTAX OCTET STRING (SIZE (0..256))
       MAX-ACCESS read-write
       STATUS obsolete
       DESCRIPTION
           "Coded Key specific for board and required features."
       ::= {acFeatureKey 1}



     acActiveFeaturesList OBJECT-TYPE
       SYNTAX OCTET STRING (SIZE (0..484))
       MAX-ACCESS read-only
       STATUS obsolete
       DESCRIPTION
           "List of all avtivated features."
       ::= {acFeatureKey 2}



     -- ****************************************
     -- supplementary Configuration
     -- ****************************************
     supplementary                 OBJECT IDENTIFIER ::= {boardConfiguration 99}


     supplementaryField OBJECT-TYPE
       SYNTAX OCTET STRING (SIZE (0..255))
       MAX-ACCESS read-write
       STATUS obsolete
       DESCRIPTION
           "Flexible INI file line."
       ::= {supplementary 1}



     -- ****************************************
     -- boardInformation Configuration
     -- ****************************************
     boardInformation              OBJECT IDENTIFIER ::= {acBoard 2}


     boardType OBJECT-TYPE
       SYNTAX INTEGER {
                  unKnownBoard(0)
,
                  tP-08(1)
,
                  mEDIAPACK-108(2)
,
                  mEDIAPACK-124(3)
,
                  tP-240(8)
,
                  tP-610-CL120(10)
,
                  tP-600(11)
,
                  tP-600-IPMEDIA(12)
,
                  tP-9800-C(13)
,
                  tPM800(16)
,
                  tPM800-RDK(17)
,
                  tPM800B(18)
,
                  tPM800B-RDK(19)
,
                  tP1600(20)
,
                  tP-240-IpMedia(21)
,
                  tPM1100(22)
,
                  trunkPack-260-IpMedia(23)
,
                  tP1610(24)
,
                  mP-104(25)
,
                  mP-102(26)
,
                  tP-04(27)
,
                  tP-02(28)
,
                  tP-1610-SB(29)
,
                  tP-1610-IpMedia(30)
,
                  tP-MEDIANT2000(31)
,
                  tP-STRETTO2000(32)
,
                  tP-IPMServer2000(33)
,
                  tP-2810(34)
,
                  tP-260-UN-IpMedia(35)
,
                  tP-260-IpMedia-30Ch(36)
,
                  tP-260-IpMedia-60Ch(37)
,
                  tP-260-IpMedia-120Ch(38)
,
                  tP-260RT-IpMedia-30Ch(39)
,
                  tP-260RT-IpMedia-60Ch(40)
,
                  tP-260RT-IpMedia-120Ch(41)
,
                  tP-260(42)
,
                  tP-260-UN(43)
,
                  tPM1100-PCM(44)
,
                  tP-6310(45)
,
                  tPM6300(46)
,
                  mediant1000(47)
,
                  ipMedia3000(48)
,
                  mediant3000(49)
,
                  stretto3000(50)
,
                  tP-6310-IpMedia(51)
,
                  tP-6310-SB(52)
,
                  aTP-1610(53)
,
                  aTP-260(54)
,
                  aTP-260-UN(55)
,
                  mP-118(56)

                  }
       MAX-ACCESS read-only
       STATUS obsolete
       DESCRIPTION
           "The type of the Board."
       ::= {boardInformation 1}



     boardName OBJECT-TYPE
       SYNTAX OCTET STRING (SIZE (0..20))
       MAX-ACCESS read-only
       STATUS obsolete
       DESCRIPTION
           "The name fo the board"
       ::= {boardInformation 2}



     serialNum OBJECT-TYPE
       SYNTAX INTEGER (0..2147483647)
       MAX-ACCESS read-only
       STATUS obsolete
       DESCRIPTION
           "serial number of board."
       ::= {boardInformation 3}



     dSPCount OBJECT-TYPE
       SYNTAX INTEGER (0..2147483647)
       MAX-ACCESS read-only
       STATUS obsolete
       DESCRIPTION
           "DSP Count"
       ::= {boardInformation 4}



     channelsCount OBJECT-TYPE
       SYNTAX INTEGER (0..2147483647)
       MAX-ACCESS read-only
       STATUS obsolete
       DESCRIPTION
           "Channel Count."
       ::= {boardInformation 5}



     cPUSpeed OBJECT-TYPE
       SYNTAX INTEGER (0..2147483647)
       MAX-ACCESS read-only
       STATUS obsolete
       DESCRIPTION
           "CPU Speed"
       ::= {boardInformation 6}



     softwareVersion OBJECT-TYPE
       SYNTAX OCTET STRING (SIZE (0..20))
       MAX-ACCESS read-only
       STATUS obsolete
       DESCRIPTION
           "TrunkPack Software Version"
       ::= {boardInformation 7}



     trunkPackSoftwareDate OBJECT-TYPE
       SYNTAX OCTET STRING (SIZE (0..40))
       MAX-ACCESS read-only
       STATUS obsolete
       DESCRIPTION
           "TrunkPack Software Date"
       ::= {boardInformation 8}



     slotNumber OBJECT-TYPE
       SYNTAX INTEGER (0..2147483647)
       MAX-ACCESS read-only
       STATUS obsolete
       DESCRIPTION
           "Slot number"
       ::= {boardInformation 9}



     iniFileVersion OBJECT-TYPE
       SYNTAX INTEGER (0..2147483647)
       MAX-ACCESS read-only
       STATUS obsolete
       DESCRIPTION
           "Ini file version."
       ::= {boardInformation 10}



     acDspType OBJECT-TYPE
       SYNTAX INTEGER (0..2147483647)
       MAX-ACCESS read-only
       STATUS obsolete
       DESCRIPTION
           "Dsp Type"
       ::= {boardInformation 11}



     acFlashVersion OBJECT-TYPE
       SYNTAX INTEGER (0..2147483647)
       MAX-ACCESS read-only
       STATUS obsolete
       DESCRIPTION
           "Flash [BootLoader] Version. "
       ::= {boardInformation 12}



     acBoardFxsOrFxo OBJECT-TYPE
       SYNTAX INTEGER {
                  fXO (0)
,
                  fXS (1)

                  }
       MAX-ACCESS read-only
       STATUS obsolete
       DESCRIPTION
           "Board is Fxs Or Fxo"
       ::= {boardInformation 13}



     acTrunkslCount OBJECT-TYPE
       SYNTAX INTEGER (0..2147483647)
       MAX-ACCESS read-only
       STATUS obsolete
       DESCRIPTION
           "Trunks Count."
       ::= {boardInformation 14}



     acDspVersionTemplate OBJECT-TYPE
       SYNTAX INTEGER (0..2147483647)
       MAX-ACCESS read-only
       STATUS obsolete
       DESCRIPTION
           "selects the DSP load number, which defines the supported set of coders. 
Default=0

Each template assigns a specific version to each DSP. 
Each DSP version supports a set of coders and features. 

The number of channels supported by the DSP can also vary between DSP versions.
 The total number of channels supported by the board depends on the selected template. "
       ::= {boardInformation 15}



     acFirstPortDuplexMode OBJECT-TYPE
       SYNTAX INTEGER {
                  halfDuplex(0)
,
                  fullDuplex(1)
,
                  forceModeValue(2)
,
                  notAvailable(3)

                  }
       MAX-ACCESS read-only
       STATUS obsolete
       DESCRIPTION
           "full-duplex or half-duplex connection"
       ::= {boardInformation 16}



     acFirstPortSpeed OBJECT-TYPE
       SYNTAX INTEGER {
                  forceModeValue(2)
,
                  notAvailable(3)
,
                  ac10Mbps(10)
,
                  ac100Mbps(100)

                  }
       MAX-ACCESS read-only
       STATUS obsolete
       DESCRIPTION
           "."
       ::= {boardInformation 17}



     acMeanFreeChannels OBJECT-TYPE
       SYNTAX INTEGER (0..2147483647)
       MAX-ACCESS read-only
       STATUS obsolete
       DESCRIPTION
           "Mean of Free Channels"
       ::= {boardInformation 18}



     acMaxFreeChannels OBJECT-TYPE
       SYNTAX INTEGER (0..2147483647)
       MAX-ACCESS read-only
       STATUS obsolete
       DESCRIPTION
           "Max of Free Channels"
       ::= {boardInformation 19}



     acSysUpTime OBJECT-TYPE
       SYNTAX INTEGER (0..2147483647)
       MAX-ACCESS read-only
       STATUS obsolete
       DESCRIPTION
           "Time (in Seconds) that the board is alive."
       ::= {boardInformation 20}



     acPhysicalModCount OBJECT-TYPE
       SYNTAX INTEGER {
                  soloist (0)
,
                  second(1)
,
                  first(2)

                  }
       MAX-ACCESS read-only
       STATUS obsolete
       DESCRIPTION
           "."
       ::= {boardInformation 21}



     acBoardTemperature OBJECT-TYPE
       SYNTAX INTEGER (0..100)
       MAX-ACCESS read-only
       STATUS obsolete
       DESCRIPTION
           "Temperature of the board in degrees Celsius, should not go higher then 60!"
       ::= {boardInformation 22}



     -- ****************************************
     -- channelConfiguration Configuration
     -- ****************************************
     channelConfiguration          OBJECT IDENTIFIER ::= {acBoard 3}


     -- ****************************************
     -- voiceSettings Configuration
     -- ****************************************
     voiceSettings                 OBJECT IDENTIFIER ::= {channelConfiguration 2}


     -- ****************************************
     -- voiceSettings table decleration
     -- ****************************************
     voiceSettingsTable OBJECT-TYPE
       SYNTAX SEQUENCE OF VoiceSettingsEntry
       MAX-ACCESS not-accessible
       STATUS obsolete
       DESCRIPTION
           "Data in voice SettingsTable uniquely identify a voice parameters of channel."
       ::= {voiceSettings 1}



     -- ****************************************
     -- voiceSettings table entry
     -- ****************************************
     voiceSettingsEntry OBJECT-TYPE
       SYNTAX VoiceSettingsEntry
       MAX-ACCESS not-accessible
       STATUS obsolete
       DESCRIPTION
           ""
       INDEX {cID}
       ::= {voiceSettingsTable 1}



     -- ****************************************
     -- voiceSettings TABLE
     -- ****************************************
     VoiceSettingsEntry ::= SEQUENCE {
       cID                                             INTEGER,
       coder                                           INTEGER,
       eCE                                             INTEGER,
       sCE                                             INTEGER,
       pFE                                             INTEGER,
       hPFE                                            INTEGER,
       testMode                                        INTEGER,
       voiceVolume                                     INTEGER,
       inputGain                                       INTEGER,
       m                                               INTEGER,
       rTPRedundancyDepth                              INTEGER,
       eCLength                                        INTEGER,
       eCHybridLoss                                    INTEGER
     }



     cID OBJECT-TYPE
       SYNTAX INTEGER (0..2147483647)
       MAX-ACCESS read-only
       STATUS deprecated
       DESCRIPTION
           "Channel ID"
       ::= {voiceSettingsEntry 1}



     coder OBJECT-TYPE
       SYNTAX INTEGER {
                  g711Alaw(0)
,
                  g711Mulaw(1)
,
                  g726-16(2)
,
                  g726-24(3)
,
                  g726-32(4)
,
                  g726-40(5)
,
                  g727-16(6)
,
                  g727-24-16(7)
,
                  g727-24(8)
,
                  g727-32-16(9)
,
                  g727-32-24(10)
,
                  g727-32(11)
,
                  g727-40-16(12)
,
                  g727-40-24(13)
,
                  g727-40-32(14)
,
                  g723Low(15)
,
                  g723High(16)
,
                  g729(17)
,
                  gSM(19)
,
                  gSM610MS(20)
,
                   transparent(22)
,
                  g728(23)
,
                  hDLCCoder(24)
,
                  netCoder-4-8(25)
,
                  netCoder-5-6(26)
,
                  netCoder-6-4(27)
,
                  netCoder-7-2(28)
,
                  netCoder-8(29)
,
                  netCoder-8-8(30)
,
                  netCoder-9-6(31)
,
                  eVRC(32)
,
                  eVRC-TFO(33)
,
                  qCELP-8(34)
,
                  qCELP-8-TFO(35)
,
                  qCELP-13(36)
,
                  qCELP-13-TFO(37)
,
                  noCoder(40)
,
                  modemAnswer(41)
,
                  modemCall(42)
,
                  g711Alaw-5-5(45)
,
                  g711Mulaw-5-5(46)
,
                  g726-32-5-5(47)
,
                  aMR-4-75(50)
,
                  aMR-5-15(51)
,
                   aMR-5-9(52)
,
                  aMR-6-7(53)
,
                  aMR-7-4(54)
,
                  aMR-7-95(55)
,
                  aMR-10-2(56)
,
                  aMR-12-2(57)
,
                  iLBC-15(63)
,
                  iLBC-13(64)
,
                  bV-16(65)
,
                  acAMRWB-6-6(66)
,
                  acAMRWB-8-85(67)
,
                  acAMRWB-12-65(68)
,
                  acAMRWB-14-25(69)
,
                  acAMRWB-15-85(70)
,
                  acAMRWB-18-25(71)
,
                  acAMRWB-19-85(72)
,
                  acAMRWB-23-05(73)
,
                  acAMRWB-23-85(74)
,
                  acG722-48K(75)
,
                  acG722-56K(76)
,
                   acG722-64K(77)
,
                  acDPNSSCoder(78)

                  }
       MAX-ACCESS read-only
       STATUS deprecated
       DESCRIPTION
           "Digital voice coder"
       ::= {voiceSettingsEntry 2}



     eCE OBJECT-TYPE
       SYNTAX INTEGER {
                  disable(0)
,
                  enable(1)

                  }
       MAX-ACCESS read-only
       STATUS deprecated
       DESCRIPTION
           "Enable/Disable Echo Canceler"
       ::= {voiceSettingsEntry 3}



     sCE OBJECT-TYPE
       SYNTAX INTEGER {
                  disable(0)
,
                  enable(1)

                  }
       MAX-ACCESS read-only
       STATUS deprecated
       DESCRIPTION
           "Enable/Disable Silence Compresion mechanism"
       ::= {voiceSettingsEntry 4}



     pFE OBJECT-TYPE
       SYNTAX INTEGER {
                  disable(0)
,
                  enable(1)

                  }
       MAX-ACCESS read-only
       STATUS deprecated
       DESCRIPTION
           "Post Filter Enable of the voice coder"
       ::= {voiceSettingsEntry 5}



     hPFE OBJECT-TYPE
       SYNTAX INTEGER {
                  disable(0)
,
                  enable(1)

                  }
       MAX-ACCESS read-only
       STATUS deprecated
       DESCRIPTION
           "High Pass Filter Enabled of the voice coder"
       ::= {voiceSettingsEntry 6}



     testMode OBJECT-TYPE
       SYNTAX INTEGER {
                  coderLoopback(0)
,
                  pCMLoopback(1)
,
                  toneInjection(2)
,
                  noLoopback(3)

                  }
       MAX-ACCESS read-only
       STATUS deprecated
       DESCRIPTION
           "Testing mode to be applied. 
 Valid Range:CoderLoopback will perform an encoder-decoder loopback inside the DSP device, 
  PCMLoopback will loopback the incoming PCM to the outgoing PCM, 
  ToneInjection will generate a1000 Hz tone to outgoing PCM and 
  NoLoopback will set the channel to work in a normal mode. 
  Refer to TTestCode enumeration 
  (default =3= NoLoopBack).
"
       ::= {voiceSettingsEntry 7}



     voiceVolume OBJECT-TYPE
       SYNTAX INTEGER (0..63)
       MAX-ACCESS read-only
       STATUS deprecated
       DESCRIPTION
           "Voice Volume sets the voice decoder’s output gain
  Range: 0-63 corresponding to -31 dB to +31 dB in 1 dB steps"
       ::= {voiceSettingsEntry 8}



     inputGain OBJECT-TYPE
       SYNTAX INTEGER (0..63)
       MAX-ACCESS read-only
       STATUS deprecated
       DESCRIPTION
           "PCM input gain sets the gain at the encoder’s input."
       ::= {voiceSettingsEntry 9}



     m OBJECT-TYPE
       SYNTAX INTEGER (1..12)
       MAX-ACCESS read-only
       STATUS deprecated
       DESCRIPTION
           "This Packet Multiply Factor is the Number of 20 msec payloads 
  (30 msec for G.723) 
  to be used for generating one RTP packet. 
  Range: 1 - Until max Tx/Rx buffer size is reached"
       ::= {voiceSettingsEntry 10}



     rTPRedundancyDepth OBJECT-TYPE
       SYNTAX INTEGER {
                  disable(0)
,
                  enable(1)

                  }
       MAX-ACCESS read-only
       STATUS deprecated
       DESCRIPTION
           "RTP Redundancy Depth.
  Number of repetitions to be applied to each RTP payload 
  when transmitting to network.
   apply redundancy sequence per RFC2198. 
  Valid range:  Disable redundancy packets generation = 0.
  Enable generation of RFC2198 redundancy packets = 1."
       ::= {voiceSettingsEntry 11}



     eCLength OBJECT-TYPE
       SYNTAX INTEGER {
                  eCLength10MSec(0)
,
                  eCLength15Msec(1)
,
                  eCLength20Msec(2)
,
                  eCLength25Msec(3)
,
                  eCLength30Msec(4)
,
                  eCLength35Msec(5)
,
                  eCLength40Msec(6)
,
                  eCLength45Msec(7)
,
                  eCLength50Msec(8)
,
                  eCLength55Msec(9)
,
                  eCLength60Msec(10)

                  }
       MAX-ACCESS read-only
       STATUS deprecated
       DESCRIPTION
           "Length of echo canceler tail to be used
  according to TECLength enumeration. 
  Note that EC length has different length limitations for different boards."
       ::= {voiceSettingsEntry 12}



     eCHybridLoss OBJECT-TYPE
       SYNTAX INTEGER {
                  loss6DB(0)
,
                  loss9DB(1)
,
                  loss0DB(2)
,
                  loss3DB(3)

                  }
       MAX-ACCESS read-only
       STATUS deprecated
       DESCRIPTION
           "Echo Cancler Hybrid Loss.
  sets the worst case ratio between the signal level transmitted to the hybrid
  and the echo level returning from the hybrid.
  User should set this value according to the worst hybrid
  in the system in terms of echo return loss
  according to enum TECHybridLoss enumeration"
       ::= {voiceSettingsEntry 13}



     -- ****************************************
     -- faxModemSettings Configuration
     -- ****************************************
     faxModemSettings              OBJECT IDENTIFIER ::= {channelConfiguration 3}


     -- ****************************************
     -- faxModemSettings table decleration
     -- ****************************************
     faxModemSettingsTable OBJECT-TYPE
       SYNTAX SEQUENCE OF FaxModemSettingsEntry
       MAX-ACCESS not-accessible
       STATUS obsolete
       DESCRIPTION
           "Data in faxModem Settings Table uniquely identify fax and modem parameters  channel."
       ::= {faxModemSettings 1}



     -- ****************************************
     -- faxModemSettings table entry
     -- ****************************************
     faxModemSettingsEntry OBJECT-TYPE
       SYNTAX FaxModemSettingsEntry
       MAX-ACCESS not-accessible
       STATUS obsolete
       DESCRIPTION
           ""
       INDEX {cID}
       ::= {faxModemSettingsTable 1}



     -- ****************************************
     -- faxModemSettings TABLE
     -- ****************************************
     FaxModemSettingsEntry ::= SEQUENCE {
       fAXTransportType                                INTEGER,
       acCallerIDType                                  INTEGER,
       v21ModemTransportType                           INTEGER,
       v22ModemTransportType                           INTEGER,
       v23ModemTransportType                           INTEGER,
       v32ModemTransportType                           INTEGER,
       v34ModemTransportType                           INTEGER,
       faxRelayMaxRate                                 INTEGER,
       modemRelayMaxRate                               INTEGER,
       faxRelayECMEnable                               INTEGER,
       t38FaxRelayProtectionMode                       INTEGER,
       faxRelayRedundancyDepth                         INTEGER,
       enhancedFaxRelayRedundancyDepth                 INTEGER,
       modemRelayRedundancyDepth                       INTEGER,
       faxModemRelayVolume                             INTEGER,
       faxModemBypassCoderType                         INTEGER,
       faxModemBypassM                                 INTEGER,
       useT38orFRF11                                   INTEGER
     }



     fAXTransportType OBJECT-TYPE
       SYNTAX INTEGER {
                  transparent(0)
,
                  relay(1)
,
                  bypass(2)

                  }
       MAX-ACCESS read-only
       STATUS obsolete
       DESCRIPTION
           "FAX Transport Type."
       ::= {faxModemSettingsEntry 1}



     acCallerIDType OBJECT-TYPE
       SYNTAX INTEGER {
                  transparent(0)
,
                  relay(1)
,
                  bypass(2)

                  }
       MAX-ACCESS read-only
       STATUS obsolete
       DESCRIPTION
           "CallerID Type."
       ::= {faxModemSettingsEntry 2}



     v21ModemTransportType OBJECT-TYPE
       SYNTAX INTEGER {
                  transparent(0)
,
                  relay(1)
,
                  bypass(2)

                  }
       MAX-ACCESS read-only
       STATUS obsolete
       DESCRIPTION
           "V21 Modem Transpor tType.
"
       ::= {faxModemSettingsEntry 3}



     v22ModemTransportType OBJECT-TYPE
       SYNTAX INTEGER {
                  transparent(0)
,
                  relay(1)
,
                  bypass(2)

                  }
       MAX-ACCESS read-only
       STATUS obsolete
       DESCRIPTION
           "V22 Modem Transpor tType.
"
       ::= {faxModemSettingsEntry 4}



     v23ModemTransportType OBJECT-TYPE
       SYNTAX INTEGER {
                  transparent(0)
,
                  relay(1)
,
                  bypass(2)

                  }
       MAX-ACCESS read-only
       STATUS obsolete
       DESCRIPTION
           "V23 Modem Transpor tType.
"
       ::= {faxModemSettingsEntry 5}



     v32ModemTransportType OBJECT-TYPE
       SYNTAX INTEGER {
                  transparent(0)
,
                  relay(1)
,
                  bypass(2)

                  }
       MAX-ACCESS read-only
       STATUS obsolete
       DESCRIPTION
           "V32 Modem Transpor tType.
"
       ::= {faxModemSettingsEntry 6}



     v34ModemTransportType OBJECT-TYPE
       SYNTAX INTEGER {
                  transparent(0)
,
                  relay(1)
,
                  bypass(2)

                  }
       MAX-ACCESS read-only
       STATUS obsolete
       DESCRIPTION
           "V34 Modem Transpor tType.
"
       ::= {faxModemSettingsEntry 7}



     faxRelayMaxRate OBJECT-TYPE
       SYNTAX INTEGER {
                  ac2400(0)
,
                  ac4800(1)
,
                  ac7200(2)
,
                  ac9600(3)
,
                  ac12000(4)
,
                  ac14400(5)

                  }
       MAX-ACCESS read-only
       STATUS obsolete
       DESCRIPTION
           "Fax Relay Max Rate
Limits the maximum rate at which fax messages are transmitted. 
Refer to acTFaxModemRelayRate enumeration. 
 (Default =14400 bps).
"
       ::= {faxModemSettingsEntry 8}



     modemRelayMaxRate OBJECT-TYPE
       SYNTAX INTEGER {
                  ac2400(0)
,
                  ac4800(1)
,
                  ac7200(2)
,
                  ac9600(3)
,
                  ac12000(4)
,
                  ac14400(5)

                  }
       MAX-ACCESS read-only
       STATUS obsolete
       DESCRIPTION
           "Modem Relay Max Rate
Limits the maximum rate at which modem relay messages are transmitted. 
  Refer to acTFaxModemRelayRate enumeration. 
  (Default =14400 bps)."
       ::= {faxModemSettingsEntry 9}



     faxRelayECMEnable OBJECT-TYPE
       SYNTAX INTEGER {
                  disable(0)
,
                  enable(1)

                  }
       MAX-ACCESS read-only
       STATUS obsolete
       DESCRIPTION
           "Fax Relay ECM Enable
  Enable using ECM mode during Fax Relay."
       ::= {faxModemSettingsEntry 10}



     t38FaxRelayProtectionMode OBJECT-TYPE
       SYNTAX INTEGER {
                  redundancyPackets(0)
,
                  fEC(1)

                  }
       MAX-ACCESS read-only
       STATUS obsolete
       DESCRIPTION
           "T38 Fax Relay Protection Mode
  Use Forward Error Correction (FEC) algorithm 
  to protect T.38 fax relay stream."
       ::= {faxModemSettingsEntry 11}



     faxRelayRedundancyDepth OBJECT-TYPE
       SYNTAX INTEGER (0..4)
       MAX-ACCESS read-only
       STATUS obsolete
       DESCRIPTION
           "Fax Relay Redundancy Depth
Number of repetitions to be applied to each fax relay payload 
  when transmitting to network (applicable only when acTFaxModemCmdacTFaxModemSettings.T38FaxRelayProtectionMode=0).
"
       ::= {faxModemSettingsEntry 12}



     enhancedFaxRelayRedundancyDepth OBJECT-TYPE
       SYNTAX INTEGER (0..4)
       MAX-ACCESS read-only
       STATUS obsolete
       DESCRIPTION
           "Enhanced Fax Relay Redundancy Depth
 Number of repetitions to be applied to control packets when using T.38 standard."
       ::= {faxModemSettingsEntry 13}



     modemRelayRedundancyDepth OBJECT-TYPE
       SYNTAX INTEGER {
                  disable(0)
,
                  enable(1)

                  }
       MAX-ACCESS read-only
       STATUS obsolete
       DESCRIPTION
           "Modem Relay Redundancy Depth
Number of repetitions to be applied to each modem relay payload 
when transmitting to network."
       ::= {faxModemSettingsEntry 14}



     faxModemRelayVolume OBJECT-TYPE
       SYNTAX INTEGER (-18..15)
       MAX-ACCESS read-only
       STATUS obsolete
       DESCRIPTION
           "Fax Modem Relay Volume
 Fax gain control. 
  Range: -18 - 15 corresponding to -18.5 dBm to -3.5 dBm in 1 dB steps. 
  The reason the range extends to 15 is for backward compatibility.
  (Default =6)."
       ::= {faxModemSettingsEntry 15}



     faxModemBypassCoderType OBJECT-TYPE
       SYNTAX INTEGER {
                  g711Alaw(0)
,
                  g711Mulaw(1)
,
                  g726-16(2)
,
                  g726-24(3)
,
                  g726-32(4)
,
                  g726-40(5)
,
                  g727-16(6)
,
                  g727-24-16(7)
,
                  g727-24(8)
,
                  g727-32-16(9)
,
                  g727-32-24(10)
,
                  g727-32(11)
,
                  g727-40-16(12)
,
                  g727-40-24(13)
,
                  g727-40-32(14)
,
                  g723Low(15)
,
                  g723High(16)
,
                  g729(17)
,
                  gSM(19)
,
                  gSM610MS(20)
,
                  transparent(22)
,
                  g728(23)
,
                  hDLCCoder(24)
,
                  netCoder-4-8(25)
,
                  netCoder-5-6(26)
,
                  netCoder-6-4(27)
,
                  netCoder-7-2(28)
,
                  netCoder-8(29)
,
                  netCoder-8-8(30)
,
                  netCoder-9-6(31)

                  }
       MAX-ACCESS read-only
       STATUS obsolete
       DESCRIPTION
           "Fax Modem Bypass Coder Type
  Coder to be used while performing fax/modem bypass. 
  Usually, high bit rate coders such as G.711 and G.726/G.727 should be used.
  (Default = G.711 A-law)."
       ::= {faxModemSettingsEntry 16}



     faxModemBypassM OBJECT-TYPE
       SYNTAX INTEGER (0..2147483647)
       MAX-ACCESS read-only
       STATUS obsolete
       DESCRIPTION
           "Fax Modem Bypass M
  Number of 20 msec payloads to be used for generating one RTP fax/modem bypass packet.
  Range: 1 - Until max Tx/Rx buffer size is reached"
       ::= {faxModemSettingsEntry 17}



     useT38orFRF11 OBJECT-TYPE
       SYNTAX INTEGER {
                  fRF11(0)
,
                  t38(1)

                  }
       MAX-ACCESS read-only
       STATUS obsolete
       DESCRIPTION
           "Use T38 or FRF11
  Use T.38 protocol or proprietary FRF.11 syntax, 
  to send/receive fax relay."
       ::= {faxModemSettingsEntry 18}



     -- ****************************************
     -- dJBSettings Configuration
     -- ****************************************
     dJBSettings                   OBJECT IDENTIFIER ::= {channelConfiguration 4}


     -- ****************************************
     -- dJBSettings table decleration
     -- ****************************************
     dJBSettingsTable OBJECT-TYPE
       SYNTAX SEQUENCE OF DJBSettingsEntry
       MAX-ACCESS not-accessible
       STATUS obsolete
       DESCRIPTION
           "Data in dJB Settings Table uniquely identify jitter buffer parameters of channel."
       ::= {dJBSettings 1}



     -- ****************************************
     -- dJBSettings table entry
     -- ****************************************
     dJBSettingsEntry OBJECT-TYPE
       SYNTAX DJBSettingsEntry
       MAX-ACCESS not-accessible
       STATUS obsolete
       DESCRIPTION
           ""
       INDEX {cID}
       ::= {dJBSettingsTable 1}



     -- ****************************************
     -- dJBSettings TABLE
     -- ****************************************
     DJBSettingsEntry ::= SEQUENCE {
       dJBufMinDelay                                   INTEGER,
       dJBufOptFactor                                  INTEGER
     }



     dJBufMinDelay OBJECT-TYPE
       SYNTAX INTEGER (0..150)
       MAX-ACCESS read-only
       STATUS obsolete
       DESCRIPTION
           "[Millisec] Dynamic Jitter Buffer Minimum Delay.
  0 - 150  (default =150)"
       ::= {dJBSettingsEntry 1}



     dJBufOptFactor OBJECT-TYPE
       SYNTAX INTEGER (0..12)
       MAX-ACCESS read-only
       STATUS obsolete
       DESCRIPTION
           "Dynamic Jitter Buffer Optimization Factor.
Dynamic jitter buffer frame error/delay optimization.
0 - 12  (default =7)"
       ::= {dJBSettingsEntry 2}



     -- ****************************************
     -- channelTDMBusSettings Configuration
     -- ****************************************
     channelTDMBusSettings         OBJECT IDENTIFIER ::= {channelConfiguration 5}


     -- ****************************************
     -- channelTDMBusSettings table decleration
     -- ****************************************
     channelTDMBusSettingsTable OBJECT-TYPE
       SYNTAX SEQUENCE OF ChannelTDMBusSettingsEntry
       MAX-ACCESS not-accessible
       STATUS obsolete
       DESCRIPTION
           " Data in channel TDM Bus Settings Table, uniquely identify TDM Bus sparameters of channel
"
       ::= {channelTDMBusSettings 1}



     -- ****************************************
     -- channelTDMBusSettings table entry
     -- ****************************************
     channelTDMBusSettingsEntry OBJECT-TYPE
       SYNTAX ChannelTDMBusSettingsEntry
       MAX-ACCESS not-accessible
       STATUS obsolete
       DESCRIPTION
           ""
       INDEX {cID}
       ::= {channelTDMBusSettingsTable 1}



     -- ****************************************
     -- channelTDMBusSettings TABLE
     -- ****************************************
     ChannelTDMBusSettingsEntry ::= SEQUENCE {
       tDMBusInputPort                                 INTEGER,
       tDMBusInputChannel                              INTEGER,
       tDMBusOutputDisable                             INTEGER,
       tDMBusOutputPort                                INTEGER,
       tDMBusOutputChannel                             INTEGER
     }



     tDMBusInputPort OBJECT-TYPE
       SYNTAX INTEGER (0..127)
       MAX-ACCESS read-only
       STATUS obsolete
       DESCRIPTION
           "TDM Bus Input Port.  
  Together with TDMBusInputChannel, 
  defines the TDM bus timeslot to be used as input for this channel. 
  Note that the valid region for this parameter varies according to the type of TDM bus used.
  When using TDMBusType=acFramers this parameter selects the trunkID, 
  in which the incoming B-channel resides. 0-127. "
       ::= {channelTDMBusSettingsEntry 1}



     tDMBusInputChannel OBJECT-TYPE
       SYNTAX INTEGER (0..31)
       MAX-ACCESS read-only
       STATUS obsolete
       DESCRIPTION
           "TDM Bus Input Channel. 
  Together with TDMBusInputPort, 
  defines the TDM bus timeslot to be used as input for this channel. 
 Note that the valid region for this parameter varies according to the TDMBusSpeed. 
  When using TDMBusType=acFramers, this parameter selects the incoming B-channel 
  (in this case the valid region is 0-31)."
       ::= {channelTDMBusSettingsEntry 2}



     tDMBusOutputDisable OBJECT-TYPE
       SYNTAX INTEGER {
                  disable(0)
,
                  enable(1)

                  }
       MAX-ACCESS read-only
       STATUS obsolete
       DESCRIPTION
           "TDM Bus Output Disable. 
 0: Places TDM bus output timeslot in tri-state mode. 
     Ignored in case of PSTN interface.
 1: Enables TDM bus output timeslot. 
     Ignored in case of PSTN interface."
       ::= {channelTDMBusSettingsEntry 3}



     tDMBusOutputPort OBJECT-TYPE
       SYNTAX INTEGER (0..255)
       MAX-ACCESS read-only
       STATUS obsolete
       DESCRIPTION
           "TDM Bus Output Port. 
Together with TDMBusOutputChannel, defines the TDM bus timeslot 
  to be used as output for this channel. 
 Note that the valid region for this parameter varies according to the type of TDM bus used. 
  When this parameter is set to 0xff=255 the boardwise setting (set in acOpenBoard()) will be used. 
  When using TDMBusType=acFramers, this parameter is ignored.
  0-31 or 255."
       ::= {channelTDMBusSettingsEntry 4}



     tDMBusOutputChannel OBJECT-TYPE
       SYNTAX INTEGER (0..2147483647)
       MAX-ACCESS read-only
       STATUS obsolete
       DESCRIPTION
           "TDM Bus Output Channel. 
 Together with TDMBusOutputPort, defines the TDM bus timeslot 
  to be used as output for this channel. 
 Note that the valid region for this parameter varies according to the TDMBusSpeed. 
 When using TDMBusType=acFramers, this parameter is ignored."
       ::= {channelTDMBusSettingsEntry 5}



     -- ****************************************
     -- transportSettings Configuration
     -- ****************************************
     transportSettings             OBJECT IDENTIFIER ::= {channelConfiguration 6}


     -- ****************************************
     -- transportSettings table decleration
     -- ****************************************
     transportSettingsTable OBJECT-TYPE
       SYNTAX SEQUENCE OF TransportSettingsEntry
       MAX-ACCESS not-accessible
       STATUS obsolete
       DESCRIPTION
           "Data in Transport Table, uniquely identify Transport sparameters of channel."
       ::= {transportSettings 1}



     -- ****************************************
     -- transportSettings table entry
     -- ****************************************
     transportSettingsEntry OBJECT-TYPE
       SYNTAX TransportSettingsEntry
       MAX-ACCESS not-accessible
       STATUS obsolete
       DESCRIPTION
           ""
       INDEX {cID}
       ::= {transportSettingsTable 1}



     -- ****************************************
     -- transportSettings TABLE
     -- ****************************************
     TransportSettingsEntry ::= SEQUENCE {
       useNIorPCI                                      INTEGER,
       disableSoftIPLoopback                           INTEGER,
       uniDirectionalRTP                               INTEGER
     }



     useNIorPCI OBJECT-TYPE
       SYNTAX INTEGER (0..1)
       MAX-ACCESS read-only
       STATUS obsolete
       DESCRIPTION
           "Description: Use NI or PCI interface. 
  =1 if channel will use NI interface, =0 if PCI interface.
  0- PCI interface: Compressed traffic will be sent/received through the PCI interface.
 1- NI interface: RTP-RTCP packets sent/received to/from on board Ethernet interface.
(default=1)."
       ::= {transportSettingsEntry 1}



     disableSoftIPLoopback OBJECT-TYPE
       SYNTAX INTEGER (0..1)
       MAX-ACCESS read-only
       STATUS obsolete
       DESCRIPTION
           "Disable Soft IP Loopback
  =1 in order to diable soft IP loopback. 
  0- Enables the hair pin connection made in case two channels on the same board are connected together.
  1- Disables the hair pin connection made in case two channels on the same board are connected together."
       ::= {transportSettingsEntry 2}



     uniDirectionalRTP OBJECT-TYPE
       SYNTAX INTEGER (0..2147483647)
       MAX-ACCESS read-only
       STATUS obsolete
       DESCRIPTION
           "uni Directional RTP.
  enables one sided RTP stream - according to niDirectionalRTPMode.
  enables the User to set the channel to work with unidirectional RTP streams. 
  When UniDirectionalRTP is set to acRTPTxOnly, 
  the receiver part of the channel will be disabled, and only the transmitter (encoder) will work. 
  When UniDirectionalRTP is set to acRTPRxOnly, 
  the transmitter part of the channel will be disabled, and only the receiver (decoder) will work. 
  When UniDirectionalRTP is set to acRTPTxRx, both sides will be enabled.
  Users should note that when configuring a session between two endpoints, 
  some of the channel configuration parameters must be identical on both sides. 
  Such parameters are the voice coder type, the Fax/Modem transport type and bypass coders. 
  All other configuration parameters are independent."
       ::= {transportSettingsEntry 3}



     -- ****************************************
     -- rTPRTCPSettings Configuration
     -- ****************************************
     rTPRTCPSettings               OBJECT IDENTIFIER ::= {channelConfiguration 7}


     -- ****************************************
     -- rTPRTCPSettings table decleration
     -- ****************************************
     rTPRTCPSettingsTable OBJECT-TYPE
       SYNTAX SEQUENCE OF RTPRTCPSettingsEntry
       MAX-ACCESS not-accessible
       STATUS obsolete
       DESCRIPTION
           "Data in RTP-RTCP Table, uniquely identify RTP-RTCP sparameters of channel."
       ::= {rTPRTCPSettings 1}



     -- ****************************************
     -- rTPRTCPSettings table entry
     -- ****************************************
     rTPRTCPSettingsEntry OBJECT-TYPE
       SYNTAX RTPRTCPSettingsEntry
       MAX-ACCESS not-accessible
       STATUS obsolete
       DESCRIPTION
           ""
       INDEX {cID}
       ::= {rTPRTCPSettingsTable 1}



     -- ****************************************
     -- rTPRTCPSettings TABLE
     -- ****************************************
     RTPRTCPSettingsEntry ::= SEQUENCE {
       cNAME                                           OCTET STRING,
       iPPrecedence                                    INTEGER,
       iPTOS                                           INTEGER,
       localRTPPort                                    INTEGER,
       remoteRTPAddr                                   IpAddress,
       remoteRTPPort                                   INTEGER,
       remoteT38Addr                                   IpAddress,
       remoteT38Port                                   INTEGER,
       rTCPMeanTxInterval                              INTEGER,
       rxRTPPayloadType                                INTEGER,
       txRTPPayloadType                                INTEGER
     }



     cNAME OBJECT-TYPE
       SYNTAX OCTET STRING (SIZE (0..255))
       MAX-ACCESS read-only
       STATUS obsolete
       DESCRIPTION
           "RTP Canonical Name. 
  Should be unique among all participants within one RTP session. 
  Refer to RFC1890 for more information.
  Up to 255 characters string. 
  (default ='ChX',  X=CID)."
       ::= {rTPRTCPSettingsEntry 1}



     iPPrecedence OBJECT-TYPE
       SYNTAX INTEGER (0..7)
       MAX-ACCESS read-only
       STATUS obsolete
       DESCRIPTION
           "IP Precedence.  
  Sets the value of the IP precedence field in the IP header 
  for all the packets to be generated from this channel. 
  Follow the acTIPPrecedence enumeration.
  Valid Range: 0-7  (default =0)
"
       ::= {rTPRTCPSettingsEntry 2}



     iPTOS OBJECT-TYPE
       SYNTAX INTEGER (0..15)
       MAX-ACCESS read-only
       STATUS obsolete
       DESCRIPTION
           "iP Type Of Service. 
  sets the value of the IP Type Of Service field in the IP header 
  for all the packets to be generated from this channel. 
  acNormalServiceTOS=0,
  acMinimizeMonetaryCostTOS=1,
  acMaximizeReliabilityTOS=2,
  acMaximizeThroughputTOS=4,
  acMinimizeDelayTOS=8
   (Follow the acTIPTOS enumeration). "
       ::= {rTPRTCPSettingsEntry 3}



     localRTPPort OBJECT-TYPE
       SYNTAX INTEGER (0..2147483647)
       MAX-ACCESS read-only
       STATUS obsolete
       DESCRIPTION
           "Local RTP Port.
 Local UDP Port to be used for incoming RTP stream to this channel. 
  This parameter also sets the local RTCP and local T.38 ports 
  in offset of 1,2 from LocalRTPPort respectively. 
  The local RTP port must be a number dividable by 10 
  and must reside within the following range 
  BoardParams.BaseUDPPort-> BoardParams.BaseUDPPort +10*MAX_CID_NUM. "
       ::= {rTPRTCPSettingsEntry 4}



     remoteRTPAddr OBJECT-TYPE
       SYNTAX IpAddress
       MAX-ACCESS read-only
       STATUS obsolete
       DESCRIPTION
           "Remote RTP Address"
       ::= {rTPRTCPSettingsEntry 5}



     remoteRTPPort OBJECT-TYPE
       SYNTAX INTEGER (0..2147483647)
       MAX-ACCESS read-only
       STATUS obsolete
       DESCRIPTION
           "IP/UDP Address of the remote endpoint RTP port"
       ::= {rTPRTCPSettingsEntry 6}



     remoteT38Addr OBJECT-TYPE
       SYNTAX IpAddress
       MAX-ACCESS read-only
       STATUS obsolete
       DESCRIPTION
           "remote T38 Address"
       ::= {rTPRTCPSettingsEntry 7}



     remoteT38Port OBJECT-TYPE
       SYNTAX INTEGER (0..2147483647)
       MAX-ACCESS read-only
       STATUS obsolete
       DESCRIPTION
           "IP/UDP Address of the remote endpoint  T.38  port"
       ::= {rTPRTCPSettingsEntry 8}



     rTCPMeanTxInterval OBJECT-TYPE
       SYNTAX INTEGER (100..2147483647)
       MAX-ACCESS read-only
       STATUS obsolete
       DESCRIPTION
           "RTCP Mean Tx Interval.
  Mean interval [msec] between channel's RTCP reports. "
       ::= {rTPRTCPSettingsEntry 9}



     rxRTPPayloadType OBJECT-TYPE
       SYNTAX INTEGER (-2..127)
       MAX-ACCESS read-only
       STATUS obsolete
       DESCRIPTION
           "Rx RTP Payload Type
  -1 = use the default coder RTP payload type for incoming voice packets. 
  -2 = allow any RTP payload type for incoming packets. 
  Otherwise, = sets the RTP payload type to be used for incoming voice packets 
  (this will override the default RTP payload type defined for each coder). 
   Valid Range: -1/-2 or any unoccupied RTPPT in the range 0-127 . 
  (default =-1). "
       ::= {rTPRTCPSettingsEntry 10}



     txRTPPayloadType OBJECT-TYPE
       SYNTAX INTEGER (-2..127)
       MAX-ACCESS read-only
       STATUS obsolete
       DESCRIPTION
           "Tx RTP Payload Type
  -1 = use the default coder RTP payload type for incoming voice packets. 
  -2 = allow any RTP payload type for incoming packets. 
  Otherwise, = sets the RTP payload type to be used for incoming voice packets 
  (this will override the default RTP payload type defined for each coder). 
   Valid Range: -1/-2 or any unoccupied RTPPT in the range 0-127. 
  (default =-1). "
       ::= {rTPRTCPSettingsEntry 11}



     -- ****************************************
     -- channelStatus Configuration
     -- ****************************************
     channelStatus                 OBJECT IDENTIFIER ::= {acBoard 4}


     -- ****************************************
     -- channelStatus table decleration
     -- ****************************************
     channelStatusTable OBJECT-TYPE
       SYNTAX SEQUENCE OF ChannelStatusEntry
       MAX-ACCESS not-accessible
       STATUS obsolete
       DESCRIPTION
           "Data in voice SettingsTable uniquely identify a voice parameters of channel."
       ::= {channelStatus 1}



     -- ****************************************
     -- channelStatus table entry
     -- ****************************************
     channelStatusEntry OBJECT-TYPE
       SYNTAX ChannelStatusEntry
       MAX-ACCESS not-accessible
       STATUS obsolete
       DESCRIPTION
           ""
       INDEX { cID }
       ::= {channelStatusTable 1}



     -- ****************************************
     -- channelStatus TABLE
     -- ****************************************
     ChannelStatusEntry ::= SEQUENCE {
       rTPActive                                       INTEGER,
       bypassNIC                                       INTEGER,
       pendingIdle                                     INTEGER,
       txSilencePeriod                                 INTEGER,
       rxSilencePeriod                                 INTEGER,
       txFaxMode                                       INTEGER,
       rxFaxMode                                       INTEGER,
       txDTMFPeriod                                    INTEGER,
       rxDTMFPeriod                                    INTEGER,
       packetsToDSPCnt                                 INTEGER,
       jitterBufErrorCnt                               INTEGER,
       jitterBufForcedPacketLost                       INTEGER,
       jitterBufForcedPacketAddition                   INTEGER,
       jitterBufUnderRunCnt                            INTEGER,
       jitterBufOverRunCnt                             INTEGER,
       jitterBufAccumDelay                             INTEGER,
       fXSorFXO                                        INTEGER,
       channelHookState                                INTEGER
     }



     rTPActive OBJECT-TYPE
       SYNTAX INTEGER {
                  notActive(0)
,
                  active(1)

                  }
       MAX-ACCESS read-only
       STATUS deprecated
       DESCRIPTION
           "RTP Active"
       ::= {channelStatusEntry 1}



     bypassNIC OBJECT-TYPE
       SYNTAX INTEGER (0..1)
       MAX-ACCESS read-only
       STATUS deprecated
       DESCRIPTION
           "Bypass NIC"
       ::= {channelStatusEntry 2}



     pendingIdle OBJECT-TYPE
       SYNTAX INTEGER (0..1)
       MAX-ACCESS read-only
       STATUS obsolete
       DESCRIPTION
           "Pending Idle"
       ::= {channelStatusEntry 3}



     txSilencePeriod OBJECT-TYPE
       SYNTAX INTEGER (0..1)
       MAX-ACCESS read-only
       STATUS deprecated
       DESCRIPTION
           "Tx Silence Period
"
       ::= {channelStatusEntry 4}



     rxSilencePeriod OBJECT-TYPE
       SYNTAX INTEGER (0..1)
       MAX-ACCESS read-only
       STATUS deprecated
       DESCRIPTION
           "Rx Silence Period"
       ::= {channelStatusEntry 5}



     txFaxMode OBJECT-TYPE
       SYNTAX INTEGER (0..1)
       MAX-ACCESS read-only
       STATUS deprecated
       DESCRIPTION
           "Tx Fax Mode
"
       ::= {channelStatusEntry 6}



     rxFaxMode OBJECT-TYPE
       SYNTAX INTEGER (0..1)
       MAX-ACCESS read-only
       STATUS deprecated
       DESCRIPTION
           "Rx Fax Mode
"
       ::= {channelStatusEntry 7}



     txDTMFPeriod OBJECT-TYPE
       SYNTAX INTEGER (0..1)
       MAX-ACCESS read-only
       STATUS deprecated
       DESCRIPTION
           "Tx DTMF Period
"
       ::= {channelStatusEntry 8}



     rxDTMFPeriod OBJECT-TYPE
       SYNTAX INTEGER (0..1)
       MAX-ACCESS read-only
       STATUS deprecated
       DESCRIPTION
           "Rx DTMF Period"
       ::= {channelStatusEntry 9}



     packetsToDSPCnt OBJECT-TYPE
       SYNTAX INTEGER (0..2147483647)
       MAX-ACCESS read-only
       STATUS deprecated
       DESCRIPTION
           "Jitter Buffer Error Counter"
       ::= {channelStatusEntry 10}



     jitterBufErrorCnt OBJECT-TYPE
       SYNTAX INTEGER (0..2147483647)
       MAX-ACCESS read-only
       STATUS obsolete
       DESCRIPTION
           "Jitter Buffer Forced Packet count"
       ::= {channelStatusEntry 11}



     jitterBufForcedPacketLost OBJECT-TYPE
       SYNTAX INTEGER (0..2147483647)
       MAX-ACCESS read-only
       STATUS obsolete
       DESCRIPTION
           "Jitter Buffer Forced Packet Lost"
       ::= {channelStatusEntry 12}



     jitterBufForcedPacketAddition OBJECT-TYPE
       SYNTAX INTEGER (0..2147483647)
       MAX-ACCESS read-only
       STATUS obsolete
       DESCRIPTION
           "Jitter Buffer Forced Packet Addition"
       ::= {channelStatusEntry 13}



     jitterBufUnderRunCnt OBJECT-TYPE
       SYNTAX INTEGER (0..2147483647)
       MAX-ACCESS read-only
       STATUS deprecated
       DESCRIPTION
           "Jitter Buffer Under-Run Counter"
       ::= {channelStatusEntry 14}



     jitterBufOverRunCnt OBJECT-TYPE
       SYNTAX INTEGER (0..2147483647)
       MAX-ACCESS read-only
       STATUS deprecated
       DESCRIPTION
           "Jitter Buffer Over-Run Counter"
       ::= {channelStatusEntry 15}



     jitterBufAccumDelay OBJECT-TYPE
       SYNTAX INTEGER (0..2147483647)
       MAX-ACCESS read-only
       STATUS obsolete
       DESCRIPTION
           "Jitter Buffer accumulation Delay. In packets."
       ::= {channelStatusEntry 16}



     fXSorFXO OBJECT-TYPE
       SYNTAX INTEGER {
                  nonAnalogDevice(-1)
,
                  fXO(0)
,
                  fXS(1)

                  }
       MAX-ACCESS read-only
       STATUS deprecated
       DESCRIPTION
           "returns the type phisical type of endpoint"
       ::= {channelStatusEntry 17}



     channelHookState OBJECT-TYPE
       SYNTAX INTEGER {
                  nonAnalogDevice(-1)
,
                  offHook(0)
,
                  onHook(1)

                  }
       MAX-ACCESS read-only
       STATUS deprecated
       DESCRIPTION
           "Channel Hook State"
       ::= {channelStatusEntry 18}



     -- ****************************************
     -- notifications Configuration
     -- ****************************************
     notifications                 OBJECT IDENTIFIER ::= {acBoard 5}


     -- ****************************************
     -- reset Configuration
     -- ****************************************
     reset                         OBJECT IDENTIFIER ::= {acBoard 6}


     remoteReset OBJECT-TYPE
       SYNTAX INTEGER (0..2147483647)
       MAX-ACCESS read-write
       STATUS obsolete
       DESCRIPTION
           "remote Reset. 
  To remote reset the board, set an integer value to this parameter. 
  Note: Before Reset, The current boardConfiguration parameters will be burned to the board.  "
       ::= {reset 1}



     acSetDefaults OBJECT-TYPE
       SYNTAX INTEGER (1..2147483647)
       MAX-ACCESS read-write
       STATUS obsolete
       DESCRIPTION
           "To set the default values, set an integer value to this parameter"
       ::= {reset 2}



     acgwAdminState OBJECT-TYPE
       SYNTAX INTEGER {
                  locked(0)
,
                   shuttingDown(1)
,
                   unlocked(2)

                  }
       MAX-ACCESS read-write
       STATUS obsolete
       DESCRIPTION
           "Determines the gateway's operational state.  
0 - locked: Shutdown the GW In the time frame set by acgwAdminStateLockControl
1 - shuttingDown: (read only) Graceful Shutdown is being carried out  
2 - unlocked: GW is in service.  "
       ::= {reset 3}



     acgwAdminStateLockControl OBJECT-TYPE
       SYNTAX INTEGER (-1..65535)
       MAX-ACCESS read-write
       STATUS obsolete
       DESCRIPTION
           "(in sec) time left for the graceful shutdown to complete.
  -1 indicates unlimited time frame. 
  0 indicates immediate (forced) lock. 
Implementing the control requires setting acgwAdminState to locked.  "
       ::= {reset 4}



     acSaveConfigToSystem OBJECT-TYPE
       SYNTAX INTEGER (0..2147483647)
       MAX-ACCESS read-write
       STATUS obsolete
       DESCRIPTION
           "This will save all current configuration in the board onto the flash. 
Any digit will call on the function. 
NOTE: Do NOT save the configuration while voice is running - this will cause a delay."
       ::= {reset 5}



     acOperationalState OBJECT-TYPE
       SYNTAX INTEGER {
                  disabled(1)
,
                  enabled(2)

                  }
       MAX-ACCESS read-only
       STATUS obsolete
       DESCRIPTION
           "The operational state of the gateway."
       ::= {reset 6}



     remoteResetControl OBJECT-TYPE
       SYNTAX INTEGER {
                  resetFromFlashAfterBurn(1)
,
                   resetFromFlashNoBurn(2)
,
                   resetFromBootP(3)

                  }
       MAX-ACCESS read-write
       STATUS obsolete
       DESCRIPTION
           "Determine the remote reset action
1 - burn staged load image, if any, and config to flash, perform a reset, and load from flash
2 - perform a reset, and load from flash (staged load image, if any, and config is not burned to flash)
3 - perform a reset, and load from bootp/tftp (staged load image, if any, and config burn is not needed)
* - an error is returned for any other value
Note: The staged load image is an image of a cmp file that was previously loaded to a area in RAM via an HTTP upload

"
       ::= {reset 7}



     -- ****************************************
     -- acTrap Configuration
     -- ****************************************
     acTrap                        OBJECT IDENTIFIER ::= {acBoard 21}


     -- ****************************************
     -- acBoardTrapGlobals Configuration
     -- ****************************************
     acBoardTrapGlobals            OBJECT IDENTIFIER ::= {acTrap 1}


     acBoardTrapGlobalsName OBJECT-TYPE
       SYNTAX INTEGER (0..1000)
       MAX-ACCESS read-only
       STATUS deprecated
       DESCRIPTION
           "trap name"
       ::= {acBoardTrapGlobals 1}



     acBoardTrapGlobalsTextualDescription OBJECT-TYPE
       SYNTAX OCTET STRING (SIZE (0..200))
       MAX-ACCESS read-only
       STATUS deprecated
       DESCRIPTION
           "title of trap"
       ::= {acBoardTrapGlobals 2}



     acBoardTrapGlobalsSource OBJECT-TYPE
       SYNTAX OCTET STRING (SIZE (0..100))
       MAX-ACCESS read-only
       STATUS deprecated
       DESCRIPTION
           "Trap Source - MG1/Shelf1/Board2/Trunk3"
       ::= {acBoardTrapGlobals 3}



     acBoardTrapGlobalsSeverity OBJECT-TYPE
       SYNTAX INTEGER {
                  cleared(0)
,
                  indeterminate(1)
,
                  warning(2)
,
                  minor(3)
,
                  major(4)
,
                  critical(5)

                  }
       MAX-ACCESS read-only
       STATUS deprecated
       DESCRIPTION
           "Trap Severity"
       ::= {acBoardTrapGlobals 4}



     acBoardTrapGlobalsUniqID OBJECT-TYPE
       SYNTAX INTEGER (0..32000)
       MAX-ACCESS read-only
       STATUS deprecated
       DESCRIPTION
           "Trap Uniq Id - generated by AcBoard and should be uniq for the entire EMS"
       ::= {acBoardTrapGlobals 5}



     acBoardTrapGlobalsType OBJECT-TYPE
       SYNTAX INTEGER {
                  other(0)
,
                  communicationsAlarm(1)
,
                  qualityOfServiceAlarm(2)
,
                  processingErrorAlarm(3)
,
                  equipmentAlarm(4)
,
                  environmentalAlarm(5)

                  }
       MAX-ACCESS read-only
       STATUS deprecated
       DESCRIPTION
           "Trap type - ItuAlarmType"
       ::= {acBoardTrapGlobals 6}



     acBoardTrapGlobalsProbableCause OBJECT-TYPE
       SYNTAX INTEGER {
                  other(0)
,
                  adapterError(1)
,
                  applicationSubsystemFailure(2)
,
                  bandwidthReduced(3)
,
                  callEstablishmentError(4)
,
                  communicationsProtocolError(5)
,
                  communicationsSubsystemFailure(6)
,
                  configurationOrCustomizationError(7)
,
                  congestion(8)
,
                  corruptData(9)
,
                  cpuCyclesLimitExceeded(10)
,
                  dataSetOrModemError(11)
,
                  degradedSignal(12)
,
                  dteDceInterfaceError(13)
,
                  enclosureDoorOpen(14)
,
                  equipmentMalfunction(15)
,
                  excessiveVibration(16)
,
                  fileError(17)
,
                  fireDetected(18)
,
                  floodDetected(19)
,
                  framingError(20)
,
                  heatingVentCoolingSystemProblem(21)
,
                  humidityUnacceptable(22)
,
                  inputOutputDeviceError(23)
,
                  inputDeviceError(24)
,
                  lanError(25)
,
                  leakDetected(26)
,
                  localNodeTransmissionError(27)
,
                  lossOfFrame(28)
,
                  lossOfSignal(29)
,
                  materialSupplyExhausted(30)
,
                  multiplexerProblem(31)
,
                  outOfMemory(32)
,
                  ouputDeviceError(33)
,
                  performanceDegraded(34)
,
                  powerProblem(35)
,
                  pressureUnacceptable(36)
,
                  processorProblem(37)
,
                  pumpFailure(38)
,
                  queueSizeExceeded(39)
,
                  receiveFailure(40)
,
                  receiverFailure(41)
,
                  remoteNodeTransmissionError(42)
,
                  resourceAtOrNearingCapacity(43)
,
                  responseTimeExecessive(44)
,
                  retransmissionRateExcessive(45)
,
                  softwareError(46)
,
                  softwareProgramAbnormallyTerminated(47)
,
                  softwareProgramError(48)
,
                  storageCapacityProblem(49)
,
                  temperatureUnacceptable(50)
,
                  thresholdCrossed(51)
,
                  timingProblem(52)
,
                  toxicLeakDetected(53)
,
                  transmitFailure(54)
,
                  transmitterFailure(55)
,
                  underlyingResourceUnavailable(56)
,
                  versionMismatch(57)
,
                  authenticationFailure(58)
,
                  breachOfConfidentiality(59)
,
                  cableTamper(60)
,
                  delayedInformation(61)
,
                  denialOfService(62)
,
                  duplicateInformation(63)
,
                  informationMissing(64)
,
                  informationModificationDetected(65)
,
                  informationOutOfSequence(66)
,
                  intrusionDetection(67)
,
                  keyExpired(68)
,
                  nonRepudiationFailure(69)
,
                  outOfHoursActivity(70)
,
                  outOfService(71)
,
                  proceduralError(72)
,
                  unauthorizedAccessAttempt(73)
,
                  unexpectedInformation(74)

                  }
       MAX-ACCESS read-only
       STATUS deprecated
       DESCRIPTION
           "Trap probable cause - SnmpAlarmProbableCause"
       ::= {acBoardTrapGlobals 7}



     acBoardTrapGlobalsAdditionalInfo1 OBJECT-TYPE
       SYNTAX OCTET STRING (SIZE (0..100))
       MAX-ACCESS read-only
       STATUS deprecated
       DESCRIPTION
           "Trap additional info global field"
       ::= {acBoardTrapGlobals 8}



     acBoardTrapGlobalsAdditionalInfo2 OBJECT-TYPE
       SYNTAX OCTET STRING (SIZE (0..100))
       MAX-ACCESS read-only
       STATUS deprecated
       DESCRIPTION
           "Trap additional info global field"
       ::= {acBoardTrapGlobals 9}



     acBoardTrapGlobalsAdditionalInfo3 OBJECT-TYPE
       SYNTAX OCTET STRING (SIZE (0..100))
       MAX-ACCESS read-only
       STATUS deprecated
       DESCRIPTION
           "Trap additional info global field"
       ::= {acBoardTrapGlobals 10}



     acBoardTrapGlobalsDateAndTime OBJECT-TYPE
       SYNTAX DateAndTime
       MAX-ACCESS read-only
       STATUS deprecated
       DESCRIPTION
           "Date and time that the trap was sent."
       ::= {acBoardTrapGlobals 11}



     -- ****************************************







     -- ****************************************
     -- acBoardTrapDefinitions Configuration
     -- ****************************************
     acBoardTrapDefinitions        OBJECT IDENTIFIER ::= {acTrap 2}


     acBoardFatalError NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Board fatal error"
       ::= {acBoardTrapDefinitions 0 1}



     acBoardConfigurationError NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Configuration Error"
       ::= {acBoardTrapDefinitions 0 2}



     acBoardTemperatureAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Temperature Alarm. Turned on when temperature exceeds 60 degrees Celsius, and relaxes when temperature goes under 55 again."
       ::= {acBoardTrapDefinitions 0 3}



     acBoardEvBoardStarted NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Initialization Ended"
       ::= {acBoardTrapDefinitions 0 4}



     acBoardEvResettingBoard NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "The board start Reset process - following software reset"
       ::= {acBoardTrapDefinitions 0 5}



     acFeatureKeyError NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Feature key related Error"
       ::= {acBoardTrapDefinitions 0 6}



     acgwAdminStateChange NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "The administrative state of the gate way has been changed to a new state."
       ::= {acBoardTrapDefinitions 0 7}



     acBoardCallResourcesAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "No free channels available"
       ::= {acBoardTrapDefinitions 0 8}



     acBoardControllerFailureAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "The GK/Proxy not found or registration failed. internal routing table may be used for routing"
       ::= {acBoardTrapDefinitions 0 9}



     acBoardEthernetLinkAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Ethernet Link is down or remote Ethernet link is down and board has no communication to any other host"
       ::= {acBoardTrapDefinitions 0 10}



     acBoardOverloadAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Overload in one or some of the system's components"
       ::= {acBoardTrapDefinitions 0 11}



     acActiveAlarmTableOverflow NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "An active alarm could not be placed in the active alarm table because the table is full. 
This alarm will not clear. Reboot is the only way to completely clear the Active Alarm table overflow problem.
Any alarm raised at this state will not be Carrier Grade compatible. Therefore, Updates will not clear the alarm
before changing the bindings and re-raising alarms. The History tables remain unaffected. 
All Alarms raised prior to overflow will remain Carrier Grade compatible. 
Other alarms, raised after this alarm was raised, that are placed in the Active Alarm table will be Carrier Grade 
compatible. (This is for when after the alarm was raised there were some clears, clearing alarms off the Active Alarm table)."
       ::= {acBoardTrapDefinitions 0 12}



     acAtmPortAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           " ATM Port Alarm"
       ::= {acBoardTrapDefinitions 0 13}



     acAudioProvisioningAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           " This alarm is raised if the Media Server is unable to provision its audio. This could be because the Audio Provisioning System (APS) is down or there is a network problem."
       ::= {acBoardTrapDefinitions 0 14}



     acOperationalStateChange NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This alarm is raised if the operational state of the node goes to disabled. The alarm is cleared when the operational state of the node goes to enabled."
       ::= {acBoardTrapDefinitions 0 15}



     acKeepAlive NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This trap is the NAT Traversal keep alive trap. 
If the STUN application in the device detects a NAT then this trap will be sent out on a regular time laps - 9/10 of the acSysSTUNBindingLifeTime object. The AdditionalInfo1 varbind has the MAC address of the device.
Note that all traps are sent out from the SNMP Port (usually 161)."
       ::= {acBoardTrapDefinitions 0 16}



     acNATTraversalAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "When the NAT placed in front a device is identified as a symmetric NAT - this alarm is raised. It is cleared when a non-symmetric NAT or no NAT replace the symmetric one. "
       ::= {acBoardTrapDefinitions 0 17}



     acEnhancedBITStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This trap is used to for the status of the BIT (Built In Test).
The information in the trap contains board HW elements being tested and their status.
The information is presented in the additional info fields."
       ::= {acBoardTrapDefinitions 0 18}



     acSS7LinkStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This alarm is raised if the operational state of the SS7 link becomes XXXX. The alarm is cleared when the operational state of the link becomes XXXX."
       ::= {acBoardTrapDefinitions 0 19}



     acSS7LinkInhibitStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This alarm is raised if the SS7 link becomes inhibited (local or remote). The alarm is cleared when the link becomes uninhibited - local AND remote. Note that this alarm will be raised for any change in the remote or local inhibition status."
       ::= {acBoardTrapDefinitions 0 20}



     acSS7LinkBlockStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This alarm is raised if the SS7 link becomes blocked (local or remote). The alarm is cleared when the link becomes unblocked - local AND remote. Note that this alarm will be raised for any change in the remote or local blocking status."
       ::= {acBoardTrapDefinitions 0 21}



     acSS7LinkCongestionStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This alarm is raised if the SS7 link becomes congested (local or remote). The alarm is cleared when the link becomes uncongested - local AND remote. Note that this alarm will be raised for any change in the remote or local congestion status."
       ::= {acBoardTrapDefinitions 0 22}



     acSS7LinkSetStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This alarm is raised if the operational state of the SS7 linkset becomes BUSY. The alarm is cleared when the operational state of the linkset becomes IN-SERVICE or OFFLINE."
       ::= {acBoardTrapDefinitions 0 23}



     acSS7RouteSetStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This alarm is raised if the operational state of the SS7 routeset becomes BUSY. The alarm is cleared when the operational state of the routeset becomes IN-SERVICE or OFFLINE."
       ::= {acBoardTrapDefinitions 0 24}



     acSS7SNSetStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This alarm is raised if the operational state of the SS7 node becomes BUSY. The alarm is cleared when the operational state of the node becomes IN-SERVICE or OFFLINE."
       ::= {acBoardTrapDefinitions 0 25}



     acSS7RedundancyAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Raised when the SS7 redundancy degregated. Cleared when all entities of redundancy are fully functional and in serveice."
       ::= {acBoardTrapDefinitions 0 26}



     acPerformanceMonitoringThresholdCrossing NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This log trap is sent out for every time the threshold
of a Performance Monitored object is crossed.
The severity field is 'indeterminate' when the crossing is above the threshold
and 'cleared' when it goes back under the threshold.
The 'source' varbind in the trap indicates the object
for which the threshold is being crossed."
       ::= {acBoardTrapDefinitions 0 27}



     acHTTPDownloadResult NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This trap indicates the result of a recent file download (includes HTTP error code, if available)."
       ::= {acBoardTrapDefinitions 0 28}



     acFanTrayAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This alarm is raised when the fan tray is missing or some of the fans are faulty.
If the fan tray is missing or more then X fans are faulty the severity will be Critical.
If more then one and less the X fans are faulty the severity will be Major.
"
       ::= {acBoardTrapDefinitions 0 29}



     acPowerSupplyAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This alarm is raised when the HA (High Availability) feature is active and one of the power supply units is faulty."
       ::= {acBoardTrapDefinitions 0 30}



     acPEMAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This alarm is raised when the HA (High Availability) feature is active. The severity is critical if one of the PEM units is missing and major if the electric wire to one of the units is disconnected. "
       ::= {acBoardTrapDefinitions 0 31}



     acSAMissingAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This alarm is raised when the SA module in the M3K MG is missing. Whenthere is no SAT there are no other chassis HW related alarms.
Note - relevant only for M3K."
       ::= {acBoardTrapDefinitions 0 32}



     acHASystemFaultAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This alarm is raised when the HA (High Availability) feature is active and the system is NOT HA.
Critical severity - 
1.Wrong HW Configuration.
2. Redundant module is missing (not in slot).
3. The redundant module is non operable.
Minor severity -  waiting for redunadant to connect (after reset!). "
       ::= {acBoardTrapDefinitions 0 33}



     acHASystemConfigMismatchAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This alarm is raised when the HA (High Availability) feature is active and there has been a configuration change due to which the HA system may or may not be usable."
       ::= {acBoardTrapDefinitions 0 34}



     acHASystemSwitchOverAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This alarm is raised when the HA (High Availability) feature is active and there has been a switchover due to failure or reset in the active module."
       ::= {acBoardTrapDefinitions 0 35}



     acUserInputAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This Alarm is raised when the input dry contact is short circuited. Cleared when the circuit is reopened."
       ::= {acBoardTrapDefinitions 0 36}



     acDChannelStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This non alarm trap is sent when establishment, re-establishment or release of LAPD link with its peer connection occurs.
The trap will be sent out with one of the following in the textual description:
D-channel synchronized
D-channel not-synchronized"
       ::= {acBoardTrapDefinitions 0 37}



     acSonetSectionLOFAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "SONET section Loss of Frame alarm."
       ::= {acBoardTrapDefinitions 0 38}



     acSonetSectionLOSAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "SONET section Loss of Signal alarm."
       ::= {acBoardTrapDefinitions 0 39}



     acSonetLineAISAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "SONET Line AIS alarm."
       ::= {acBoardTrapDefinitions 0 40}



     acSonetLineRDIAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "SONET Line RDI alarm."
       ::= {acBoardTrapDefinitions 0 41}



     acSonetIfHwFailureAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "SONET or SDH medium Interface has failed."
       ::= {acBoardTrapDefinitions 0 42}



     acHwFailureAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "HW failure alarm."
       ::= {acBoardTrapDefinitions 0 43}



     acH248LostConnectionWithCA NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "H248 lost connection with call agent"
       ::= {acBoardTrapDefinitions 0 44}



     acDialPlanFileReplaced NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "dial plan file replaced notification"
       ::= {acBoardTrapDefinitions 0 45}



     acAnalogPortSPIOutOfService NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Analog port out of service "
       ::= {acBoardTrapDefinitions 0 46}



     acAnalogPortHighTemperature NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Analog Port High Temperature"
       ::= {acBoardTrapDefinitions 0 47}



     acHitlessUpdateStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Notification trap that is sent out at the beginning and the end of a Hitless SW update.
Failure during the process will also instigate the trap.
Relevant to HA systems only."
       ::= {acBoardTrapDefinitions 0 48}



     acTrunksAlarmNearEndLOS NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Loss of signal at trunk's near end."
       ::= {acBoardTrapDefinitions 0 49}



     acTrunksAlarmNearEndLOF NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Loss of frame at trunk's near end."
       ::= {acBoardTrapDefinitions 0 50}



     acTrunksAlarmRcvAIS NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Received AIS from trunk's far end."
       ::= {acBoardTrapDefinitions 0 51}



     acTrunksAlarmFarEndLOF NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Loss of frame at trunk's far end."
       ::= {acBoardTrapDefinitions 0 52}



     acIPv6ErrorAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Alarm trap that is sent out for IPv6 related errors."
       ::= {acBoardTrapDefinitions 0 53}



     acAMSProcedureResult NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "AMS procedure related information"
       ::= {acBoardTrapDefinitions 0 54}



     acWeakRedundancy NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "The system is in weak redundancy mode. Switch over is done with a reset to the board taking over."
       ::= {acBoardTrapDefinitions 0 55}



     acTMInconsistentRemoteAndLocalPLLStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Inconsistent Remote And Local PLL Status "
       ::= {acBoardTrapDefinitions 0 56}



     acTMReferenceStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Timing manager reference status"
       ::= {acBoardTrapDefinitions 0 57}



     acTMReferenceChange NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Timing manager reference Change"
       ::= {acBoardTrapDefinitions 0 58}



     acGWSASEmergencyModeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "The alarm is raised when SAS enters the Emergency Mode and then cleared when SAS enters Normal Mode again."
       ::= {acBoardTrapDefinitions 0 59}



     acV52InterfaceAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "The alarm is raised for v5.2 interface errors and alarms.{@}For a detailed list of the interfaces' alarms see the acV5InterfceTable."
       ::= {acBoardTrapDefinitions 0 60}



     acSonetPathSTSLOPAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Sonet Path STS  LOP alarm."
       ::= {acBoardTrapDefinitions 0 61}



     acSonetPathSTSAISAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Sonet Path STS AIS alarm."
       ::= {acBoardTrapDefinitions 0 62}



     acSonetPathSTSRDIAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Sonet Path STS RDI alarm."
       ::= {acBoardTrapDefinitions 0 63}



     acSonetPathUnequippedAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Sonet Path Unequipped alarm."
       ::= {acBoardTrapDefinitions 0 64}



     acSonetPathSignalLabelMismatchAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Sonet Path Signal Label Mismatch alarm."
       ::= {acBoardTrapDefinitions 0 65}



     acDS3RAIAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "DS3 RAI alarm."
       ::= {acBoardTrapDefinitions 0 66}



     acDS3AISAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "DS3 AIS alarm."
       ::= {acBoardTrapDefinitions 0 67}



     acDS3LOFAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "DS3 LOF alarm."
       ::= {acBoardTrapDefinitions 0 68}



     acDS3LOSAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "DS3 LOS alarm."
       ::= {acBoardTrapDefinitions 0 69}



     acSWUpgradeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Raised for SW upgrade process errors."
       ::= {acBoardTrapDefinitions 0 70}



     acNTPServerStatusAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "NTP server status alarm. {@}Raised when the connection to the NTP server is lost. Cleared when the connection is reestablished. {@}Unset time (as a result of no connection to NTP server) may result with functionality degradation and failure in device."
       ::= {acBoardTrapDefinitions 0 71}



     acThreeWayConferenceOutOfResources NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Three way conference  out of resources.  "
       ::= {acBoardTrapDefinitions 0 72}



     acSS7AliasPcStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "raised when the Alias PC is in BUSY state. Cleared when it is in In-Service state."
       ::= {acBoardTrapDefinitions 0 73}



     acSS7UalGroupStateChangeAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Raised when the Ual Group Asp state is not ACTIVE. Cleared when it is Active."
       ::= {acBoardTrapDefinitions 0 74}



     acLDAPLostConnection NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Raised when there is no connection to the LDAP server."
       ::= {acBoardTrapDefinitions 0 75}



     acAnalogPortGroundFaultOutOfService NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Raised when the MP500 FXS port is inactive due to ground fault."
       ::= {acBoardTrapDefinitions 0 76}



     acSSHConnectionStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "This trap indicates the result of a recent SSH connection attempt."
       ::= {acBoardTrapDefinitions 0 77}



     acOCSPServerStatusAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "raised when OCSP connection is not available."
       ::= {acBoardTrapDefinitions 0 78}



     acBoardWanLinkAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Wan Link is down."
       ::= {acBoardTrapDefinitions 0 79}



     acPowerOverEthernetStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Raised when PEO resources are over allocated"
       ::= {acBoardTrapDefinitions 0 80}



     acMediaProcessOverloadAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Raised when media process overloads"
       ::= {acBoardTrapDefinitions 0 81}



     acWirelessCellularModemAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Raised when either the wireless modem is down or in backup mode."
       ::= {acBoardTrapDefinitions 0 82}



     acDataInterfaceStatus NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Raised when a DSL interface state changes to up or down."
       ::= {acBoardTrapDefinitions 0 83}



     acNFASGroupAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Raised when an NFAS group goes Out-Of-Service"
       ::= {acBoardTrapDefinitions 0 84}



     acBChannelAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Raised when B-Channel service state changes"
       ::= {acBoardTrapDefinitions 0 85}



     acEthernetGroupAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Raised when the Ethernet group has no Ethernet port with its link up. Cleared when at least on port has established a link."
       ::= {acBoardTrapDefinitions 0 86}



     acMediaRealmBWThresholdAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Raised when a BW threshold is crossed"
       ::= {acBoardTrapDefinitions 0 87}



     acNqmConnectivityAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Connectivity with NQM probe destination is lost"
       ::= {acBoardTrapDefinitions 0 88}



     acNqmRttAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Detected high Round Trip Time towards NQM probe destination"
       ::= {acBoardTrapDefinitions 0 89}



     acNqmJitterAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Detected high Jitter towards NQM probe destination"
       ::= {acBoardTrapDefinitions 0 90}



     acNqmPacketLossAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Detected high Packet Loss towards NQM probe destination"
       ::= {acBoardTrapDefinitions 0 91}



     acCertificateExpiryNotifiaction NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Send before the expiration of the installed credentials, which cannot be renewed automatically."
       ::= {acBoardTrapDefinitions 0 92}



     acWEBUserAccessDisabled NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Web user was disabled due to inactivity."
       ::= {acBoardTrapDefinitions 0 93}



     acProxyConnectionLost NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Raised when all connections in the proxy set are down."
       ::= {acBoardTrapDefinitions 0 94}



     acNqmCqMosAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Detected low conversational voice quality towards NQM probe destination"
       ::= {acBoardTrapDefinitions 0 95}



     acNqmLqMosAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Detected low listening voice quality towards NQM probe destination"
       ::= {acBoardTrapDefinitions 0 96}



     acRedundantBoardAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Active board sends notification when an alarm or notification is raised in the redundant board.
The information is as follow:
acBoardTrapGlobalsAdditionalInfo1: redundant’s original info
acBoardTrapGlobalsAdditionalInfo2: trap Id
acBoardTrapGlobalsAdditionalInfo3: redundant’s serial number
"
       ::= {acBoardTrapDefinitions 0 97}



     acHANetworkWatchdogStatusAlarm NOTIFICATION-TYPE
       OBJECTS {
                acBoardTrapGlobalsName,
                
                acBoardTrapGlobalsTextualDescription,
                
                acBoardTrapGlobalsSource,
                
                acBoardTrapGlobalsSeverity,
                
                acBoardTrapGlobalsUniqID,
                
                acBoardTrapGlobalsType,
                
                acBoardTrapGlobalsProbableCause,
                
                acBoardTrapGlobalsAdditionalInfo1,
                
                acBoardTrapGlobalsAdditionalInfo2,
                
                acBoardTrapGlobalsAdditionalInfo3,
                
                acBoardTrapGlobalsDateAndTime
               }
       STATUS current
       DESCRIPTION
           "Sent when the module was enabled by the user but it is not running."
       ::= {acBoardTrapDefinitions 0 98}





END
