HP-AUTH-MIB DEFINITIONS ::= BEGIN

    IMPORTS
        OBJECT-TYPE, MODULE-IDENTITY, Integer32, Counter32, IpAddress,
        Gauge32, Unsigned32
             FROM SNMPv2-SMI
        RowStatus, DisplayString, TruthValue, DateAndTime
            FROM SNMPv2-TC
        OBJECT-GROUP, MODULE-COMPLIANCE
            FROM SNMPv2-CONF
        hpSwitch
          FROM HP-ICF-OID 
        ospfIfEntry, ospfVirtIfEntry
            FROM OSPF-MIB
        InetAddress, InetAddressType
            FROM INET-ADDRESS-MIB;

    hpSwitchAuthenticationMIB MODULE-IDENTITY
        LAST-UPDATED "201403120000Z" -- Mar 12, 2014
        ORGANIZATION "HP Networking"
        CONTACT-INFO "Hewlett Packard Company
                      8000 Foothills Blvd.
                      Roseville, CA 95747"
        DESCRIPTION  "This MIB module describes objects for managing
                     the Authentication features of devices in the HP
                     Integrated Communication Facility product line."

        REVISION     "201403120000Z"  -- Mar 12, 2014
        DESCRIPTION  "Added hpSwitchAuthAllowVlanTagged"

        REVISION     "201311120000Z"  -- Nov 12, 2013
        DESCRIPTION  "Added hpicfSwitchBypassUsername"
        
        REVISION     "201306120000Z"  -- June 12, 2013
        DESCRIPTION  "Deprecated object
                     hpSwitchRadiusServerIpAddr and compliances
                     hpSwitchUserConfigMIBCompliance,
                     hpSwitchAuthenticationMIBCompliance3,
                     hpSwitchAuthenticationMIBCompliance5,
                     hpSwitchAuthenticationMIBCompliance4,
                     hpSwitchAuthenticationMIBComplianceOobm.
                     Added objects hpSwitchRadiusServerAddrType,
                     hpSwitchRadiusServerAddress,hpSwitchAuthLockoutDelay.
                     Added compliances
                     hpSwitchAuthenticationMIBComplianceOobm1,
                     hpSwitchAuthenticationMIBCompliance6.Added
                     groups hpSwitchAuthenticationConfigGroup2,
                     hpSwitchRadiusConfigGroup2."

        REVISION     "201305270000Z"  -- May 27, 2013
        DESCRIPTION  "Added 'hpSwitchMinimumPasswordLength',
                      'hpSwitchAuthenticationConfigGroup3',
                      'hpSwitchAuthenticationMIBCompliance7'
                      and deprecated 
                      'hpSwitchAuthenticationConfigGroup2'
                      'hpSwitchAuthenticationMIBCompliance6'."

        REVISION     "201205110000Z"  -- May 11, 2012
        DESCRIPTION  "Added hpSwitchRadiusServerAddrType,
                      hpSwitchRadiusServerAddress"

        REVISION     "201205010000Z"  -- May 1, 2012
        DESCRIPTION  "Added hpSwitchAuthLockoutDelay."

        REVISION     "201106020000Z"  -- June 2, 2011
        DESCRIPTION  "Added 'hpSwitchServerNewCertKeySizeExists'"

        REVISION     "201102120000Z"  -- February 12, 2011
        DESCRIPTION  "Added hpSwitchAuthenticationEncryptCredentialsMethod,
                      hpSwitchTacacsAuthKeyEncrypted,
                      hpSwitchTacacsServerKeyEncrypted,
                      hpSwitchRadiusAuthKeyEncrypted,
                      hpSwitchRadiusServerKeyEncrypted,
                      hpSwitchKmsKeyEncrypted,
                      hpicfSwitchUserPasswordEncrypted,
                      hpicfSwitchOperatorPasswordEncrypted,
                      hpicfSwitchPortAccessPasswordEncrypted."

        REVISION     "201102070000Z"  -- February 07, 2011
        DESCRIPTION  "Added hpSwitchLocalMgmtPrivUsernamesTable."

        REVISION     "200906060000Z"  -- June 6, 2009
        DESCRIPTION  "Added hpicfSwitchPortAccessName, 
                      hpicfSwitchPortAccessPassword,
                      hpicfSwitchUserPasswordHashType, 
                      hpicfOperatorPasswordHashType, 
                      hpicfPortAccessPasswordHashType."

        REVISION     "200906030000Z"  -- June 3, 2009
        DESCRIPTION  "Added larger SIZE parameters, added notes to
                      refer to product documentation and removed
                      restriction on space character to comments for
                      hpicfSwitchUserName, hpicfSwitchOperatorName,
                      hpicfSwitchUserPassword, hpicfSwitchOperatorPassword"

        REVISION     "200904020000Z"  -- April 2, 2009
        DESCRIPTION  "Removed SIZE parameters from UserName, OperatorName,
                      UserPassword, OperatorPassword"

        REVISION     "200902270000Z"  -- February 27, 2009
        DESCRIPTION  "Added cachedReauth to  
                      'hpSwitchAuthenLoginSecondary' values."

        REVISION     "200901290000Z"  -- January 29, 2009
        DESCRIPTION  "Added 'hpSwitchTacacsServerIsOobm' MIB object 
                      in 'hpSwitchTacacsServersTable' table and
                      'hpSwitchRadiusServerIsOobm' MIB object
                      in 'hpSwitchRadiusServerTable' table."

        REVISION     "200807110000Z"  -- July 11, 2008
        DESCRIPTION  "Added 'hpSwitchAuthenLoginServerGroupName',
                     'hpSwitchAuthenEnableServerGroupName' MIB objects.
                      Added hpSwitchAAAServerGroupTable."

        REVISION     "200806110000Z"  -- June 11, 2008
        DESCRIPTION  "Added radiusPeapMSChapv2 to                       
                     'hpSwitchAuthenEnablePrimary' values."

        REVISION     "200709210000Z"  -- September 21, 2007
        DESCRIPTION  "Added 'hpSwitchRadiusDynAutzPortNumber',
                     'hpSwitchRadiusServerDynAutzEnabled',
                     'hpSwitchRadiusServerDynAutzTimeWindow' MIB objects.
                     'hpSwitchRadiusAuthPortNumber' MIB object renamed to
                     'hpSwitchRadiusServerAuthPortNumber',
                     'hpSwitchRadiusAcctPortNumber' MIB object renamed to
                     'hpSwitchRadiusServerAcctPortNumber'."

        REVISION     "200610050000Z"  -- October 5, 2006
        DESCRIPTION  "Added 'hpicfSwitchUserConfigTable' MIB object."

        REVISION     "200409120000Z"  -- September 12, 2004
        DESCRIPTION  "Moved 802.1x objects to separate module."

        REVISION     "200403310012Z"  -- March 31, 2004
        DESCRIPTION  "Revised version of this MIB module."

        REVISION     "200108100238Z"  -- August 10, 2001
        DESCRIPTION  "Initial version of this MIB module."
     
        ::= { hpSwitch 16 }
            
-- ------------------------------------------------------------
    -- Configuration support for Authentication
-- ------------------------------------------------------------

    hpSwitchAuthenticationConfig
        OBJECT IDENTIFIER ::= { hpSwitchAuthenticationMIB 1 }

    hpSwitchNumLoginAttempts OBJECT-TYPE
        SYNTAX      Integer32 (1..10)
        MAX-ACCESS  read-write
        STATUS      current
        DESCRIPTION "The number of login attempts allowed, both per session
                     and within the time of hpSwitchAuthLockoutDelay."
        DEFVAL      { 3 }
        ::= { hpSwitchAuthenticationConfig 1 }

    hpSwitchAuthRespectPriv OBJECT-TYPE
        SYNTAX      INTEGER {
                        disabled(1),
                        enabled(2)
                    }
        MAX-ACCESS  read-write
        STATUS      current
        DESCRIPTION "This object allows the switch to set privilege level
                     of the session based on the received configuration
                     variable from the authentication server. For RADIUS, the
                     Service-Type attribute's configured value on the server
                     should be 6-Administrative for manager's privilege level,
                     or 7-NAS-prompt for the user/operator privilege level."
        DEFVAL    {1}
        ::= { hpSwitchAuthenticationConfig 2 }

    hpSwitchAuthenticationEncryptCredentialsMethod OBJECT-TYPE
        SYNTAX      INTEGER {
                        none (0),
                        aes256cbc (1)
                    }
        MAX-ACCESS  read-write
        STATUS      current
        DESCRIPTION "This object determines the methods used to encrypt
                    passwords configured on this device."
        DEFVAL      { 0 }
        ::= { hpSwitchAuthenticationConfig 3 }

    hpSwitchAuthLockoutDelay OBJECT-TYPE
        SYNTAX      Integer32 (0..3600)
        MAX-ACCESS  read-write
        STATUS      current
        DESCRIPTION "The number of seconds after repeated login failures
                     before a user may again attempt login, and the period
                     within which login rate is limited. When the value is set 0,
                     the login rate limit feature is disabled."
        DEFVAL      { 0 }
        ::= { hpSwitchAuthenticationConfig 4 }
		
	hpSwitchMinimumPasswordLength OBJECT-TYPE
        SYNTAX      Integer32 (0..1024)
        MAX-ACCESS  read-write
        STATUS      current
        DESCRIPTION "Minimum number of permissible characters required
                     to set a new password for manager, operator, or
                     local management privilege user. The exact range
                     of valid values for this object is implementation
                     dependent; consult the product documentation to
                     determine the supported range for a specific
                     product."
        ::= { hpSwitchAuthenticationConfig 5 }

    hpSwitchAuthAllowVlanTagged OBJECT-TYPE
        SYNTAX      TruthValue
        MAX-ACCESS  read-write
        STATUS      current
        DESCRIPTION "When set to 'true', tagged VLAN membership changes
		     are immediately applied on AAA enabled ports.
		     By default, VLAN changes are postponed when there
		     are authenticated clients connected on the port."
        DEFVAL      { false }
        ::= { hpSwitchAuthenticationConfig 6 }

    hpSwitchAuthenTable OBJECT-TYPE
        SYNTAX      SEQUENCE OF HpSwitchAuthenEntry
        MAX-ACCESS  not-accessible
        STATUS      current
        DESCRIPTION "This table lists the authentication methods to be
                    tried for granting different access levels through
                    various access tasks."
        ::= { hpSwitchAuthenticationMIB 2 }

    hpSwitchAuthenEntry OBJECT-TYPE 
        SYNTAX      HpSwitchAuthenEntry
        MAX-ACCESS  not-accessible
        STATUS      current
        DESCRIPTION "An Authentication Method Table Entry."
        INDEX       { hpSwitchAuthenIndex }
        ::= {hpSwitchAuthenTable 1}

    HpSwitchAuthenEntry ::=
        SEQUENCE {
            hpSwitchAuthenIndex                  INTEGER,
            hpSwitchAuthenLoginPrimary           INTEGER,
            hpSwitchAuthenLoginSecondary         INTEGER,
            hpSwitchAuthenEnablePrimary          INTEGER,
            hpSwitchAuthenEnableSecondary        INTEGER,
            hpSwitchAuthenLoginServerGroupName   DisplayString,
            hpSwitchAuthenEnableServerGroupName  DisplayString
        }

    hpSwitchAuthenIndex OBJECT-TYPE
        SYNTAX      INTEGER {
                        console(1),
                        telnet(2),
                        ieee8021X(3),
                        webui(4),
                        ssh(5),
                        webauth(6),
                        macauth(7),
			snmp(8),
			localMacAuth(9)
                    }
        MAX-ACCESS  not-accessible
        STATUS      current
        DESCRIPTION "Signifies the access task for which authentication
                    methods are listed in this entry."
        ::= {hpSwitchAuthenEntry 1}

    hpSwitchAuthenLoginPrimary OBJECT-TYPE
        SYNTAX      INTEGER {
                        local(1),
                        tacacs(2),
                        radius(3),
                        radiusEap(4),
                        radiusChap(5),
                        sshRsa(6),
                        radiusPeapMSChapv2(7)
                    }
        MAX-ACCESS  read-write
        STATUS      current
        DESCRIPTION "The value of this object indicates the primary login 
                     authentication mechanism. When user logs in, the 
                     authentication method configured by this object will 
                     be tried first."
        ::= { hpSwitchAuthenEntry 2 }

    hpSwitchAuthenLoginSecondary OBJECT-TYPE
        SYNTAX      INTEGER {
                        local(1),
                        none(2),
                        authorized(3),
                        cachedReauth(4) 
                    }
        MAX-ACCESS  read-write
        STATUS      current
        DESCRIPTION "The value of this object indicates the secondary 
                     login authentication mechanism, i.e whether Local
                     or Authorized will be tried in case the primary 
                     authentication results in an error.The Local authentication 
                     method uses the credential database on the switch.  
                     The Authorized authentication method will be granted access 
                     without authenticating. The cachedReauth authentication method 
                     will grant access in case of reauthentication retaining the 
                     current session attributes."
        ::= { hpSwitchAuthenEntry 3 }

    hpSwitchAuthenEnablePrimary OBJECT-TYPE
        SYNTAX      INTEGER {
                        local(1),
                        tacacs(2),
                        radius(3),
                        sshPubkey(6),
                        radiusPeapMSChapv2(7)
                    }
        MAX-ACCESS  read-write
        STATUS      current
        DESCRIPTION "This object configures the primary authentication mechanism
                    that will be tried first.When a user requests manager-level access"
        ::= { hpSwitchAuthenEntry 4 }

    hpSwitchAuthenEnableSecondary OBJECT-TYPE
        SYNTAX      INTEGER {
                        local(1),
                        none(2),
                        authorized(3)
                    }
        MAX-ACCESS  read-write
        STATUS      current
        DESCRIPTION "This object indicates the secondary login authentication
                    mechanism, i.e whether Local or Authorized will be tried
                    in case the primary authentication results in an error.
                    The authentication method Local uses the credential
                    database on the switch. The Authorized authentication
                    method will be granted access without authenticating."
        ::= { hpSwitchAuthenEntry 5 }

    hpSwitchAuthenLoginServerGroupName OBJECT-TYPE
        SYNTAX      DisplayString (SIZE(0..255))
        MAX-ACCESS  read-write
        STATUS      current
        DESCRIPTION "The name that defines the RADIUS server group that this
                     authentication method is associated with. The
                     current maximum length is 12."
        ::= { hpSwitchAuthenEntry 6 }

    hpSwitchAuthenEnableServerGroupName OBJECT-TYPE
        SYNTAX      DisplayString (SIZE(0..255))
        MAX-ACCESS  read-write
        STATUS      current
        DESCRIPTION "The name that defines the RADIUS server group that this
                     authentication method is associated with. The
                     current maximum length is 12."
        ::= { hpSwitchAuthenEntry 7 }

-- ------------------------------------------------------------
    -- Configuration support for TACACS+ Protocol
-- ------------------------------------------------------------

    hpSwitchTacacsConfig 
        OBJECT IDENTIFIER ::= { hpSwitchAuthenticationMIB 3 }

    hpSwitchTacacsTimeout OBJECT-TYPE
        SYNTAX      Integer32 (1..255)
        MAX-ACCESS  read-write
        STATUS      current
        DESCRIPTION "The duration in seconds to wait for a response from 
                    the TACACS+ server host."
        DEFVAL { 5 }
        ::= { hpSwitchTacacsConfig 1 }

    hpSwitchTacacsAuthKey OBJECT-TYPE
        SYNTAX      OCTET STRING (SIZE(0..100))
        MAX-ACCESS  read-write
        STATUS      current
        DESCRIPTION "The key used in encrypting the packets passed between
                    the TACACS+ server and the client. This key must match
                    the one configured on the server."
        ::= { hpSwitchTacacsConfig 2 }

    hpSwitchTacacsAuthKeyEncrypted OBJECT-TYPE
        SYNTAX      OCTET STRING (SIZE(0..256))
        MAX-ACCESS  read-write
        STATUS      current
        DESCRIPTION "An encrypted form of the key used in encrypting the
                    packets passed between the TACACS+ server and the client.
                    This key must match the one configured on the server.
                    This object may only be read or written when
                    hpSwitchAuthenticationEncryptCredentialsMethod is set to a
                    value other than none(0). At most one of
                    hpSwitchTacacsAuthKey and hpSwitchTacacsAuthKeyEncrypted
                    may be set in any transaction. This object should only be
                    written with an encrypted key previously read from a
                    compatible HP Networking device."
        ::= { hpSwitchTacacsConfig 3 }

    hpSwitchTacacsServersTable OBJECT-TYPE
        SYNTAX      SEQUENCE OF HpSwitchTacacsServersEntry
        MAX-ACCESS  not-accessible
        STATUS      current
        DESCRIPTION "This table lists a maximum of 3 TACACS+ servers."
        ::= { hpSwitchAuthenticationMIB 4 }

    hpSwitchTacacsServersEntry OBJECT-TYPE
        SYNTAX      HpSwitchTacacsServersEntry
        MAX-ACCESS  not-accessible
        STATUS      current
        DESCRIPTION "A TACACS+ server table entry."
        INDEX       { hpSwitchTacacsServerIndex }
        ::= { hpSwitchTacacsServersTable 1 }

    HpSwitchTacacsServersEntry ::=
        SEQUENCE {
            hpSwitchTacacsServerIndex        Integer32,
            hpSwitchTacacsServerIpAddr       IpAddress,
            hpSwitchTacacsServerKey          OCTET STRING,
            hpSwitchTacacsServerStatus       RowStatus,
            hpSwitchTacacsServerIsOobm       TruthValue,
            hpSwitchTacacsServerKeyEncrypted OCTET STRING
        }

    hpSwitchTacacsServerIndex OBJECT-TYPE
        SYNTAX      Integer32 (1..65535)
        MAX-ACCESS  not-accessible
        STATUS      current
        DESCRIPTION "The index value which uniquely identifies a row in
                    the TACACS+ Servers Table."
        ::= { hpSwitchTacacsServersEntry 1 }

    hpSwitchTacacsServerIpAddr OBJECT-TYPE
        SYNTAX      IpAddress
        MAX-ACCESS  read-create
        STATUS      current
        DESCRIPTION "The IP address of a TACACS+ Server."
        ::= { hpSwitchTacacsServersEntry 2 }

    hpSwitchTacacsServerKey OBJECT-TYPE
        SYNTAX      OCTET STRING (SIZE(0..100))
        MAX-ACCESS  read-create
        STATUS      current
        DESCRIPTION "The key used in encrypting the packets passed between
                    the TACACS+ server and the client. This key must match
                    the one configured on the server."
        ::= { hpSwitchTacacsServersEntry 3 }

    hpSwitchTacacsServerStatus OBJECT-TYPE
        SYNTAX      RowStatus
        MAX-ACCESS  read-create
        STATUS      current
        DESCRIPTION "Status of Servers Table row."
        ::= { hpSwitchTacacsServersEntry 4 }

    hpSwitchTacacsServerIsOobm OBJECT-TYPE
        SYNTAX      TruthValue
        MAX-ACCESS  read-create
        STATUS      current
        DESCRIPTION "This object indicates whether this TACACS+ Server
                    is reachable over OOBM (Out Of Band Management) 
                    interface or not. This mib object will be applicable
                    only if there is a physical OOBM port on the device."
       DEFVAL      {false}
        ::= { hpSwitchTacacsServersEntry 5 }

    hpSwitchTacacsServerKeyEncrypted OBJECT-TYPE
        SYNTAX      OCTET STRING (SIZE(0..256))
        MAX-ACCESS  read-create
        STATUS      current
        DESCRIPTION "An encrypted form of the key used in encrypting the
                    packets passed between the TACACS+ server and the client.
                    This key must match the one configured on the server.
                    This object may only be read or written when
                    hpSwitchAuthenticationEncryptCredentialsMethod is set to a
                    value other than none(0). At most one of
                    hpSwitchTacacsServerKey and hpSwitchTacacsServerKeyEncrypted
                    may be set in any transaction. This object should only be
                    written with an encrypted key previously read from a
                    compatible HP Networking device."
        ::= { hpSwitchTacacsServersEntry 6 }

-- ------------------------------------------------------------
    -- Status support for TACACS+ Protocol
-- ------------------------------------------------------------

    hpTacacsStatsServersTable OBJECT-TYPE
        SYNTAX      SEQUENCE OF HpTacacsStatsServersEntry
        MAX-ACCESS  not-accessible
        STATUS      current
        DESCRIPTION "A table containing statistics for the configured
                    TACACS+ servers."
        ::= { hpSwitchAuthenticationMIB 5 }

    hpTacacsStatsServersEntry OBJECT-TYPE
        SYNTAX      HpTacacsStatsServersEntry
        MAX-ACCESS  not-accessible
        STATUS      current
        DESCRIPTION "The information associated with each row in the
                    TACACS+ servers table."
        INDEX       { hpTacacsStatsServerIndex }
        ::= { hpTacacsStatsServersTable 1 }

    HpTacacsStatsServersEntry ::=
        SEQUENCE {
            hpTacacsStatsServerIndex          Integer32,
            hpTacacsStatsTacacsServerIpAddr   IpAddress,
            hpTacacsStatsNumSessOpened        Counter32,
            hpTacacsStatsNumSessClosed        Counter32,
            hpTacacsStatsNumSessAborted       Counter32,
            hpTacacsStatsNumSessErrors        Counter32,
            hpTacacsStatsNumPktsIn            Counter32,
            hpTacacsStatsNumPktsOut           Counter32
        }

    hpTacacsStatsServerIndex OBJECT-TYPE
        SYNTAX      Integer32 (1..65535)
        MAX-ACCESS  not-accessible
        STATUS      current
        DESCRIPTION "The index identifying the row in the table."
        ::= { hpTacacsStatsServersEntry 1 }

    hpTacacsStatsTacacsServerIpAddr OBJECT-TYPE
        SYNTAX      IpAddress
        MAX-ACCESS  read-only
        STATUS      current
        DESCRIPTION "The IP address of a TACACS+ Server."
        ::= { hpTacacsStatsServersEntry 2 }

    hpTacacsStatsNumSessOpened OBJECT-TYPE
        SYNTAX      Counter32
        MAX-ACCESS  read-only
        STATUS      current
        DESCRIPTION "The number of authentication sessions opened with
                    this server."
        ::= { hpTacacsStatsServersEntry 3 }

    hpTacacsStatsNumSessClosed OBJECT-TYPE
        SYNTAX      Counter32
        MAX-ACCESS  read-only
        STATUS      current
        DESCRIPTION "The number of authentication sessions closed
                    (i.e. Passed/Failed) with this server."
        ::= { hpTacacsStatsServersEntry 4 }

    hpTacacsStatsNumSessAborted OBJECT-TYPE
        SYNTAX      Counter32
        MAX-ACCESS  read-only
        STATUS      current
        DESCRIPTION "The number of authentication sessions aborted with
                    this server."
        ::= { hpTacacsStatsServersEntry 5 }

    hpTacacsStatsNumSessErrors OBJECT-TYPE
        SYNTAX      Counter32
        MAX-ACCESS  read-only
        STATUS      current
        DESCRIPTION "The number of authentication sessions with this
                    server that ended in an error."
        ::= { hpTacacsStatsServersEntry 6 }

    hpTacacsStatsNumPktsIn OBJECT-TYPE
        SYNTAX      Counter32
        MAX-ACCESS  read-only
        STATUS      current
        DESCRIPTION "The number of packets received from this server."
        ::= { hpTacacsStatsServersEntry 7 }

    hpTacacsStatsNumPktsOut OBJECT-TYPE
        SYNTAX      Counter32
        MAX-ACCESS  read-only
        STATUS      current
        DESCRIPTION "The number of packets sent to this server."
        ::= { hpTacacsStatsServersEntry 8 }

-- ------------------------------------------------------------
    -- Configuration support for RADIUS Protocol
-- ------------------------------------------------------------

    hpSwitchRadiusConfig OBJECT IDENTIFIER ::= { hpSwitchAuthenticationMIB 6 }

    hpSwitchRadiusDeadTime OBJECT-TYPE
        SYNTAX      Integer32 (0..1440)
        MAX-ACCESS  read-write
        STATUS      current
        DESCRIPTION "The length of time in minutes a RADIUS server is skipped
                    over by transaction requests (from 0 up to 24 hours). 
                    Used to improve RADIUS response times when some servers might
                    be unavailable."
        DEFVAL { 0 }
        ::= { hpSwitchRadiusConfig 1 }

    hpSwitchRadiusTimeout OBJECT-TYPE
        SYNTAX      Integer32 (1..15)
        MAX-ACCESS  read-write
        STATUS      current
        DESCRIPTION "The duration in seconds to wait for a response from 
                    the RADIUS server host."
        DEFVAL { 5 }
        ::= { hpSwitchRadiusConfig 2 }

    hpSwitchRadiusRetransmitAttempts OBJECT-TYPE
        SYNTAX      Integer32 (1..5)
        MAX-ACCESS  read-write
        STATUS      current
        DESCRIPTION "Maximum number of retransmission attempts."
        DEFVAL { 3 }
        ::= { hpSwitchRadiusConfig 3 }

    hpSwitchRadiusAuthKey OBJECT-TYPE
        SYNTAX      OCTET STRING (SIZE(0..100))
        MAX-ACCESS  read-write
        STATUS      current
        DESCRIPTION "The key used in encrypting the packets passed between
                    the RADIUS server and the client. This key must match
                    the one configured on the server."
        ::= { hpSwitchRadiusConfig 4 }

    hpSwitchRadiusDynAutzPortNumber OBJECT-TYPE
        SYNTAX      Integer32 (1..65535)
        MAX-ACCESS  read-write
        STATUS      current
        DESCRIPTION "The UDP port number to listen for Disconnect and 
                    Change-of-Authorization messages."
        REFERENCE  "RFC 3576"
        DEFVAL    {3799}
        ::= { hpSwitchRadiusConfig 5 }

    hpSwitchRadiusAuthKeyEncrypted OBJECT-TYPE
        SYNTAX      OCTET STRING (SIZE(0..256))
        MAX-ACCESS  read-write
        STATUS      current
        DESCRIPTION "An encrypted form of the key used in encrypting the
                    packets passed between the RADIUS server and the client.
                    This key must match the one configured on the server.
                    This object may only be read or written when
                    hpSwitchAuthenticationEncryptCredentialsMethod is set to a
                    value other than none(0). At most one of
                    hpSwitchRadiusAuthKey and hpSwitchRadiusAuthKeyEncrypted
                    may be set in any transaction. This object should only be
                    written with an encrypted key previously read from a
                    compatible HP Networking device."
        ::= { hpSwitchRadiusConfig 6 }

    hpSwitchRadiusServerTable OBJECT-TYPE
        SYNTAX      SEQUENCE OF HpSwitchRadiusServerEntry
        MAX-ACCESS  not-accessible
        STATUS      current
        DESCRIPTION "This table lists a maximum of 3 RADIUS servers."
        ::= { hpSwitchAuthenticationMIB 7 }

    hpSwitchRadiusServerEntry OBJECT-TYPE
        SYNTAX      HpSwitchRadiusServerEntry
        MAX-ACCESS  not-accessible
        STATUS      current
        DESCRIPTION "A RADIUS server table entry."
        INDEX       { hpSwitchRadiusServerIndex }
        ::= { hpSwitchRadiusServerTable 1 }

    HpSwitchRadiusServerEntry ::=
        SEQUENCE {
            hpSwitchRadiusServerIndex             Integer32,
            hpSwitchRadiusServerIpAddr            IpAddress,
            hpSwitchRadiusServerKey               OCTET STRING,
            hpSwitchRadiusServerAuthPortNumber    Integer32,
            hpSwitchRadiusServerAcctPortNumber    Integer32,
            hpSwitchRadiusServerDynAutzEnabled    TruthValue,
            hpSwitchRadiusServerDynAutzTimeWindow Integer32,
            hpSwitchRadiusServerStatus            RowStatus,
            hpSwitchRadiusServerIsOobm            TruthValue,
            hpSwitchRadiusServerKeyEncrypted      OCTET STRING,
            hpSwitchRadiusServerAddrType          InetAddressType,
            hpSwitchRadiusServerAddress           InetAddress
        }

    hpSwitchRadiusServerIndex OBJECT-TYPE
        SYNTAX      Integer32 (1..65535)
        MAX-ACCESS  not-accessible
        STATUS      current
        DESCRIPTION "The index value which uniquely identifies a row in
                    the RADIUS Servers Table."
        ::= { hpSwitchRadiusServerEntry 1 }

    hpSwitchRadiusServerIpAddr OBJECT-TYPE
        SYNTAX      IpAddress
        MAX-ACCESS  read-create
        STATUS      deprecated 
        DESCRIPTION "The IP address of a RADIUS Server. When the RADIUS server 
                     has been configured with IPv6 address, the value of 
                     this object will be set to Null."
        ::= { hpSwitchRadiusServerEntry 2 }

    hpSwitchRadiusServerKey OBJECT-TYPE
        SYNTAX      OCTET STRING (SIZE(0..100))
        MAX-ACCESS  read-create
        STATUS      current
        DESCRIPTION "The key used in encrypting the packets passed between
                    the RADIUS server and the client. This key must match
                    the one configured on the server."
        ::= { hpSwitchRadiusServerEntry 3 }

    hpSwitchRadiusServerAuthPortNumber OBJECT-TYPE
        SYNTAX      Integer32 (1..65535)
        MAX-ACCESS  read-create
        STATUS      current
        DESCRIPTION "The UDP destination port number to use for sending
                    authentication requests to this RADIUS Server."
        ::= { hpSwitchRadiusServerEntry 4 }

    hpSwitchRadiusServerAcctPortNumber OBJECT-TYPE
        SYNTAX      Integer32 (1..65535)
        MAX-ACCESS  read-create
        STATUS      current
        DESCRIPTION "The UDP destination port number to use for sending
                    accounting requests to this RADIUS server."
        ::= { hpSwitchRadiusServerEntry 5 }

    hpSwitchRadiusServerDynAutzEnabled OBJECT-TYPE
        SYNTAX      TruthValue
        MAX-ACCESS  read-create
        STATUS      current
        DESCRIPTION "This object indicates whether Dynamic Authorization
                    messages (Disconnect-Requests and CoA-Requests) are
                    authorized for processing from this RADIUS Server."
        DEFVAL    {false}
        ::= { hpSwitchRadiusServerEntry 6 }

    hpSwitchRadiusServerDynAutzTimeWindow OBJECT-TYPE
        SYNTAX      Integer32 (0..65535)
        MAX-ACCESS  read-create
        STATUS      current
        DESCRIPTION "A non-zero value indicates that the Event-Timestamp
                    attribute must be used in the dynamic authorization
                    communication exchange between the NAS and the RADIUS
                    server. Such a value determines the time window (in
                    seconds) within which RADIUS packets carrying the 
                    Event-Timestamp attribute will be considered as current
                    and accepted for processing by the NAS and the RADIUS 
                    Server. Zero value disables checking for the 
                    Event-Timestamp attribute. The default time window 
                    is 300 seconds."
        REFERENCE  "RFC 3576"
        DEFVAL    {300}
        ::= { hpSwitchRadiusServerEntry 7 }

    hpSwitchRadiusServerStatus OBJECT-TYPE
        SYNTAX      RowStatus
        MAX-ACCESS  read-create
        STATUS      current
        DESCRIPTION "Status of Servers Table row."
        ::= { hpSwitchRadiusServerEntry 8 }

    hpSwitchRadiusServerIsOobm OBJECT-TYPE
        SYNTAX      TruthValue
        MAX-ACCESS  read-create
        STATUS      current
        DESCRIPTION "This object indicates whether this RADIUS Server
                    is reachable over OOBM (Out Of Band Management) 
                    interface or not. This mib object will be applicable
                    only if there is a physical OOBM port on the device."
        DEFVAL    {false}
        ::= { hpSwitchRadiusServerEntry 9 }

    hpSwitchRadiusServerKeyEncrypted OBJECT-TYPE
        SYNTAX      OCTET STRING (SIZE(0..256))
        MAX-ACCESS  read-create
        STATUS      current
        DESCRIPTION "An encrypted form of the key used in encrypting the
                    packets passed between the RADIUS server and the client.
                    This key must match the one configured on the server.
                    This object may only be read or written when
                    hpSwitchAuthenticationEncryptCredentialsMethod is set to a
                    value other than none(0). At most one of
                    hpSwitchRadiusServerKey and hpSwitchRadiusServerKeyEncrypted
                    may be set in any transaction. This object should only be
                    written with an encrypted key previously read from a
                    compatible HP Networking device."
        ::= { hpSwitchRadiusServerEntry 10 }
 
   hpSwitchRadiusServerAddrType OBJECT-TYPE
        SYNTAX      InetAddressType
        MAX-ACCESS  read-create
        STATUS      current
        DESCRIPTION "Type of RADIUS Server IP Address stored in
                     hpSwitchRadiusServerAddress."
        ::= { hpSwitchRadiusServerEntry 11 }

    hpSwitchRadiusServerAddress OBJECT-TYPE
        SYNTAX      InetAddress
        MAX-ACCESS  read-create
        STATUS      current
        DESCRIPTION "The IPv4 or IPv6 Address of the RADIUS server."
        ::= { hpSwitchRadiusServerEntry 12 }


-- The 802.1X tables are deprecated

-- ------------------------------------------------------------
-- Key Management Subsystem chain configuration table
-- ------------------------------------------------------------

    hpSwitchKmsChainConfigTable OBJECT-TYPE
         SYNTAX      SEQUENCE OF HpSwitchKmsChainConfigEntry
         MAX-ACCESS  not-accessible
         STATUS      current
         DESCRIPTION "This table contains configuration objects for
                      Key Management Subsystem chains."
    ::= { hpSwitchAuthenticationMIB 15 }
 
-- ------------------------------------------------------------
-- Key Management Subsystem chain configuration entry
-- ------------------------------------------------------------

    hpSwitchKmsChainConfigEntry OBJECT-TYPE
         SYNTAX      HpSwitchKmsChainConfigEntry
         MAX-ACCESS  not-accessible
         STATUS      current
         DESCRIPTION "KMS chain configuration table entry."
         INDEX { hpSwitchKmsChainId }
    ::= { hpSwitchKmsChainConfigTable 1 }
 
    HpSwitchKmsChainConfigEntry ::=
         SEQUENCE {
            hpSwitchKmsChainId         Integer32,
            hpSwitchKmsChainName       DisplayString,
            hpSwitchKmsChainKeys       Gauge32,
            hpSwitchKmsChainActiveKeys Gauge32,
            hpSwitchKmsChainExpKeys    Gauge32,
            hpSwitchKmsChainStatus     RowStatus
         }

    hpSwitchKmsChainId OBJECT-TYPE
         SYNTAX      Integer32 (0..32767)
         MAX-ACCESS  not-accessible
         STATUS      current
         DESCRIPTION "This object is the KMS chain index. Do not rely
                      on it since it may be removed in the future, when
                      it is possible to use the object hpSwitchKmsChainName 
                      as the index."
    ::= { hpSwitchKmsChainConfigEntry 1 }

    hpSwitchKmsChainName OBJECT-TYPE
         SYNTAX      DisplayString (SIZE(1..32))
         MAX-ACCESS  read-create
         STATUS      current
         DESCRIPTION "This object configures the KMS chain name." 
    ::= { hpSwitchKmsChainConfigEntry 2 }

    hpSwitchKmsChainKeys OBJECT-TYPE
         SYNTAX      Gauge32
         MAX-ACCESS  read-only
         STATUS      current
         DESCRIPTION "Returns the number of keys in the KMS chain." 
    ::= { hpSwitchKmsChainConfigEntry 4 }

    hpSwitchKmsChainActiveKeys OBJECT-TYPE
         SYNTAX      Gauge32
         MAX-ACCESS  read-only
         STATUS      current
         DESCRIPTION "Returns the number of active keys in the KMS chain."
    ::= { hpSwitchKmsChainConfigEntry 5 }

    hpSwitchKmsChainExpKeys OBJECT-TYPE
         SYNTAX      Gauge32
         MAX-ACCESS  read-only
         STATUS      current
         DESCRIPTION "Returns the number of expired keys in the KMS chain."
    ::= { hpSwitchKmsChainConfigEntry 6 }

    hpSwitchKmsChainStatus OBJECT-TYPE
        SYNTAX      RowStatus
        MAX-ACCESS  read-create
        STATUS      current
        DESCRIPTION "The status of the row in the KMS chain configuration table."
                     
    ::= { hpSwitchKmsChainConfigEntry 7 }

-- ------------------------------------------------------------
-- Key Management Subsystem key configuration table
-- ------------------------------------------------------------

    hpSwitchKmsKeyConfigTable OBJECT-TYPE
         SYNTAX      SEQUENCE OF HpSwitchKmsKeyConfigEntry
         MAX-ACCESS  not-accessible
         STATUS      current
         DESCRIPTION "This table contains the configuration objects for
                      the Key Management Subsystem."
    ::= { hpSwitchAuthenticationMIB 16 }
 
-- ------------------------------------------------------------
-- Key Management Subsystem key configuration entry
-- ------------------------------------------------------------

    hpSwitchKmsKeyConfigEntry OBJECT-TYPE
         SYNTAX      HpSwitchKmsKeyConfigEntry
         MAX-ACCESS  not-accessible
         STATUS      current
         DESCRIPTION "KMS configuration table entry."
         INDEX { hpSwitchKmsKeyChainId, hpSwitchKmsKeyId }
    ::= { hpSwitchKmsKeyConfigTable 1 }
 
    HpSwitchKmsKeyConfigEntry ::=
         SEQUENCE {
            hpSwitchKmsKeyChainId      Integer32,
            hpSwitchKmsKeyId           Integer32,
            hpSwitchKmsKeyStr          OCTET STRING,
            hpSwitchKmsKeyStartTime    Unsigned32,
            hpSwitchKmsKeyStopTime     Unsigned32,
            hpSwitchKmsKeyTxStartTime  Unsigned32,
            hpSwitchKmsKeyTxStopTime   Unsigned32,
            hpSwitchKmsKeyStatus       RowStatus,
            hpSwitchKmsKeyEncrypted    OCTET STRING
         }

    hpSwitchKmsKeyChainId OBJECT-TYPE
         SYNTAX      Integer32 (0..32767)
         MAX-ACCESS  not-accessible
         STATUS      current
         DESCRIPTION "This object is the KMS chain index. Do not rely
                      on it since it may be removed in the future, when
                      it is possible to use the object hpSwitchKmsChainName
                      as the index."
    ::= { hpSwitchKmsKeyConfigEntry 1 }

    hpSwitchKmsKeyId OBJECT-TYPE
         SYNTAX      Integer32 (0..255)
         MAX-ACCESS  not-accessible
         STATUS      current
         DESCRIPTION "This object is the KMS key index."
    ::= { hpSwitchKmsKeyConfigEntry 2 }

    hpSwitchKmsKeyStr OBJECT-TYPE
         SYNTAX      OCTET STRING (SIZE(0..16))
         MAX-ACCESS  read-create
         STATUS      current
         DESCRIPTION "This object configures the KMS key chain name." 
    ::= { hpSwitchKmsKeyConfigEntry 3 }

    hpSwitchKmsKeyStartTime OBJECT-TYPE
         SYNTAX      Unsigned32
         MAX-ACCESS  read-create
         STATUS      current
         DESCRIPTION "Start time of the KMS key." 
    ::= { hpSwitchKmsKeyConfigEntry 4 }

    hpSwitchKmsKeyStopTime OBJECT-TYPE
         SYNTAX      Unsigned32
         MAX-ACCESS  read-create
         STATUS      current
         DESCRIPTION "Stop time of the KMS key." 
    ::= { hpSwitchKmsKeyConfigEntry 5 }

    hpSwitchKmsKeyTxStartTime OBJECT-TYPE
         SYNTAX      Unsigned32
         MAX-ACCESS  read-create
         STATUS      current
         DESCRIPTION "Start time of the transmission for the KMS key." 
    ::= { hpSwitchKmsKeyConfigEntry 6 }

    hpSwitchKmsKeyTxStopTime OBJECT-TYPE
         SYNTAX      Unsigned32
         MAX-ACCESS  read-create
         STATUS      current
         DESCRIPTION "Stop time of the transmission for the KMS key." 
    ::= { hpSwitchKmsKeyConfigEntry 7 }

    hpSwitchKmsKeyStatus OBJECT-TYPE
        SYNTAX      RowStatus
        MAX-ACCESS  read-create
        STATUS      current
        DESCRIPTION "Row Status of the KMS chain configuration table."
    ::= { hpSwitchKmsKeyConfigEntry 8 }

    hpSwitchKmsKeyEncrypted OBJECT-TYPE
         SYNTAX      OCTET STRING (SIZE(0..256))
         MAX-ACCESS  read-create
         STATUS      current
         DESCRIPTION "An encrypted form of the KMS key. This object may only be
                     read or written when
                     hpSwitchAuthenticationEncryptCredentialsMethod is set to a
                     value other than none(0). At most one of
                     hpSwitchKmsKeyStr and hpSwitchKmsKeyEncrypted may be set
                     in any transaction. This object should only be written
                     with an encrypted key previously read from a compatible
                     HP Networking device."
    ::= { hpSwitchKmsKeyConfigEntry 9 }

-- ------------------------------------------------------------
-- OSPF Interface authentication configuration table
-- ------------------------------------------------------------

    hpSwitchOspfIfAuthTable OBJECT-TYPE
         SYNTAX      SEQUENCE OF HpSwitchOspfIfAuthEntry
         MAX-ACCESS  not-accessible
         STATUS      current
         DESCRIPTION "This table supplements the OSPF interface 
                      configuration table."
    ::= { hpSwitchAuthenticationMIB 17 }
 
    hpSwitchOspfIfAuthEntry OBJECT-TYPE
         SYNTAX      HpSwitchOspfIfAuthEntry
         MAX-ACCESS  not-accessible
         STATUS      current
         DESCRIPTION "OSPF interface authentication 
                      configuration table entry."
         AUGMENTS { ospfIfEntry }
    ::= { hpSwitchOspfIfAuthTable 1 }
 
    HpSwitchOspfIfAuthEntry ::=
         SEQUENCE {
            hpSwitchOspfIfAuthChain DisplayString
         }

    hpSwitchOspfIfAuthChain OBJECT-TYPE
         SYNTAX      DisplayString (SIZE(0..32))
         MAX-ACCESS  read-create
         STATUS      current
         DESCRIPTION "This object configures the KMS chain name for
                      OSPF interfaces." 
    ::= { hpSwitchOspfIfAuthEntry 1 }

-- ------------------------------------------------------------
-- OSPF Virtual Interface authentication configuration table
-- ------------------------------------------------------------

    hpSwitchOspfVirtIfAuthTable OBJECT-TYPE
         SYNTAX      SEQUENCE OF HpSwitchOspfVirtIfAuthEntry
         MAX-ACCESS  not-accessible
         STATUS      current
         DESCRIPTION "This table supplements the OSPF virtual 
                      interface configuration table."
    ::= { hpSwitchAuthenticationMIB 18 }
 
    hpSwitchOspfVirtIfAuthEntry OBJECT-TYPE
         SYNTAX      HpSwitchOspfVirtIfAuthEntry
         MAX-ACCESS  not-accessible
         STATUS      current
         DESCRIPTION "OSPF virtual interface authentication 
                      configuration table entry."
         AUGMENTS { ospfVirtIfEntry }
    ::= { hpSwitchOspfVirtIfAuthTable 1 }
 
    HpSwitchOspfVirtIfAuthEntry ::=
         SEQUENCE {
            hpSwitchOspfVirtIfAuthChain DisplayString
         }

    hpSwitchOspfVirtIfAuthChain OBJECT-TYPE
         SYNTAX      DisplayString (SIZE(0..32))
         MAX-ACCESS  read-create
         STATUS      current
         DESCRIPTION "This object configures the KMS chain name for
                      OSPF virtual interfaces." 
    ::= { hpSwitchOspfVirtIfAuthEntry 1 }
            
-- ------------------------------------------------------------
    -- Configuration support for SSL server
-- ------------------------------------------------------------

    hpSwitchSslConfig OBJECT IDENTIFIER ::= { hpSwitchAuthenticationMIB 12 }        
    
    hpSwitchSslAdminStatus OBJECT-TYPE
        SYNTAX      INTEGER {
                        disabled(1),
                        enabled(2)
                    }
        MAX-ACCESS  read-write
        STATUS      current
        DESCRIPTION "This objects specifies the desired operational 
                     status of SSL."
        DEFVAL     {1}
        ::= { hpSwitchSslConfig 1 }   
        

   hpSwitchSslPortNumber OBJECT-TYPE
        SYNTAX      Integer32 (1..65535)
        MAX-ACCESS  read-write
        STATUS      current
        DESCRIPTION "The port number on which the SSL server should listen 
                     for connection requests."
        DEFVAL { 443 }
        ::= { hpSwitchSslConfig 2 } 

-- ------------------------------------------------------------
    -- Configuration support for Certificates 
-- ------------------------------------------------------------
                
    hpSwitchCertConfig OBJECT IDENTIFIER ::= { hpSwitchAuthenticationMIB 13 }        
        
    hpSwitchServerCertificateOperation OBJECT-TYPE
        SYNTAX      INTEGER {
                        none(1),
                        useInstalled(2),
                        createAndUseSelfSigned(3),
                        createCACertReq(4),
                        applyCASignedCert(5),
                        abortCASignedRequest(6)
                    }
        MAX-ACCESS  read-write
        STATUS      current
        DESCRIPTION "When this object is read, it returns the last value that was written.
                     If a value was not set previously, then the object value will be 'none'(1).
                     The object supports the following values and actions: 
                     'none' - no action is taken, null operation.
                     
                     'useInstalled' - This causes the switch to use a previously
                     installed server certificate, if one is present. 

                     'createAndUseSelfSigned' - This causes the switch to 
                     create a new self-signed certificate based on the
                     hpSwitchServerNewCertificate parameters and use it.

                     'createCACertReq' - This causes the switch to create
                     a certificate request, which is to be signed by a CA
                     authority, based on the hpSwitchServerNewCertificate  
                     parameters. The user must subsequently download the signed 
                     certificate to complete certificate creation process.

                     'applyCASignedCert' - This causes the switch to process the
                     user's response to a signed certificate from a CA to complete
                     the certificate creation process. 

                     'abortCASignedRequest' - This causes the switch to abort
                     the certificate request procedure, which was initiated on
                     createAndUseCASigned set."

        ::= { hpSwitchCertConfig 1 }
        
    hpSwitchServerNewRSAKeyOperation OBJECT-TYPE
        SYNTAX      INTEGER {
                        useInstalled(1),
                        createBits512(2),
                        createBits768(3),
                        createBits1024(4),
                        createBits2048(5)
                    }
        MAX-ACCESS  read-write
        STATUS      current
        DESCRIPTION "This object when will returns a value either 'useInstalled'(1) or 
                     'createBits1024'(4). 
                     The value 'useInstalled'(1) is returned when 
                     a certificate RSA key already exists on switch. 
                     The value 'createBits1024'(4) is returned when no certificate RSA key
                     exists on switch. 

                     When user configuresthe values, the value triggers the following action:
                     
                     'useInstalled' - The switch will use the currently configured RSA key
                     that is already present on the switch.
                     
                     'createBits512' - This value is deprecated and no longer supported. 
                     
                     'createBits768' - This value is deprecated and no longer supported.
                     
                     'createBits1024' - This value specifies the creation of a new RSA 
                     key of length 1024-bit.
                     
                     'createBits2048' - This value specifies the creation of a new RSA 
                     key of length 2048-bit."
        ::= { hpSwitchCertConfig 2 }

    hpSwitchServerNewCertificateStartDate OBJECT-TYPE
        SYNTAX      DateAndTime
        MAX-ACCESS  read-write
        STATUS      current
        DESCRIPTION "Specifies the start date of validity for a new server 
                     certificate."
        ::= { hpSwitchCertConfig 3 }

    hpSwitchServerNewCertificateEndDate OBJECT-TYPE
        SYNTAX      DateAndTime
        MAX-ACCESS  read-write
        STATUS     current
        DESCRIPTION "Specifies the end date of validity for a new server 
                     certificate."
        ::= { hpSwitchCertConfig 4 }

    hpSwitchServerNewCertificateCommonName OBJECT-TYPE
        SYNTAX      OCTET STRING (SIZE(1..40))
        MAX-ACCESS  read-write
        STATUS      deprecated
        DESCRIPTION "Specifies the common name for a new server 
                     certificate."
        ::= { hpSwitchCertConfig 5 }

    hpSwitchServerNewCertificateOrgUnit OBJECT-TYPE
        SYNTAX      OCTET STRING (SIZE(1..40))
        MAX-ACCESS  read-write
        STATUS      deprecated
        DESCRIPTION "Specifies the organization for a new server
                     certificate."
        ::= { hpSwitchCertConfig 6 }

    hpSwitchServerNewCertificateOrgName OBJECT-TYPE
        SYNTAX      OCTET STRING (SIZE(1..40))
        MAX-ACCESS  read-write
        STATUS      deprecated
        DESCRIPTION "Specifies the organization name for a new server
                     certificate."
        ::= { hpSwitchCertConfig 7 }

    hpSwitchServerNewCertificateCityName OBJECT-TYPE
        SYNTAX      OCTET STRING (SIZE(1..40))
        MAX-ACCESS  read-write
        STATUS      deprecated
        DESCRIPTION "Specifies the city for a new server certificate."
        ::= { hpSwitchCertConfig 8 }

    hpSwitchServerNewCertificateStateName OBJECT-TYPE
        SYNTAX      OCTET STRING (SIZE(1..40))
        MAX-ACCESS  read-write
        STATUS      deprecated
        DESCRIPTION "Specifies the state for a new server certificate."
        ::= { hpSwitchCertConfig 9 }

    hpSwitchServerNewCertificateCountryCode OBJECT-TYPE
        SYNTAX      OCTET STRING (SIZE(2))
        MAX-ACCESS  read-write
        STATUS     current
        DESCRIPTION "Specifies the 2-letter ISO country code of the server certificate."
        ::= { hpSwitchCertConfig 10 }
    hpSwitchServerNewCertCommonName OBJECT-TYPE
        SYNTAX      OCTET STRING (SIZE(1..200))
        MAX-ACCESS  read-write
        STATUS     current
        DESCRIPTION "Specifies the common name for a new server 
                     certificate."
        ::= { hpSwitchCertConfig 11 }

    hpSwitchServerNewCertOrgUnit OBJECT-TYPE
        SYNTAX      OCTET STRING (SIZE(1..200))
        MAX-ACCESS  read-write
        STATUS     current
        DESCRIPTION "Specifies the organization for a new server
                     certificate."
        ::= { hpSwitchCertConfig 12 }

    hpSwitchServerNewCertOrgName OBJECT-TYPE
        SYNTAX      OCTET STRING (SIZE(1..200))
        MAX-ACCESS  read-write
        STATUS     current
        DESCRIPTION "Specifies the organization name for a new server
                     certificate."
        ::= { hpSwitchCertConfig 13 }

    hpSwitchServerNewCertCityName OBJECT-TYPE
        SYNTAX      OCTET STRING (SIZE(1..200))
        MAX-ACCESS  read-write
        STATUS     current
        DESCRIPTION "Specifies the city for a new server certificate."
        ::= { hpSwitchCertConfig 14 }

    hpSwitchServerNewCertStateName OBJECT-TYPE
        SYNTAX      OCTET STRING (SIZE(1..200))
        MAX-ACCESS  read-write
        STATUS     current
        DESCRIPTION "Specifies the state for a new server certificate."
        ::= { hpSwitchCertConfig 15 }

    hpSwitchServerNewCertKeySizeExists OBJECT-TYPE
        SYNTAX      TruthValue
        MAX-ACCESS  read-write
        STATUS      current
        DESCRIPTION "Specifies whether the given key size already exist."
        DEFVAL      {false}
        ::= { hpSwitchCertConfig 16 }

-- ------------------------------------------------------------
    -- Certificate Status
-- ------------------------------------------------------------
    hpSwitchCertStatus OBJECT IDENTIFIER ::= { hpSwitchAuthenticationMIB  14}

    hpSwitchServerCertificateType OBJECT-TYPE
        SYNTAX      INTEGER {
                        none(1),
                        pendCaSigned(2),
                        selfSigned(3),
                        caSigned(4)
                    }
        MAX-ACCESS  read-only
        STATUS      current
        DESCRIPTION "Specifies the type of server certificate the switch is 
                     currently using as follows:
                     
                    'none' - no server certificate is present.
                    
                    'pendCaSigned' - switch is waiting for user to offer 
                    CA-signed certificate request.
                    
                    'selfSigned' - a self-signed server certificate is being 
                    used.
                    
                    'caSigned' - a CA-signed server certificate is being 
                    used."
        ::= { hpSwitchCertStatus 1 }
    
    hpSwitchServerCertificateRSAKeySize OBJECT-TYPE
        SYNTAX       INTEGER {
                         none(0),
                         bits512(1),
                         bits768(2),
                         bits1024(3),
                         bits2048(4)
                     }
        MAX-ACCESS   read-only
        STATUS       current
        DESCRIPTION  "Specifies the RSA key length of the public key contained 
                      in the certificate as follows:
                      
                      'none'     - no certificate is present
                      'Bits512'  - certificate has a 512-bit public key
                      'Bits768'  - certificate has a 768-bit public key 
                      'Bits1024' - certificate has a 1024-bit public key
                      'Bits2048' - certificate has a 2048-bit public key"
        ::= { hpSwitchCertStatus 2 }                      
        
    hpSwitchServerCertificateSerialNumber  OBJECT-TYPE
        SYNTAX       OCTET STRING (SIZE(0..40))
        MAX-ACCESS   read-only 
        STATUS       current
        DESCRIPTION  "Specifies the serial number of installed server 
                     certificate."
        ::= { hpSwitchCertStatus 3 }

    hpSwitchServerCertificateStartDate OBJECT-TYPE
        SYNTAX       DateAndTime
        MAX-ACCESS   read-only 
        STATUS       current
        DESCRIPTION  "Specifies the start date of validity of installed server 
                     certificate."
        ::= { hpSwitchCertStatus 4 }

    hpSwitchServerCertificateEndDate OBJECT-TYPE
        SYNTAX       DateAndTime
        MAX-ACCESS   read-only
        STATUS       current
        DESCRIPTION  "Specifies the end date of validity of installed server 
                     server certificate."
        ::= { hpSwitchCertStatus 5 }

    hpSwitchServerCertificateCommonName OBJECT-TYPE
        SYNTAX       OCTET STRING (SIZE(0..40))
        MAX-ACCESS   read-only
        STATUS       current
        DESCRIPTION  "Specifies the common name of installed server 
                     certificate."
        ::= { hpSwitchCertStatus 6 }

    hpSwitchServerCertificateOrgUnit OBJECT-TYPE
        SYNTAX       OCTET STRING (SIZE(0..40))
        MAX-ACCESS   read-only
        STATUS      current
        DESCRIPTION  "Specifies the organization of installed server                    
                     certificate."
        ::= { hpSwitchCertStatus 7 }

    hpSwitchServerCertificateOrgName OBJECT-TYPE
        SYNTAX       OCTET STRING (SIZE(0..40))
        MAX-ACCESS   read-only
        STATUS      current
        DESCRIPTION  "Specifies the organization name of installed server                    
                     certificate."
        ::= { hpSwitchCertStatus 8 }

    hpSwitchServerCertificateCityName OBJECT-TYPE
        SYNTAX       OCTET STRING (SIZE(0..40))
        MAX-ACCESS   read-only
        STATUS       current
        DESCRIPTION  "Specifies the city of installed server certificate."
        ::= { hpSwitchCertStatus 9 }

    hpSwitchServerCertificateStateName OBJECT-TYPE
        SYNTAX       OCTET STRING (SIZE(0..40))
MAX-ACCESS   read-only 
STATUS      current
        DESCRIPTION  "Specifies the state of installed server certificate."
        ::= { hpSwitchCertStatus 10 }

    hpSwitchServerCertificateCountryCode OBJECT-TYPE
        SYNTAX       OCTET STRING (SIZE(0..40))
        MAX-ACCESS   read-only
        STATUS       current
        DESCRIPTION  "Specifies the 2-letter ISO country code of installed 
                     server certificate."
        ::= { hpSwitchCertStatus 11 }
        
    hpSwitchServerCertificateFingerprintMD5 OBJECT-TYPE
        SYNTAX       OCTET STRING (SIZE(0..48))
        MAX-ACCESS   read-only
        STATUS       current
        DESCRIPTION  "Specifies the MD5 fingerprint of installed server 
                     certificate."
        ::= { hpSwitchCertStatus 12 }

    hpSwitchServerCertificateFingerprintSHA1 OBJECT-TYPE
        SYNTAX       OCTET STRING (SIZE(0..51))
        MAX-ACCESS   read-only
        STATUS       current
        DESCRIPTION  "Specifies the SHA1 fingerprint of installed server 
                     certificate."
        ::= { hpSwitchCertStatus 13 }        

-- ------------------------------------------------------------
-- User Config Table
-- ------------------------------------------------------------

    hpicfSwitchUserConfigTable OBJECT-TYPE
         SYNTAX      SEQUENCE OF HpicfSwitchUserConfigEntry
         MAX-ACCESS  not-accessible
         STATUS      current
         DESCRIPTION "This table supplements the manager/operator name/password. The manager/operator password are limited to the CLI interface through Console and Menu interface, and web."
    ::= { hpSwitchAuthenticationMIB 19 }

    hpicfSwitchUserConfigEntry OBJECT-TYPE
         SYNTAX      HpicfSwitchUserConfigEntry
         MAX-ACCESS  not-accessible
         STATUS      current
         DESCRIPTION "Manager/operator name/password table entry."
         INDEX { hpicfSwitchUserConfigIndex }
    ::= { hpicfSwitchUserConfigTable 1 }

       HpicfSwitchUserConfigEntry ::=
        SEQUENCE {
            hpicfSwitchUserConfigIndex      Integer32,
            hpicfSwitchUserName             OCTET STRING,
            hpicfSwitchOperatorName         OCTET STRING,
            hpicfSwitchUserPassword         OCTET STRING,
            hpicfSwitchOperatorPassword     OCTET STRING,
            hpicfSwitchUserConfigStatus     RowStatus,
            hpicfSwitchPortAccessName       OCTET STRING,
            hpicfSwitchPortAccessPassword   OCTET STRING,
            hpicfSwitchUserPasswordHashType        INTEGER,
            hpicfSwitchOperatorPasswordHashType    INTEGER,
            hpicfSwitchPortAccessPasswordHashType  INTEGER,
            hpicfSwitchUserPasswordEncrypted       OCTET STRING,
            hpicfSwitchOperatorPasswordEncrypted   OCTET STRING,
            hpicfSwitchPortAccessPasswordEncrypted OCTET STRING,
            hpicfSwitchBypassUsername              INTEGER
        }

    hpicfSwitchUserConfigIndex OBJECT-TYPE
        SYNTAX      Integer32 (1..65535)
        MAX-ACCESS  not-accessible
        STATUS      current
        DESCRIPTION "The index value uniquely identifies a row in the User Config table, currently limited to a value of 1."
        ::= { hpicfSwitchUserConfigEntry 1 }

    hpicfSwitchUserName OBJECT-TYPE
        SYNTAX      OCTET STRING (SIZE(0..1024))
        MAX-ACCESS  read-create
        STATUS      current
        DESCRIPTION "The User Name, in ASCII format. The exact size of
                    this object is implementation dependent; consult
                    the product documentation to determine the supported
                    size for a specific product."
        ::= { hpicfSwitchUserConfigEntry 2 }

    hpicfSwitchOperatorName OBJECT-TYPE
        SYNTAX      OCTET STRING (SIZE(0..1024))
        MAX-ACCESS  read-create
        STATUS      current
        DESCRIPTION "The Operator Name, in ASCII format. The exact size
                    of this object is implementation dependent; consult
                    the product documentation to determine the supported
                    size for a specific product."
        ::= { hpicfSwitchUserConfigEntry 3 }  

    hpicfSwitchUserPassword OBJECT-TYPE
        SYNTAX      OCTET STRING (SIZE(0..1024))
        MAX-ACCESS  read-create
        STATUS      current
        DESCRIPTION "The User Password, in ASCII format. The exact size
                    of this object is implementation dependent; consult
                    the product documentation to determine the supported 
                    size for a specific product."
        ::= { hpicfSwitchUserConfigEntry 4 }

    hpicfSwitchOperatorPassword OBJECT-TYPE
        SYNTAX      OCTET STRING (SIZE(0..1024))
        MAX-ACCESS  read-create
        STATUS      current
        DESCRIPTION "The Operator Password, in ASCII format. The exact
                    size of this object is implementation dependent;
                    consult the product documentation to determine the
                    supported size for a specific product."
        ::= { hpicfSwitchUserConfigEntry 5 }

    hpicfSwitchUserConfigStatus OBJECT-TYPE
        SYNTAX      RowStatus
        MAX-ACCESS  read-create
        STATUS      current
        DESCRIPTION "Status of User Config Table row."
        ::= { hpicfSwitchUserConfigEntry 6 }

    hpicfSwitchPortAccessName OBJECT-TYPE
        SYNTAX      OCTET STRING (SIZE(0..1024))
        MAX-ACCESS  read-create
        STATUS      current
        DESCRIPTION "The Port-Access Name, ASCII format. The exact size
                    of this object is implementation dependent; consult
                    the product documentation to determine the supported
                    size for a specific product."
        ::= { hpicfSwitchUserConfigEntry 7 } 
        

    hpicfSwitchPortAccessPassword OBJECT-TYPE
        SYNTAX      OCTET STRING (SIZE(0..1024))
        MAX-ACCESS  read-create
        STATUS      current
        DESCRIPTION "The Port-Access Password, in ASCII format. The 
                     exact size of this object is implementation 
                     dependent; consult the product documentation to 
                     determine the supported size for a specific 
                     product."
        ::= { hpicfSwitchUserConfigEntry 8 }

    hpicfSwitchUserPasswordHashType OBJECT-TYPE
        SYNTAX      INTEGER{
                       unknown(0),
                       plainText(1),
                       sha1(3)
                   }                    
        MAX-ACCESS  read-create
        STATUS      current
        DESCRIPTION "The hash-type of the User Password."
        DEFVAL      {plainText} 
        ::= { hpicfSwitchUserConfigEntry 9 }

     hpicfSwitchOperatorPasswordHashType OBJECT-TYPE
        SYNTAX      INTEGER{
                       unknown(0),
                       plainText(1),
                       sha1(3)
                   }                    
        MAX-ACCESS  read-create
        STATUS      current
        DESCRIPTION "The hash-type of the Operator Password."
        DEFVAL      {plainText}
        ::= { hpicfSwitchUserConfigEntry 10 }
       
     hpicfSwitchPortAccessPasswordHashType OBJECT-TYPE
        SYNTAX      INTEGER{
                       unknown(0),
                       plainText(1)
                   }
        MAX-ACCESS  read-create
        STATUS      current
        DESCRIPTION "The hash-type of the Port-Access Password."
        DEFVAL      {plainText}
        ::= { hpicfSwitchUserConfigEntry 11 }

    hpicfSwitchUserPasswordEncrypted OBJECT-TYPE
        SYNTAX      OCTET STRING (SIZE(0..256))
        MAX-ACCESS  read-create
        STATUS      current
        DESCRIPTION "An encrypted form of the user password. The exact size
                    of this object is implementation dependent; consult
                    the product documentation to determine the supported 
                    size for a specific product.
                    This object may only be read or written when
                    hpSwitchAuthenticationEncryptCredentialsMethod is set to a
                    value other than none(0). At most one of
                    hpicfSwitchUserPassword and hpicfSwitchUserPasswordEncrypted
                    may be set in any transaction. This object should only be
                    written with an encrypted password previously read from a
                    compatible HP Networking device."
        ::= { hpicfSwitchUserConfigEntry 12 }

    hpicfSwitchOperatorPasswordEncrypted OBJECT-TYPE
        SYNTAX      OCTET STRING (SIZE(0..256))
        MAX-ACCESS  read-create
        STATUS      current
        DESCRIPTION "An encrypted form of the operator password. The exact
                    size of this object is implementation dependent;
                    consult the product documentation to determine the
                    supported size for a specific product.
                    This object may only be read or written when
                    hpSwitchAuthenticationEncryptCredentialsMethod is set to a
                    value other than none(0). At most one of
                    hpicfSwitchOperatorPassword and 
                    hpicfSwitchOperatorPasswordEncrypted may be set in any
                    transaction. This object should only be written with an
                    encrypted password previously read from a compatible
                    HP Networking device."
        ::= { hpicfSwitchUserConfigEntry 13 }

    hpicfSwitchPortAccessPasswordEncrypted OBJECT-TYPE
        SYNTAX      OCTET STRING (SIZE(0..256))
        MAX-ACCESS  read-create
        STATUS      current
        DESCRIPTION "An encrypted form of the port-access password. The 
                     exact size of this object is implementation 
                     dependent; consult the product documentation to 
                     determine the supported size for a specific 
                     product. This object may only be read or written when
                     hpSwitchAuthenticationEncryptCredentialsMethod is set to a
                     value other than none(0). At most one of
                     hpicfSwitchPortAccessPassword and 
                     hpicfSwitchPortAccessPasswordEncrypted may be set in any
                     transaction. This object should only be written with an
                     encrypted password previously read from a compatible
                     HP Networking device."
        ::= { hpicfSwitchUserConfigEntry 14 }
     
    hpicfSwitchBypassUsername OBJECT-TYPE
        SYNTAX      INTEGER {
                       enable(1),
                       disable(2)
                   }
        MAX-ACCESS  read-create
        STATUS      current
        DESCRIPTION "This object allows a user to bypass the username 
                     authentication when the default usernames manager
                     and operator are in use. This allows a user to 
                     log on to the switch using only a password.

                     When non-default usernames are configured, the 
                     authentication will be based on both the username 
                     and password."
        DEFVAL      { disable }
        ::= { hpicfSwitchUserConfigEntry 15 }         

        
-- ------------------------------------------------------------
-- AAA Server Group Table
-- ------------------------------------------------------------

    hpSwitchAAAServerGroupTable OBJECT-TYPE
        SYNTAX      SEQUENCE OF HpSwitchAAAServerGroupEntry
        MAX-ACCESS  not-accessible
        STATUS      current
        DESCRIPTION "This table lists the RADIUS server groups."
        ::= { hpSwitchAuthenticationMIB 20 }

   hpSwitchAAAServerGroupEntry OBJECT-TYPE
       SYNTAX      HpSwitchAAAServerGroupEntry
       MAX-ACCESS  not-accessible
       STATUS      current
       DESCRIPTION "RADIUS server group entry."
          INDEX { hpSwitchAAAServerGroupProtocolType,
                  hpSwitchAAAServerGroupIndex,
                  hpSwitchAAAServerGroupServerIndex }
   ::= { hpSwitchAAAServerGroupTable 1 }

    HpSwitchAAAServerGroupEntry ::=
        SEQUENCE {
            hpSwitchAAAServerGroupProtocolType    INTEGER,
            hpSwitchAAAServerGroupIndex           Integer32,
            hpSwitchAAAServerGroupServerIndex     Integer32,
            hpSwitchAAAServerGroupName            DisplayString,
            hpSwitchAAAServerGroupServerInetType  InetAddressType,
            hpSwitchAAAServerGroupServerInetAddr  InetAddress,
            hpSwitchAAAServerGroupStatus          RowStatus
        }

    hpSwitchAAAServerGroupProtocolType OBJECT-TYPE
        SYNTAX      INTEGER {
                        radius(1),
                        tacacs(2)
                    }
        MAX-ACCESS  not-accessible
        STATUS      current
        DESCRIPTION "This part of the index indicates which protocol
                     server the server group is for.  See the documentation
                     protocols supported."
        ::= { hpSwitchAAAServerGroupEntry 1 }

    hpSwitchAAAServerGroupIndex OBJECT-TYPE
        SYNTAX      Integer32
        MAX-ACCESS  not-accessible
        STATUS      current
        DESCRIPTION "This index indicates the server group in the
                     AAA server group table."
        ::= { hpSwitchAAAServerGroupEntry 2 }

    hpSwitchAAAServerGroupServerIndex OBJECT-TYPE
        SYNTAX      Integer32 
        MAX-ACCESS  not-accessible
        STATUS      current
        DESCRIPTION "The index value which identifies the server in
                     the server group."
        ::= { hpSwitchAAAServerGroupEntry 3 }

    hpSwitchAAAServerGroupName OBJECT-TYPE
        SYNTAX      DisplayString (SIZE(0..255))
        MAX-ACCESS  read-create
        STATUS      current
        DESCRIPTION "The name of a given AAA server group. The current 
                     maximum length is 12."
        ::= { hpSwitchAAAServerGroupEntry 4 }

     hpSwitchAAAServerGroupServerInetType OBJECT-TYPE
         SYNTAX      InetAddressType
         MAX-ACCESS  read-create
         STATUS      current
         DESCRIPTION "The IP Address type of the server.
                      Currently only Ipv4 is supported."
         ::= { hpSwitchAAAServerGroupEntry 5 } 

     hpSwitchAAAServerGroupServerInetAddr OBJECT-TYPE
         SYNTAX      InetAddress
         MAX-ACCESS  read-create
         STATUS      current
         DESCRIPTION "The IP Address of the server."
         ::= { hpSwitchAAAServerGroupEntry 6 } 

     hpSwitchAAAServerGroupStatus OBJECT-TYPE
         SYNTAX      RowStatus
         MAX-ACCESS  read-create
         STATUS      current
         DESCRIPTION "The status of the AAA server group row.
                      Supported values are createAndGo, destroy, and active."
         ::= { hpSwitchAAAServerGroupEntry 7 }

-- ------------------------------------------------------------
-- Local Management Privilege UserNames Table
-- ------------------------------------------------------------

   hpSwitchLocalMgmtPrivUsernamesTable OBJECT-TYPE
        SYNTAX      SEQUENCE OF HpSwitchLocalMgmtPrivUsernamesEntry
        MAX-ACCESS  not-accessible
        STATUS      current
        DESCRIPTION "This table lists the Local Management
                     Privilege user names."
        ::= { hpSwitchAuthenticationMIB 21 }

   hpSwitchLocalMgmtPrivUsernamesEntry OBJECT-TYPE
        SYNTAX      HpSwitchLocalMgmtPrivUsernamesEntry
        MAX-ACCESS  not-accessible
        STATUS      current
        DESCRIPTION "Local Management Usernames entry."
          INDEX { hpSwitchLocalMgmtPrivUsernameIndex }

        ::= { hpSwitchLocalMgmtPrivUsernamesTable 1 }

   HpSwitchLocalMgmtPrivUsernamesEntry ::=
        SEQUENCE {
            hpSwitchLocalMgmtPrivUsernameIndex         Integer32,
            hpSwitchLocalMgmtPrivUsernameStr           OCTET STRING,
            hpSwitchLocalMgmtPrivUsernamePasswdType    INTEGER,
            hpSwitchLocalMgmtPrivUsernamePasswd        OCTET STRING,
            hpSwitchLocalMgmtPrivUsernameGrpIndex      Integer32,
            hpSwitchLocalMgmtPrivUsernameStatus        RowStatus
        }

   hpSwitchLocalMgmtPrivUsernameIndex OBJECT-TYPE
        SYNTAX      Integer32 
        MAX-ACCESS  not-accessible
        STATUS      current
        DESCRIPTION "The index value uniquely identifies a row
                     in the command table."
        ::= { hpSwitchLocalMgmtPrivUsernamesEntry 1 }

   hpSwitchLocalMgmtPrivUsernameStr OBJECT-TYPE
        SYNTAX      OCTET STRING ( SIZE (1..255))
        MAX-ACCESS  read-create
        STATUS      current
        DESCRIPTION "The username ."
        ::= { hpSwitchLocalMgmtPrivUsernamesEntry 2 }

   hpSwitchLocalMgmtPrivUsernamePasswdType    OBJECT-TYPE
        SYNTAX      INTEGER {
                       unknown(0),
                       sha1(3)
        }       
        MAX-ACCESS  read-create
        STATUS      current
        DESCRIPTION "The type of encryption used for this
                     Conceptual row password object."
        ::= { hpSwitchLocalMgmtPrivUsernamesEntry 3 }

   hpSwitchLocalMgmtPrivUsernamePasswd OBJECT-TYPE
        SYNTAX      OCTET STRING ( SIZE (0..255))
        MAX-ACCESS  read-create
        STATUS      current
        DESCRIPTION "Storage location for the password associated 
                     with this Username.  Always returns a NULL string."
        ::= { hpSwitchLocalMgmtPrivUsernamesEntry 4 }


   hpSwitchLocalMgmtPrivUsernameGrpIndex  OBJECT-TYPE
        SYNTAX      Integer32
        MAX-ACCESS  read-create
        STATUS      current
        DESCRIPTION "The index that represents which group this
                     user is a member of."
        ::= { hpSwitchLocalMgmtPrivUsernamesEntry 5 }

   hpSwitchLocalMgmtPrivUsernameStatus OBJECT-TYPE
        SYNTAX      RowStatus
        MAX-ACCESS  read-create
        STATUS      current
        DESCRIPTION "The status of the  Local Management Privilege
                     username row."
        ::= { hpSwitchLocalMgmtPrivUsernamesEntry 6 }



-- ------------------------------------------------------------
-- Conformance    
-- ------------------------------------------------------------

    hpSwitchAuthenticationMIBConformance
        OBJECT IDENTIFIER ::= { hpSwitchAuthenticationMIB 11 }

    hpSwitchAuthenticationMIBCompliances
        OBJECT IDENTIFIER ::= { hpSwitchAuthenticationMIBConformance 1}

    hpSwitchAuthenticationMIBGroups
        OBJECT IDENTIFIER ::= { hpSwitchAuthenticationMIBConformance 2}


    hpSwitchAuthenticationMIBCompliance MODULE-COMPLIANCE 
        STATUS      deprecated
        DESCRIPTION "The compliance statement for devices implementing the
                     HP Authentication Mib."
        MODULE
            MANDATORY-GROUPS { hpSwitchAuthenticationConfigGroup,
                               hpSwitchTacacsConfigGroup,
                               hpSwitchTacacsStatsGroup }
        ::= { hpSwitchAuthenticationMIBCompliances 1 }

    hpSwitchAuthenticationMIBCompliance1 MODULE-COMPLIANCE 
        STATUS      deprecated 
        DESCRIPTION "The compliance statement for devices implementing the
                     HP Authentication Mib."
        MODULE
            MANDATORY-GROUPS { hpSwitchAuthenticationConfigGroup,
                               hpSwitchTacacsConfigGroup,
                               hpSwitchTacacsStatsGroup,
                               hpSwitchRadiusConfigGroup}
            GROUP   hpSwitchCertStatusGroup2
            DESCRIPTION "A collection of objects for configuring
                         Certificate Status."                   
        ::= { hpSwitchAuthenticationMIBCompliances 2 }

   hpSwitchAuthenticationMIBCompliance2 MODULE-COMPLIANCE
        STATUS      deprecated
        DESCRIPTION "The compliance statement for devices implementing the
                     HP Authentication Mib."
        MODULE
            MANDATORY-GROUPS { hpSwitchAuthenticationConfigGroup1,
                               hpSwitchTacacsConfigGroup,
                               hpSwitchTacacsStatsGroup,
                               hpSwitchRadiusConfigGroup }
            GROUP   hpSwitchKmsGroup
            DESCRIPTION "A collection of objects for configuring
                         KMS functionality."
            GROUP   hpSwitchOspfAuthGroup
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            ::= { hpSwitchAuthenticationMIBCompliances 3 }

   hpSwitchAuthenticationMIBComplianceOobm MODULE-COMPLIANCE
        STATUS      deprecated 
        DESCRIPTION "The compliance statement for devices implementing the
                     HP Authentication Mib with OOBM support"
        MODULE

            GROUP   hpSwitchRadiusOobmGroup
            DESCRIPTION "A collection of objects for configuring
                         Radius with OOBM."

            GROUP   hpSwitchTacacsOobmGroup
            DESCRIPTION "A collection of objects for configuring
                         Tacacs with OOBM."

        ::= { hpSwitchAuthenticationMIBCompliances 4 }





    hpSwitchUserConfigMIBCompliance MODULE-COMPLIANCE
        STATUS      deprecated
        DESCRIPTION "The compliance statement for configuring user-name/password
                     for operator/manager/port-access."
        MODULE

            GROUP    hpSwitchUserConfigGroup
            DESCRIPTION "A collection of objects for configuring user-name/password
                        for operator/manager/port-access."
        ::= { hpSwitchAuthenticationMIBCompliances 5 }

    hpSwitchAAAServerMIBCompliance MODULE-COMPLIANCE
        STATUS      current
        DESCRIPTION "The compliance statement for configuring RADIUS server groups."
        MODULE
            
            GROUP   hpSwitchAAAServerGroup
            DESCRIPTION "A collection of objects for configuring RADIUS server groups."
       ::= { hpSwitchAuthenticationMIBCompliances 6 }  

   hpSwitchAuthenMIBCompliance      MODULE-COMPLIANCE
        STATUS      current
        DESCRIPTION "The compliance statement for listing the authentication methods
                    to be tried for granting different access levels through
                    various access tasks"
        MODULE
            
            GROUP   hpSwitchAuthenGroup
            DESCRIPTION "A collection of objects for listing the authentication methods
                         to be tried for granting different access levels through
                         various access tasks"
       ::= { hpSwitchAuthenticationMIBCompliances 7 }  
                  

   hpSwitchLocalMgmtPrivUserMIBCompliance      MODULE-COMPLIANCE
        STATUS      current
        DESCRIPTION "The compliance statement for listing the
                     local management privilege methods to be
                     tried for granting
                     different access levels through
                     various access tasks"
        MODULE
            
        GROUP   hpSwitchAuthLocalMgmtPrivUserGroup
        DESCRIPTION "A collection of objects for listing the
                     local management privilege methods to be tried 
                     for granting different access levels through
                     various access tasks"

        OBJECT  hpSwitchLocalMgmtPrivUsernameStr
        MIN-ACCESS  read-only
        DESCRIPTION
            "Write access is not required."
        OBJECT  hpSwitchLocalMgmtPrivUsernamePasswdType
        MIN-ACCESS  read-only
        DESCRIPTION
            "Write access is not required."
        OBJECT  hpSwitchLocalMgmtPrivUsernamePasswd
        MIN-ACCESS  read-only
        DESCRIPTION
            "Write access is not required."
        OBJECT  hpSwitchLocalMgmtPrivUsernameGrpIndex
        MIN-ACCESS  read-only
        DESCRIPTION
            "Write access is not required."

       ::= { hpSwitchAuthenticationMIBCompliances 8 }  
                           
   hpSwitchAuthenticationMIBCompliance3 MODULE-COMPLIANCE
        STATUS      deprecated
        DESCRIPTION "The compliance statement for devices implementing the
                     HP Authentication Mib."
        MODULE
            MANDATORY-GROUPS { hpSwitchAuthenticationConfigGroup1,
                               hpSwitchTacacsConfigGroup1,
                               hpSwitchTacacsStatsGroup,
                               hpSwitchRadiusConfigGroup1 }
            GROUP   hpSwitchKmsGroup1
            DESCRIPTION "A collection of objects for configuring
                         KMS functionality."
            GROUP   hpSwitchOspfAuthGroup
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            ::= { hpSwitchAuthenticationMIBCompliances 9 }

    hpSwitchUserConfigMIBCompliance1 MODULE-COMPLIANCE
        STATUS      current
        DESCRIPTION "The compliance statement for configuring user-name/password
                     for operator/manager/port-access."
        MODULE

            GROUP    hpSwitchUserConfigGroup1
            DESCRIPTION "A collection of objects for configuring user-name/password
                        for operator/manager/port-access."
        ::= { hpSwitchAuthenticationMIBCompliances 10 }

    hpSwitchLocalMgmtPrivUserMIBCompliance1 MODULE-COMPLIANCE
        STATUS      current
        DESCRIPTION "The compliance statement for configuring user-name/password
                     for operator/manager/port-access."
        MODULE

        GROUP       hpSwitchAuthLocalMgmtPrivUserGroup1
        DESCRIPTION "Row Status of objects for configuring
                     Local Manangement Priviledge Groups"
        ::= { hpSwitchAuthenticationMIBCompliances 11 }

    hpSwitchAuthenticationMIBCompliance4 MODULE-COMPLIANCE
        STATUS      deprecated
        DESCRIPTION "The compliance statement for devices implementing the
                     HP Authentication MIB."
        MODULE       

        GROUP       hpSwitchCertStatusGroup3      
        DESCRIPTION "Collection of objects for configuring
                     Key Certificate"
        ::= { hpSwitchAuthenticationMIBCompliances 12 }

   hpSwitchAuthenticationMIBCompliance5 MODULE-COMPLIANCE
        STATUS     deprecated 
        DESCRIPTION "The compliance statement for devices implementing the
                     HP Authentication Mib."
        MODULE
            MANDATORY-GROUPS { hpSwitchAuthenticationConfigGroup2,
                               hpSwitchTacacsConfigGroup1,
                               hpSwitchTacacsStatsGroup,
                               hpSwitchRadiusConfigGroup1 }
            GROUP   hpSwitchKmsGroup1
            DESCRIPTION "A collection of objects for configuring
                         KMS functionality."
            GROUP   hpSwitchOspfAuthGroup
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            ::= { hpSwitchAuthenticationMIBCompliances 13 }

   hpSwitchAuthenticationMIBComplianceOobm1 MODULE-COMPLIANCE
        STATUS      current
        DESCRIPTION "The compliance statement for devices implementing the
                     HP Authentication Mib with OOBM support"
        MODULE

            GROUP   hpSwitchTacacsOobmGroup
            DESCRIPTION "A collection of objects for configuring
                         Tacacs with OOBM."

        ::= { hpSwitchAuthenticationMIBCompliances 14 }

   hpSwitchAuthenticationMIBCompliance6 MODULE-COMPLIANCE
        STATUS      deprecated
        DESCRIPTION "The compliance statement for devices implementing the
                     HP Authentication Mib."
        MODULE
            MANDATORY-GROUPS { hpSwitchAuthenticationConfigGroup2,
                               hpSwitchTacacsConfigGroup1,
                               hpSwitchTacacsStatsGroup,
                               hpSwitchRadiusConfigGroup2 }
            GROUP   hpSwitchKmsGroup1
            DESCRIPTION "A collection of objects for configuring
                         KMS functionality."
            GROUP   hpSwitchOspfAuthGroup
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            ::= { hpSwitchAuthenticationMIBCompliances 15 }
   
   hpSwitchAuthenticationMIBCompliance7 MODULE-COMPLIANCE
        STATUS      current
        DESCRIPTION "The compliance statement for devices implementing the
                     HP Authentication Mib."
        MODULE
            MANDATORY-GROUPS { hpSwitchAuthenticationConfigGroup3,
                               hpSwitchTacacsConfigGroup1,
                               hpSwitchTacacsStatsGroup,
                               hpSwitchRadiusConfigGroup2 }
            GROUP   hpSwitchKmsGroup1
            DESCRIPTION "A collection of objects for configuring
                         KMS functionality."
            GROUP   hpSwitchOspfAuthGroup
            DESCRIPTION "A collection of objects for configuring
                     OSPF authentication."
            GROUP   hpSwitchSslGroup
            DESCRIPTION "A collection of objects for configuring
                         SSL Server."
            GROUP   hpSwitchCertGroup
            DESCRIPTION "A collection of objects for configuring
                         Certificate."
            GROUP   hpSwitchCertStatusGroup
            DESCRIPTION "A collection of objects for configuring
                         Certificate Status."
            GROUP   hpSwitchCertStatusGroup3
            DESCRIPTION "Collection of objects for configuring
                         Key Certificate"
            ::= { hpSwitchAuthenticationMIBCompliances 16 }

    hpSwitchAuthenticationMIBCompliance8 MODULE-COMPLIANCE
        STATUS      current
        DESCRIPTION "The compliance statement for devices implementing the
                     HP Authentication Mib."
        MODULE

            GROUP   hpSwitchAuthenticationConfigGroup4
            DESCRIPTION "A collection of objects which controls bypassing of
                         the username during authentication to get Operator
                         or Manager access."
            ::= { hpSwitchAuthenticationMIBCompliances 17 }

--
-- GROUPS
--

   hpSwitchAuthenticationConfigGroup OBJECT-GROUP
        OBJECTS     { hpSwitchNumLoginAttempts,
                      hpSwitchAuthenLoginPrimary,
                      hpSwitchAuthenLoginSecondary,
                      hpSwitchAuthenEnablePrimary,
                      hpSwitchAuthenEnableSecondary
                    }
        STATUS      deprecated 
        DESCRIPTION "A collection of objects for configuring the
                    authentication features."
        ::= { hpSwitchAuthenticationMIBGroups 1 }

    hpSwitchTacacsConfigGroup OBJECT-GROUP
        OBJECTS     { hpSwitchTacacsTimeout,
                      hpSwitchTacacsAuthKey,
                      hpSwitchTacacsServerIpAddr,
                      hpSwitchTacacsServerKey,
                      hpSwitchTacacsServerStatus                      
                    }
        STATUS      deprecated
        DESCRIPTION "A collection of objects for configuring the 
                    state of the TACACS+ protocol."
        ::= { hpSwitchAuthenticationMIBGroups 2 }

    hpSwitchTacacsStatsGroup OBJECT-GROUP
        OBJECTS     { hpTacacsStatsTacacsServerIpAddr,
                      hpTacacsStatsNumSessOpened,
                      hpTacacsStatsNumSessClosed,
                      hpTacacsStatsNumSessAborted,
                      hpTacacsStatsNumSessErrors,
                      hpTacacsStatsNumPktsIn,
                      hpTacacsStatsNumPktsOut
                    }
        STATUS      current
        DESCRIPTION "A collection of objects for viewing the
                    status information of the TACACS+ protocol."
        ::= { hpSwitchAuthenticationMIBGroups 3 }        

    hpSwitchRadiusConfigGroup OBJECT-GROUP
        OBJECTS     { hpSwitchRadiusDeadTime,
                      hpSwitchRadiusTimeout,
                      hpSwitchRadiusRetransmitAttempts,
                      hpSwitchRadiusAuthKey,
                      hpSwitchRadiusDynAutzPortNumber,
                      hpSwitchRadiusServerIpAddr,
                      hpSwitchRadiusServerKey,
                      hpSwitchRadiusServerAuthPortNumber,
                      hpSwitchRadiusServerAcctPortNumber,
                      hpSwitchRadiusServerDynAutzEnabled,
                      hpSwitchRadiusServerDynAutzTimeWindow,
                      hpSwitchRadiusServerStatus
                    }
        STATUS      deprecated
        DESCRIPTION "A collection of objects for configuring the 
                    state of the RADIUS protocol."
        ::= { hpSwitchAuthenticationMIBGroups 4 }

    hpSwitchKmsGroup OBJECT-GROUP
        OBJECTS     { hpSwitchKmsChainName,
                      hpSwitchKmsChainKeys,
                      hpSwitchKmsChainActiveKeys,
                      hpSwitchKmsChainExpKeys,
                      hpSwitchKmsChainStatus,
                      hpSwitchKmsKeyStr,
                      hpSwitchKmsKeyStartTime,
                      hpSwitchKmsKeyStopTime,
                      hpSwitchKmsKeyTxStartTime,
                      hpSwitchKmsKeyTxStopTime,
                      hpSwitchKmsChainStatus,
                      hpSwitchKmsKeyStatus
                    }
        STATUS      deprecated
        DESCRIPTION "A collection of objects for configuring
                     KMS functionality."
        ::= { hpSwitchAuthenticationMIBGroups 6 }        

    hpSwitchOspfAuthGroup OBJECT-GROUP
        OBJECTS     { hpSwitchOspfVirtIfAuthChain,
                      hpSwitchOspfIfAuthChain
                    }
        STATUS      current
        DESCRIPTION "A collection of objects for configuring
                     OSPF authentication."
        ::= { hpSwitchAuthenticationMIBGroups 7 }        

    hpSwitchAuthenticationConfigGroup1 OBJECT-GROUP
        OBJECTS     { hpSwitchNumLoginAttempts,
                      hpSwitchAuthenLoginPrimary,
                      hpSwitchAuthenLoginSecondary,
                      hpSwitchAuthenEnablePrimary,
                      hpSwitchAuthenEnableSecondary,
                      hpSwitchAuthRespectPriv,
                      hpSwitchAuthenticationEncryptCredentialsMethod
                    }
        STATUS      deprecated
        DESCRIPTION "A collection of objects for configuring the
                    authentication features."
        ::= { hpSwitchAuthenticationMIBGroups 8 }

    hpSwitchSslGroup  OBJECT-GROUP
        OBJECTS     { hpSwitchSslAdminStatus,
                      hpSwitchSslPortNumber
                    }
        STATUS      current
        DESCRIPTION "A collection of objects for configuring SSL
                    Servers."
        ::= { hpSwitchAuthenticationMIBGroups 9 }

    hpSwitchCertGroup   OBJECT-GROUP
        OBJECTS     { hpSwitchServerCertificateType,
                      hpSwitchServerCertificateRSAKeySize,
                      hpSwitchServerCertificateSerialNumber,
                      hpSwitchServerCertificateStartDate,
                      hpSwitchServerCertificateEndDate,
                      hpSwitchServerCertificateCommonName,
                      hpSwitchServerCertificateOrgUnit,
                      hpSwitchServerCertificateOrgName,
                      hpSwitchServerCertificateCityName,
                      hpSwitchServerCertificateStateName,
                      hpSwitchServerCertificateCountryCode,
                      hpSwitchServerCertificateFingerprintMD5,
                      hpSwitchServerCertificateFingerprintSHA1
                    }
        STATUS      current
        DESCRIPTION "A collection of objects for configuring Certificates."
        ::= { hpSwitchAuthenticationMIBGroups 10 }

    hpSwitchCertStatusGroup  OBJECT-GROUP
        OBJECTS   { hpSwitchServerCertificateOperation,
                    hpSwitchServerNewRSAKeyOperation,
                    hpSwitchServerNewCertificateStartDate,
                    hpSwitchServerNewCertificateEndDate,
                    hpSwitchServerNewCertCommonName,
                    hpSwitchServerNewCertOrgUnit,
                    hpSwitchServerNewCertOrgName,
                    hpSwitchServerNewCertCityName,
                    hpSwitchServerNewCertStateName,
                    hpSwitchServerNewCertificateCountryCode
                  }
        STATUS    current
        DESCRIPTION "A collection of objects for configuring Certificate Status."
       ::= { hpSwitchAuthenticationMIBGroups 11 }

    hpSwitchTacacsOobmGroup OBJECT-GROUP
        OBJECTS     { hpSwitchTacacsServerIpAddr,
                      hpSwitchTacacsServerIsOobm                     
                    }
        STATUS      current
        DESCRIPTION "A collection of objects for configuring the 
                    TACACS+ server entry with support for OOBM 
                    (Out of Band Management) interface."
        ::= { hpSwitchAuthenticationMIBGroups 12 }

    hpSwitchRadiusOobmGroup OBJECT-GROUP
        OBJECTS     { hpSwitchRadiusServerIpAddr,
                      hpSwitchRadiusServerIsOobm
                    }
        STATUS     deprecated 
        DESCRIPTION "A collection of objects for configuring the 
                    RADIUS server entry with support for OOBM 
                    (Out of Band Management) interface."
        ::= { hpSwitchAuthenticationMIBGroups 13 }

    hpSwitchCertStatusGroup2  OBJECT-GROUP
        OBJECTS   { hpSwitchServerNewCertificateCommonName,
                    hpSwitchServerNewCertificateOrgUnit,
                    hpSwitchServerNewCertificateOrgName,
                    hpSwitchServerNewCertificateCityName,
                    hpSwitchServerNewCertificateStateName
                  }
        STATUS    deprecated
        DESCRIPTION "A collection of objects for configuring Certificate Status."
       ::= { hpSwitchAuthenticationMIBGroups 14 }

    hpSwitchUserConfigGroup OBJECT-GROUP
        OBJECTS   { hpicfSwitchUserName,
                    hpicfSwitchOperatorName,
                    hpicfSwitchPortAccessName,
                    hpicfSwitchUserPassword,
                    hpicfSwitchOperatorPassword,
                    hpicfSwitchPortAccessPassword,
                    hpicfSwitchUserPasswordHashType,
                    hpicfSwitchOperatorPasswordHashType,
                    hpicfSwitchPortAccessPasswordHashType,
                    hpicfSwitchUserConfigStatus
                  }
        STATUS    deprecated
        DESCRIPTION "A collection of objects for configuring user-name/password 
                     for operator/manager/port-access."
       ::= { hpSwitchAuthenticationMIBGroups 15 }

    hpSwitchAAAServerGroup   OBJECT-GROUP
        OBJECTS   { hpSwitchAAAServerGroupName,
                    hpSwitchAAAServerGroupServerInetType,
                    hpSwitchAAAServerGroupServerInetAddr,
                    hpSwitchAAAServerGroupStatus
                  }
        STATUS    current
        DESCRIPTION "A collection of objects for configuring RADIUS server groups."
       ::= { hpSwitchAuthenticationMIBGroups 16 }
       
   hpSwitchAuthenGroup      OBJECT-GROUP
       OBJECTS    { hpSwitchAuthenLoginServerGroupName,
                    hpSwitchAuthenEnableServerGroupName
                  }  
       STATUS    current
       DESCRIPTION "A collection of objects for listing the authentication methods
                    to be tried for granting different access levels through
                    various access tasks"
       ::= { hpSwitchAuthenticationMIBGroups 17 }

                      
    hpSwitchAuthLocalMgmtPrivUserGroup OBJECT-GROUP
        OBJECTS   { 
            hpSwitchLocalMgmtPrivUsernameStr,
            hpSwitchLocalMgmtPrivUsernamePasswdType,
            hpSwitchLocalMgmtPrivUsernamePasswd,
            hpSwitchLocalMgmtPrivUsernameGrpIndex
        }
        STATUS    current
        DESCRIPTION "A collection of objects for configuring
                     Local Management Privilege Groups"
       ::= { hpSwitchAuthenticationMIBGroups 18 }

    hpSwitchTacacsConfigGroup1 OBJECT-GROUP
        OBJECTS     { hpSwitchTacacsTimeout,
                      hpSwitchTacacsAuthKey,
                      hpSwitchTacacsAuthKeyEncrypted,
                      hpSwitchTacacsServerIpAddr,
                      hpSwitchTacacsServerKey,
                      hpSwitchTacacsServerKeyEncrypted,
                      hpSwitchTacacsServerStatus                      
                    }
        STATUS      current
        DESCRIPTION "A collection of objects for configuring the 
                    state of the TACACS+ protocol."
        ::= { hpSwitchAuthenticationMIBGroups 19 }

    hpSwitchRadiusConfigGroup1 OBJECT-GROUP
        OBJECTS     { hpSwitchRadiusDeadTime,
                      hpSwitchRadiusTimeout,
                      hpSwitchRadiusRetransmitAttempts,
                      hpSwitchRadiusAuthKey,
                      hpSwitchRadiusAuthKeyEncrypted,
                      hpSwitchRadiusDynAutzPortNumber,
                      hpSwitchRadiusServerIpAddr,
                      hpSwitchRadiusServerKey,
                      hpSwitchRadiusServerKeyEncrypted,
                      hpSwitchRadiusServerAuthPortNumber,
                      hpSwitchRadiusServerAcctPortNumber,
                      hpSwitchRadiusServerDynAutzEnabled,
                      hpSwitchRadiusServerDynAutzTimeWindow,
                      hpSwitchRadiusServerStatus
                    }
        STATUS      deprecated 
        DESCRIPTION "A collection of objects for configuring the 
                    state of the RADIUS protocol."
        ::= { hpSwitchAuthenticationMIBGroups 20 }

    hpSwitchKmsGroup1 OBJECT-GROUP
        OBJECTS     { hpSwitchKmsChainName,
                      hpSwitchKmsChainKeys,
                      hpSwitchKmsChainActiveKeys,
                      hpSwitchKmsChainExpKeys,
                      hpSwitchKmsChainStatus,
                      hpSwitchKmsKeyStr,
                      hpSwitchKmsKeyEncrypted,
                      hpSwitchKmsKeyStartTime,
                      hpSwitchKmsKeyStopTime,
                      hpSwitchKmsKeyTxStartTime,
                      hpSwitchKmsKeyTxStopTime,
                      hpSwitchKmsChainStatus,
                      hpSwitchKmsKeyStatus
                    }
        STATUS      current
        DESCRIPTION "A collection of objects for configuring
                     KMS functionality."
        ::= { hpSwitchAuthenticationMIBGroups 21 }

    hpSwitchUserConfigGroup1 OBJECT-GROUP
        OBJECTS   { hpicfSwitchUserName,
                    hpicfSwitchOperatorName,
                    hpicfSwitchPortAccessName,
                    hpicfSwitchUserPassword,
                    hpicfSwitchOperatorPassword,
                    hpicfSwitchPortAccessPassword,
                    hpicfSwitchUserPasswordEncrypted,
                    hpicfSwitchOperatorPasswordEncrypted,
                    hpicfSwitchPortAccessPasswordEncrypted,
                    hpicfSwitchUserPasswordHashType,
                    hpicfSwitchOperatorPasswordHashType,
                    hpicfSwitchPortAccessPasswordHashType,
                    hpicfSwitchUserConfigStatus
                  }
        STATUS    current
        DESCRIPTION "A collection of objects for configuring user-name/password 
                     for operator/manager/port-access."
       ::= { hpSwitchAuthenticationMIBGroups 22 }

    hpSwitchAuthLocalMgmtPrivUserGroup1 OBJECT-GROUP
        OBJECTS   { hpSwitchLocalMgmtPrivUsernameStatus 
                  }
        STATUS      current
        DESCRIPTION "Row Status of objects for configuring
                     Local Management Privilege Groups"
       ::= { hpSwitchAuthenticationMIBGroups 23 }

    hpSwitchCertStatusGroup3  OBJECT-GROUP
        OBJECTS   {
                   hpSwitchServerNewCertKeySizeExists
                  }
        STATUS    current
        DESCRIPTION "A collection of objects for configuring 
                     Certificate Keys."
        ::= { hpSwitchAuthenticationMIBGroups 24 }

    hpSwitchAuthenticationConfigGroup2 OBJECT-GROUP
        OBJECTS     { hpSwitchNumLoginAttempts,
                      hpSwitchAuthLockoutDelay,
                      hpSwitchAuthenLoginPrimary,
                      hpSwitchAuthenLoginSecondary,
                      hpSwitchAuthenEnablePrimary,
                      hpSwitchAuthenEnableSecondary,
                      hpSwitchAuthRespectPriv,
                      hpSwitchAuthenticationEncryptCredentialsMethod
                    }
        STATUS      deprecated
        DESCRIPTION "A collection of objects for configuring the
                    authentication features."
        ::= { hpSwitchAuthenticationMIBGroups 25 }

   hpSwitchRadiusConfigGroup2 OBJECT-GROUP
        OBJECTS     { hpSwitchRadiusDeadTime,
                      hpSwitchRadiusTimeout,
                      hpSwitchRadiusRetransmitAttempts,
                      hpSwitchRadiusAuthKey,
                      hpSwitchRadiusAuthKeyEncrypted,
                      hpSwitchRadiusDynAutzPortNumber,
                      hpSwitchRadiusServerAddrType,
                      hpSwitchRadiusServerAddress,
                      hpSwitchRadiusServerKey,
                      hpSwitchRadiusServerKeyEncrypted,
                      hpSwitchRadiusServerAuthPortNumber,
                      hpSwitchRadiusServerAcctPortNumber,
                      hpSwitchRadiusServerDynAutzEnabled,
                      hpSwitchRadiusServerDynAutzTimeWindow,
                      hpSwitchRadiusServerIsOobm,
                      hpSwitchRadiusServerStatus
                    }
        STATUS      current
        DESCRIPTION "A collection of objects for configuring the
                    state of the RADIUS protocol."
        ::= { hpSwitchAuthenticationMIBGroups 26 }

    hpSwitchAuthenticationConfigGroup3 OBJECT-GROUP
        OBJECTS     { hpSwitchNumLoginAttempts,
                      hpSwitchAuthLockoutDelay,
                      hpSwitchAuthenLoginPrimary,
                      hpSwitchAuthenLoginSecondary,
                      hpSwitchAuthenEnablePrimary,
                      hpSwitchAuthenEnableSecondary,
                      hpSwitchAuthRespectPriv,
                      hpSwitchAuthenticationEncryptCredentialsMethod,
                      hpSwitchMinimumPasswordLength,
                      hpSwitchAuthAllowVlanTagged
                    }
        STATUS      current
        DESCRIPTION "A collection of objects for configuring the
                    authentication features."
        ::= { hpSwitchAuthenticationMIBGroups 27 }
    
    hpSwitchAuthenticationConfigGroup4  OBJECT-GROUP
        OBJECTS   {
                   hpicfSwitchBypassUsername
                  }
        STATUS    current
        DESCRIPTION "A collection of objects which controls bypassing of the 
                     username during authentication to get Operator or Manager
                     access."
        ::= { hpSwitchAuthenticationMIBGroups 28 }

END
