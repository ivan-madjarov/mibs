GVP-MIB DEFINITIONS ::= BEGIN

--- Genesys Voice Platform MIB v8.1.3

IMPORTS
	DisplayString FROM SNMPv2-TC

	MODULE-IDENTITY,
	OBJECT-TYPE,
	enterprises,
	Unsigned32,
	TimeTicks,
	Counter64  FROM SNMPv2-SMI;

---
--- MIB High Level description
---

genesys MODULE-IDENTITY
	LAST-UPDATED "201007050000Z"
	ORGANIZATION "Genesys Telecommunications Labs, Inc. An Alcatel Company"
	CONTACT-INFO
		"Postal: 2001 Junipero Serra Blvd
		Daly City, CA 94014
		US
		Tel: +1 888 GENESYS
		Fax: +1 415 437 1260
		email: support@genesyslab.com"
	DESCRIPTION
	"Collection of managed objects that provides for remote
	management of Genesys Call Center server applications."
	REVISION "201007050000Z"
	DESCRIPTION
		"Version 8.1.3."
::= { enterprises 1729 }



-- #############################################################################
-- Object Identifiers
-- #############################################################################

gvpApps OBJECT IDENTIFIER
	::= { genesys 200 }
	
pstnc OBJECT IDENTIFIER
	::= { gvpApps 152 }

mcp OBJECT IDENTIFIER
	::= { gvpApps 145 }

ccp OBJECT IDENTIFIER
	::= { gvpApps 148 }

rm OBJECT IDENTIFIER
	::= { gvpApps 149 }

mrcpp OBJECT IDENTIFIER
	::= { gvpApps 173 }

fm OBJECT IDENTIFIER
	::= { gvpApps 146 }

rs OBJECT IDENTIFIER
    ::= { gvpApps 153 }     
		
ssg OBJECT IDENTIFIER
	::= { gvpApps 154 }
	
ctic OBJECT IDENTIFIER
	::= { gvpApps 155 }
	
gvpCommon OBJECT IDENTIFIER
	::= { genesys 300 }

gvpConfig OBJECT IDENTIFIER
	::= { gvpCommon 2 }
	
gvpReporting OBJECT IDENTIFIER
	::= { gvpCommon 3 }
	

-- #############################################################################
-- Config BRANCH
-- #############################################################################

gvpConfigScalarTable OBJECT-TYPE
	SYNTAX      	SEQUENCE OF GvpConfigScalarEntry
	MAX-ACCESS     	not-accessible
	STATUS      	current
	DESCRIPTION
		"gvpConfigTable: Contains the GVP applications' configuration details."
	::= { gvpConfig 1 }

gvpConfigScalarEntry OBJECT-TYPE
	SYNTAX      	GvpConfigScalarEntry
	MAX-ACCESS     	not-accessible
	STATUS      	current
	DESCRIPTION
		"gvpConfigTable.gvpConfigScalarEntry: An entry (conceptual row) in the gvpConfigScalarTable"
	INDEX { gvpConfigDBID }
	::= { gvpConfigScalarTable 1 }

GvpConfigScalarEntry ::= SEQUENCE 
{
	gvpConfigDBID	Unsigned32,
	gvpConfigName	DisplayString
}

gvpConfigDBID OBJECT-TYPE
	SYNTAX		Unsigned32
	MAX-ACCESS	not-accessible
	STATUS		current
	DESCRIPTION
	"gvpConfigDBID: DB IDs are generated by the Configuration Server when new
	applications are added. The IDs are unique within a given configuration environment.
	DB IDs of deleted applications are not reused within the same power cycle of the 
	Configuration Server."
	::= { gvpConfigScalarEntry 1 }

gvpConfigName OBJECT-TYPE
	SYNTAX			DisplayString
	MAX-ACCESS    	read-only
	STATUS    		current
	DESCRIPTION
        "gvpConfigTable.gvpConfigName: The name of the application on the
        Configuration Server."
::= { gvpConfigScalarEntry 2 }

-- #############################################################################
-- PSTNC BRANCH
-- #############################################################################
---
--- PSTNC CALL SUMMARY TABLE
---

pSTNCCallSummaryTable OBJECT-TYPE
	SYNTAX      	SEQUENCE OF PSTNCCallSummaryEntry
	MAX-ACCESS     	not-accessible
	STATUS      	current
	DESCRIPTION
		"GVP_PSTNCCallSummaryTable: Table to hold parameters in pSTNCCallSummaryTable"
	::= { pstnc 1 }
	
pSTNCCallSummaryEntry OBJECT-TYPE
	SYNTAX      	PSTNCCallSummaryEntry
	MAX-ACCESS     	not-accessible
	STATUS      	current
	DESCRIPTION
		"GVP_PSTNCCallSummaryTable.pSTNCCallSummaryEntry: An entry (conceptual row) in the pSTNCCallSummaryTable"
	INDEX { gvpConfigDBID }
	::= { pSTNCCallSummaryTable 1 }

PSTNCCallSummaryEntry ::= SEQUENCE 
{
	pSTNCIPAddress								DisplayString,
	pSTNCProcessStartTime						DisplayString,
	pSTNCApplicationName						DisplayString,									
	pSTNCActiveTDMInCalls						Unsigned32,
	pSTNCTotalTDMInCallsReceived				Unsigned32,
	pSTNCTotalTDMInCallsAnswered				Unsigned32,
	pSTNCTotalTDMInCallsAborted					Unsigned32,
	pSTNCTotalTDMInCallsRejected				Unsigned32,
	pSTNCActiveTDMOutCalls						Unsigned32,
	pSTNCTotalTDMOutCallsAttempted				Unsigned32,
	pSTNCTotalTDMOutCallsAnswered				Unsigned32,
	pSTNCTotalTDMOutCallsAborted				Unsigned32,
	pSTNCTotalTDMOutCallsRejected				Unsigned32,
	pSTNCActiveSIPInCalls						Unsigned32,
	pSTNCTotalSIPInCallsReceived				Unsigned32,
	pSTNCTotalSIPInCallsAnswered				Unsigned32,
	pSTNCTotalSIPInCallsAborted					Unsigned32,
	pSTNCTotalSIPInCallsRejected				Unsigned32,
	pSTNCActiveSIPOutCalls						Unsigned32,
	pSTNCTotalSIPOutCallsAttempted				Unsigned32,
	pSTNCTotalSIPOutCallsAnswered				Unsigned32,
	pSTNCTotalSIPOutCallsAborted				Unsigned32,
	pSTNCTotalSIPOutCallsRejected				Unsigned32
}

pSTNCIPAddress OBJECT-TYPE
	SYNTAX			DisplayString
	MAX-ACCESS    	read-only
	STATUS    		current
	DESCRIPTION
        "GVP_PSTNCCallSummaryTable.IPAddress: PSTN-C IP Address."
::= { pSTNCCallSummaryEntry 2 }

pSTNCProcessStartTime OBJECT-TYPE
	SYNTAX			DisplayString
	MAX-ACCESS    	read-only
	STATUS    		current
	DESCRIPTION
        "GVP_PSTNCCallSummaryTable.ProcessStartTime: PSTN-C Process start time."
::= { pSTNCCallSummaryEntry 3 }

pSTNCApplicationName OBJECT-TYPE
	SYNTAX			DisplayString
	MAX-ACCESS    	read-only
	STATUS    		current
	DESCRIPTION
        "GVP_PSTNCCallSummaryTable.ApplicationName: PSTN-C Application Name."
::= { pSTNCCallSummaryEntry 4 }

pSTNCActiveTDMInCalls OBJECT-TYPE
	SYNTAX			Unsigned32
	MAX-ACCESS    	read-only
	STATUS    		current
	DESCRIPTION
        "GVP_PSTNCCallSummaryTable.ActiveTDMInCalls: Number of TDM inbound calls received and are active."
::= { pSTNCCallSummaryEntry 5 }

pSTNCTotalTDMInCallsReceived OBJECT-TYPE
	SYNTAX			Unsigned32
	MAX-ACCESS    	read-only
	STATUS    		current
	DESCRIPTION
        "GVP_PSTNCCallSummaryTable.TotalTDMInCallsReceived: Total number of TDM inbound calls received so far."
::= { pSTNCCallSummaryEntry 6 }

pSTNCTotalTDMInCallsAnswered OBJECT-TYPE
	SYNTAX			Unsigned32
	MAX-ACCESS    	read-only
	STATUS    		current
	DESCRIPTION
        "GVP_PSTNCCallSummaryTable.TotalTDMInCallsAnswered: Total number of TDM inbound calls answered."
::= { pSTNCCallSummaryEntry 7 }

pSTNCTotalTDMInCallsAborted OBJECT-TYPE
	SYNTAX			Unsigned32
	MAX-ACCESS    	read-only
	STATUS    		current
	DESCRIPTION
        "GVP_PSTNCCallSummaryTable.TotalTDMInCallsAborted: Total number of TDM inbound calls aborted because of hanging-up (DISCONNECT) of the call by the network when the call is being setup."
::= { pSTNCCallSummaryEntry 8 }

pSTNCTotalTDMInCallsRejected OBJECT-TYPE
	SYNTAX			Unsigned32
	MAX-ACCESS    	read-only
	STATUS    		current
	DESCRIPTION
        "GVP_PSTNCCallSummaryTable.TotalTDMInCallsRejected: Total number of TDM inbound calls rejected by the TDM layer because of some internal errors (e.g. SDP negotiation fails in MCP side)."
::= { pSTNCCallSummaryEntry 9 }

pSTNCActiveTDMOutCalls OBJECT-TYPE
	SYNTAX			Unsigned32
	MAX-ACCESS    	read-only
	STATUS    		current
	DESCRIPTION
        "GVP_PSTNCCallSummaryTable.ActiveTDMOutCalls: Number of TDM outbound calls received and are active."
::= { pSTNCCallSummaryEntry 10 }

pSTNCTotalTDMOutCallsAttempted OBJECT-TYPE
	SYNTAX			Unsigned32
	MAX-ACCESS    	read-only
	STATUS    		current
	DESCRIPTION
        "GVP_PSTNCCallSummaryTable.TotalTDMOutCallsAttempted: Total number of TDM outbound calls attempted (through gc_makecall)."
::= { pSTNCCallSummaryEntry 11 }

pSTNCTotalTDMOutCallsAnswered OBJECT-TYPE
	SYNTAX			Unsigned32
	MAX-ACCESS    	read-only
	STATUS    		current
	DESCRIPTION
        "GVP_PSTNCCallSummaryTable.TotalTDMOutCallsAnswered: Total number of TDM outbound calls answered or connected."
::= { pSTNCCallSummaryEntry 12 }

pSTNCTotalTDMOutCallsAborted OBJECT-TYPE
	SYNTAX			Unsigned32
	MAX-ACCESS    	read-only
	STATUS    		current
	DESCRIPTION
        "GVP_PSTNCCallSummaryTable.TotalTDMOutCallsAborted: Total number of TDM outbound calls hung-up because of call request cancel from MCP."
::= { pSTNCCallSummaryEntry 13 }

pSTNCTotalTDMOutCallsRejected OBJECT-TYPE
	SYNTAX			Unsigned32
	MAX-ACCESS    	read-only
	STATUS    		current
	DESCRIPTION
        "GVP_PSTNCCallSummaryTable.TotalTDMOutCallsRejected: Total number of TDM outbound calls rejected by the network (far end)."
::= { pSTNCCallSummaryEntry 14 }

pSTNCActiveSIPInCalls OBJECT-TYPE
	SYNTAX			Unsigned32
	MAX-ACCESS    	read-only
	STATUS    		current
	DESCRIPTION
        "GVP_PSTNCCallSummaryTable.ActiveSIPInCalls: Number of active SIP inbound calls."
::= { pSTNCCallSummaryEntry 15 }

pSTNCTotalSIPInCallsReceived OBJECT-TYPE
	SYNTAX			Unsigned32
	MAX-ACCESS    	read-only
	STATUS    		current
	DESCRIPTION
        "GVP_PSTNCCallSummaryTable.TotalSIPInCallsReceived: Total number of SIP inbound calls received by PSTN-C."
::= { pSTNCCallSummaryEntry 16 }

pSTNCTotalSIPInCallsAnswered OBJECT-TYPE
	SYNTAX			Unsigned32
	MAX-ACCESS    	read-only
	STATUS    		current
	DESCRIPTION
        "GVP_PSTNCCallSummaryTable.TotalSIPInCallsAnswered: Total number of SIP inbound calls answered by PSTNC because of Call-Connect from TDM."
::= { pSTNCCallSummaryEntry 17 }

pSTNCTotalSIPInCallsAborted OBJECT-TYPE
	SYNTAX			Unsigned32
	MAX-ACCESS    	read-only
	STATUS    		current
	DESCRIPTION
        "GVP_PSTNCCallSummaryTable.TotalSIPInCallsAborted: Total number of SIP inbound calls  aborted by MCP through CANCEL."
::= { pSTNCCallSummaryEntry 18 }

pSTNCTotalSIPInCallsRejected OBJECT-TYPE
	SYNTAX			Unsigned32
	MAX-ACCESS    	read-only
	STATUS    		current
	DESCRIPTION
        "GVP_PSTNCCallSummaryTable.TotalSIPInCallsRejected: Total number of SIP inbound calls rejected by PSTNC because of non availability of dialogic ports or SDP related errors."
::= { pSTNCCallSummaryEntry 19 }

pSTNCActiveSIPOutCalls OBJECT-TYPE
	SYNTAX			Unsigned32
	MAX-ACCESS    	read-only
	STATUS    		current
	DESCRIPTION
        "GVP_PSTNCCallSummaryTable.ActiveSIPOutCalls: Number of active SIP Outbound calls."
::= { pSTNCCallSummaryEntry 20 }

pSTNCTotalSIPOutCallsAttempted OBJECT-TYPE
	SYNTAX			Unsigned32
	MAX-ACCESS    	read-only
	STATUS    		current
	DESCRIPTION
        "GVP_PSTNCCallSummaryTable.TotalSIPOutCallsAttempted: Total number of SIP Outbound calls initiated by PSTN-C to MCP."
::= { pSTNCCallSummaryEntry 21 }

pSTNCTotalSIPOutCallsAnswered OBJECT-TYPE
	SYNTAX			Unsigned32
	MAX-ACCESS    	read-only
	STATUS    		current
	DESCRIPTION
        "GVP_PSTNCCallSummaryTable.TotalSIPOutCallsAnswered: Total number of SIP Outbound calls initiated by PSTN-C which are answered by MCP so far."
::= { pSTNCCallSummaryEntry 22 }

pSTNCTotalSIPOutCallsAborted OBJECT-TYPE
	SYNTAX			Unsigned32
	MAX-ACCESS    	read-only
	STATUS    		current
	DESCRIPTION
        "GVP_PSTNCCallSummaryTable.TotalSIPOutCallsAborted: Total number of SIP Outbound calls aborted because of disconnect from TDM while the call with MCP is in progress."
::= { pSTNCCallSummaryEntry 23 }

pSTNCTotalSIPOutCallsRejected OBJECT-TYPE
	SYNTAX			Unsigned32
	MAX-ACCESS    	read-only
	STATUS    		current
	DESCRIPTION
        "GVP_PSTNCCallSummaryTable.TotalSIPOutCallsRejected: Total number of SIP Outbound calls rejected by MCP because of any 4xx/5xx/6xx responses."
::= { pSTNCCallSummaryEntry 24 }

---
--- PSTNC CONFIG TABLE
---

pSTNCConfigTable OBJECT-TYPE
	SYNTAX      	SEQUENCE OF PSTNCConfigEntry
	MAX-ACCESS     	not-accessible
	STATUS      	current
	DESCRIPTION
		"GVP_PSTNCConfigTable: Table to hold parameters in pSTNCConfigTable"
	::= { pstnc 2 }
	
pSTNCConfigEntry OBJECT-TYPE
	SYNTAX      	PSTNCConfigEntry
	MAX-ACCESS     	not-accessible
	STATUS      	current
	DESCRIPTION
		"GVP_PSTNCConfigTable.pSTNCConfigEntry: An entry (conceptual row) in the pSTNCConfigTable"
	INDEX { gvpConfigDBID }
	::= { pSTNCConfigTable 1 }

PSTNCConfigEntry ::= SEQUENCE 
{	
	pSTNCConfigProcessId				Unsigned32,
	pSTNCConfigApplicationName			DisplayString,
	pSTNCConfigTotalPortsInService 		Unsigned32,
	pSTNCConfigTotalPortsNotInService	Unsigned32,
	pSTNCConfigTotalInBoundPorts		Unsigned32,
	pSTNCConfigTotalOutBoundPorts		Unsigned32,
	pSTNCConfigTotalBiDirectionalPorts	Unsigned32,
	pSTNCConfigTotalPorts				Unsigned32,
	pSTNCConfigSipAddress				DisplayString,
	pSTNCConfigSipPort					Unsigned32,
	pSTNCConfigDestIpAddress			DisplayString,
	pSTNCConfigDestPort					Unsigned32
}

pSTNCConfigProcessId OBJECT-TYPE
	SYNTAX			Unsigned32
	MAX-ACCESS    	read-only
	STATUS    		current
	DESCRIPTION
        "GVP_PSTNCConfigTable.ConfigProcessId: PSTN-C Process ID."
::= { pSTNCConfigEntry 2 }

pSTNCConfigApplicationName OBJECT-TYPE
	SYNTAX			DisplayString
	MAX-ACCESS    	read-only
	STATUS    		current
	DESCRIPTION
        "GVP_PSTNCConfigTable.ConfigApplicationName: PSTN-C Application Name."
::= { pSTNCConfigEntry 3 }

pSTNCConfigTotalPortsInService OBJECT-TYPE
	SYNTAX			Unsigned32
	MAX-ACCESS    	read-only
	STATUS    		current
	DESCRIPTION
        "GVP_PSTNCConfigTable.ConfigTotalPortsInService: PSTN-C Total number of ports in service."
::= { pSTNCConfigEntry 4 }

pSTNCConfigTotalPortsNotInService OBJECT-TYPE
	SYNTAX			Unsigned32
	MAX-ACCESS    	read-only
	STATUS    		current
	DESCRIPTION
        "GVP_PSTNCConfigTable.ConfigTotalPortsNotInService: PSTN-C Total number of ports not in service."
::= { pSTNCConfigEntry 5 }

pSTNCConfigTotalInBoundPorts OBJECT-TYPE
	SYNTAX			Unsigned32
	MAX-ACCESS    	read-only
	STATUS    		current
	DESCRIPTION
        "GVP_PSTNCConfigTable.ConfigTotalInBoundPorts: PSTN-C Total number of  inbound ports."
::= { pSTNCConfigEntry 6 }

pSTNCConfigTotalOutBoundPorts OBJECT-TYPE
	SYNTAX			Unsigned32
	MAX-ACCESS    	read-only
	STATUS    		current
	DESCRIPTION
        "GVP_PSTNCConfigTable.ConfigTotalOutBoundPorts: PSTN-C Total number of outbound ports."
::= { pSTNCConfigEntry 7 }

pSTNCConfigTotalBiDirectionalPorts OBJECT-TYPE
	SYNTAX			Unsigned32
	MAX-ACCESS    	read-only
	STATUS    		current
	DESCRIPTION
        "GVP_PSTNCConfigTable.ConfigTotalBiDirectionalPorts: PSTN-C Total number of bi-directional ports."
::= { pSTNCConfigEntry 8 }

pSTNCConfigTotalPorts OBJECT-TYPE
	SYNTAX			Unsigned32
	MAX-ACCESS    	read-only
	STATUS    		current
	DESCRIPTION
        "GVP_PSTNCConfigTable.ConfigTotalPorts: PSTN-C Total number of ports."
::= { pSTNCConfigEntry 9 }

pSTNCConfigSipAddress OBJECT-TYPE
	SYNTAX			DisplayString
	MAX-ACCESS    	read-only
	STATUS    		current
	DESCRIPTION
        "GVP_PSTNCConfigTable.ConfigSipAddress: GatewayManager - PSTN-C Local SIP IP Address."
::= { pSTNCConfigEntry 10 }

pSTNCConfigSipPort OBJECT-TYPE
	SYNTAX			Unsigned32
	MAX-ACCESS    	read-only
	STATUS    		current
	DESCRIPTION
        "GVP_PSTNCConfigTable.ConfigSipPort: GatewayManager - PSTN-C SIP port number."
::= { pSTNCConfigEntry 11 }

pSTNCConfigDestIpAddress OBJECT-TYPE
	SYNTAX			DisplayString
	MAX-ACCESS    	read-only
	STATUS    		current
	DESCRIPTION
        "GVP_PSTNCConfigTable.ConfigDestIpAddress: GatewayManager - RM/MCP IP Address."
::= { pSTNCConfigEntry 12 }

pSTNCConfigDestPort OBJECT-TYPE
	SYNTAX			Unsigned32
	MAX-ACCESS    	read-only
	STATUS    		current
	DESCRIPTION
        "GVP_PSTNCConfigTable.ConfigDestPort: GatewayManager - RM/MCP SIP port number."
::= { pSTNCConfigEntry 13 }

---
--- PSTNC CALL TABLE
---

pSTNCCallTable OBJECT-TYPE
	SYNTAX      	SEQUENCE OF PSTNCCallEntry
	MAX-ACCESS     	not-accessible
	STATUS      	current
	DESCRIPTION
		"GVP_PSTNCCallTable: Table to hold parameters in pSTNCCallTable"
	::= { pstnc 3 }
	
pSTNCCallEntry OBJECT-TYPE
	SYNTAX      	PSTNCCallEntry
	MAX-ACCESS     	not-accessible
	STATUS      	current
	DESCRIPTION
		"GVP_PSTNCCallTable.pSTNCCallEntry: An entry (conceptual row) in the pSTNCCallTable"
    INDEX { gvpConfigDBID, pSTNCSipCallId }
	::= { pSTNCCallTable 1 }

PSTNCCallEntry ::= SEQUENCE 
{	
	pSTNCSipCallId						DisplayString,
	pSTNCSessionId						DisplayString,
	pSTNCTdmCallId						Unsigned32,
	pSTNCMediaId						Unsigned32,
	pSTNCDNIS							DisplayString,
	pSTNCANI							DisplayString,
	pSTNCSIPCallState					DisplayString,
	pSTNCTdmCallState					DisplayString,
	pSTNCMediaSessionState				DisplayString,
	pSTNCCallType						DisplayString,
	pSTNCCallStartTime					DisplayString,
	pSTNCTdmDlgcPort					Unsigned32,
	pSTNCSrcRtpPortNo					Unsigned32,
	pSTNCDestRtpPortNo					Unsigned32,
	pSTNCDestRtpIpAddress				DisplayString,
	pSTNCCodecUsed						Unsigned32,
	pSTNCTotalPacketLoss				Unsigned32,
	pSTNCTotalLowWaterMark				Unsigned32,
	pSTNCTotalHighWaterMark				Unsigned32,
	pSTNCTotalTdmStreamBufferOverFlow	Unsigned32,
	pSTNCTotalRtpBufferOverFlow			Unsigned32

}

pSTNCSipCallId OBJECT-TYPE
	SYNTAX			DisplayString
	MAX-ACCESS    	read-only
	STATUS    		current
	DESCRIPTION
        "GVP_PSTNCCallTable.SipCallId: SIP CallID of the call."
::= { pSTNCCallEntry 2 }

pSTNCSessionId OBJECT-TYPE
	SYNTAX			DisplayString
	MAX-ACCESS    	read-only
	STATUS    		current
	DESCRIPTION
        "GVP_PSTNCCallTable.SessionId: Session ID of the call. Session comprises the SIP calls."
::= { pSTNCCallEntry 3 }

pSTNCTdmCallId OBJECT-TYPE
	SYNTAX			Unsigned32
	MAX-ACCESS    	read-only
	STATUS    		current
	DESCRIPTION
        "GVP_PSTNCCallTable.TdmCallId: TDM Call ID of the call."
::= { pSTNCCallEntry 4 }

pSTNCMediaId OBJECT-TYPE
	SYNTAX			Unsigned32
	MAX-ACCESS    	read-only
	STATUS    		current
	DESCRIPTION
        "GVP_PSTNCCallTable.MediaId: Session ID of the media."
::= { pSTNCCallEntry 5 }

pSTNCDNIS OBJECT-TYPE
	SYNTAX			DisplayString
	MAX-ACCESS    	read-only
	STATUS    		current
	DESCRIPTION
        "GVP_PSTNCCallTable.DNIS: DNIS of the Call."
::= { pSTNCCallEntry 6 }

pSTNCANI OBJECT-TYPE
	SYNTAX			DisplayString
	MAX-ACCESS    	read-only
	STATUS    		current
	DESCRIPTION
        "GVP_PSTNCCallTable.ANI: ANI of the Call."
::= { pSTNCCallEntry 7 }

pSTNCSIPCallState OBJECT-TYPE
	SYNTAX			DisplayString
	MAX-ACCESS    	read-only
	STATUS    		current
	DESCRIPTION
        "GVP_PSTNCCallTable.SIPCallState: Call state at GatewayManager."
::= { pSTNCCallEntry 8 }

pSTNCTdmCallState OBJECT-TYPE
	SYNTAX			DisplayString
	MAX-ACCESS    	read-only
	STATUS    		current
	DESCRIPTION
        "GVP_PSTNCCallTable.TdmCallState: Call state at DialogicManager."
::= { pSTNCCallEntry 9 }

pSTNCMediaSessionState OBJECT-TYPE
	SYNTAX			DisplayString
	MAX-ACCESS    	read-only
	STATUS    		current
	DESCRIPTION
        "GVP_PSTNCCallTable.MediaSessionState: Media Session state at MediaManager."
::= { pSTNCCallEntry 10 }


pSTNCCallType OBJECT-TYPE
	SYNTAX			DisplayString
	MAX-ACCESS    	read-only
	STATUS    		current
	DESCRIPTION
        "GVP_PSTNCCallTable.CallType: Type of the call. Whether inbound or outbound."
::= { pSTNCCallEntry 11 }

pSTNCCallStartTime OBJECT-TYPE
	SYNTAX			DisplayString
	MAX-ACCESS    	read-only
	STATUS    		current
	DESCRIPTION
        "GVP_PSTNCCallTable.CallStartTime: Time at which call started."
::= { pSTNCCallEntry 12 }

pSTNCTdmDlgcPort OBJECT-TYPE
	SYNTAX			Unsigned32
	MAX-ACCESS    	read-only
	STATUS    		current
	DESCRIPTION
        "GVP_PSTNCCallTable.TdmDlgcPort: DialogicManager physical port number."
::= { pSTNCCallEntry 13 }


pSTNCSrcRtpPortNo OBJECT-TYPE
	SYNTAX			Unsigned32
	MAX-ACCESS    	read-only
	STATUS    		current
	DESCRIPTION
        "GVP_PSTNCCallTable.SrcRtpPortNo: PSTN-C RTP port number."
::= { pSTNCCallEntry 14 }

pSTNCDestRtpPortNo OBJECT-TYPE
	SYNTAX			Unsigned32
	MAX-ACCESS    	read-only
	STATUS    		current
	DESCRIPTION
        "GVP_PSTNCCallTable.DestRtpPortNo: Media Server/MCP RTP port number."
::= { pSTNCCallEntry 15 }

pSTNCDestRtpIpAddress OBJECT-TYPE
	SYNTAX			DisplayString
	MAX-ACCESS    	read-only
	STATUS    		current
	DESCRIPTION
        "GVP_PSTNCCallTable.DestRtpIpAddress: Media Server/MCP IP Address."
::= { pSTNCCallEntry 16 }

pSTNCCodecUsed OBJECT-TYPE
	SYNTAX			Unsigned32
	MAX-ACCESS    	read-only
	STATUS    		current
	DESCRIPTION
        "GVP_PSTNCCallTable.CodecUsed: Negotiated codec being used."
::= { pSTNCCallEntry 17 }

pSTNCTotalPacketLoss OBJECT-TYPE
	SYNTAX			Unsigned32
	MAX-ACCESS    	read-only
	STATUS    		current
	DESCRIPTION
        "GVP_PSTNCCallTable.TotalPacketLoss: Total number of lost RTP packets for the session."
::= { pSTNCCallEntry 18 }

pSTNCTotalLowWaterMark OBJECT-TYPE
	SYNTAX			Unsigned32
	MAX-ACCESS    	read-only
	STATUS    		current
	DESCRIPTION
        "GVP_PSTNCCallTable.TotalLowWaterMark: Total instances of low water mark in Dialogic buffer for the session."
::= { pSTNCCallEntry 19 }

pSTNCTotalHighWaterMark OBJECT-TYPE
	SYNTAX			Unsigned32
	MAX-ACCESS    	read-only
	STATUS    		current
	DESCRIPTION
        "GVP_PSTNCCallTable.TotalHighWaterMark: Total instances of high water mark in Dialogic buffer for the session."
::= { pSTNCCallEntry 20 }

pSTNCTotalTdmStreamBufferOverFlow OBJECT-TYPE
	SYNTAX			Unsigned32
	MAX-ACCESS    	read-only
	STATUS    		current
	DESCRIPTION
        "GVP_PSTNCCallTable.TotalTdmStreamBufferOverFlow: Total instances of TDM stream buffer data overflow for the session."
::= { pSTNCCallEntry 21 }

pSTNCTotalRtpBufferOverFlow OBJECT-TYPE
	SYNTAX			Unsigned32
	MAX-ACCESS    	read-only
	STATUS    		current
	DESCRIPTION
        "GVP_PSTNCCallTable.TotalRtpBufferOverFlow: Total instances of RTP buffer data overflow for the session."
::= { pSTNCCallEntry 22 }

---
--- PSTNC MEDIA SUMMARY TABLE
---

pSTNCMediaSummaryTable OBJECT-TYPE
	SYNTAX      	SEQUENCE OF PSTNCMediaSummaryEntry
	MAX-ACCESS     	not-accessible
	STATUS      	current
	DESCRIPTION
		"GVP_PSTNCMediaSummaryTable: Table to hold parameters in pSTNCMediaSummaryTable"
	::= { pstnc 4 }
	
pSTNCMediaSummaryEntry OBJECT-TYPE
	SYNTAX      	PSTNCMediaSummaryEntry
	MAX-ACCESS     	not-accessible
	STATUS      	current
	DESCRIPTION
		"GVP_PSTNCMediaSummaryTable.pSTNCMediaEntry: An entry (conceptual row) in the pSTNCMediaSummaryTable"
	INDEX { gvpConfigDBID }
	::= { pSTNCMediaSummaryTable 1 }

PSTNCMediaSummaryEntry ::= SEQUENCE 
{	
	pSTNCMediaTotalBytesReceived			Unsigned32,
	pSTNCMediaTotalBytesSent				Unsigned32,
	pSTNCMediaTotalPacketsLost				Unsigned32,
	pSTNCMediaTotalTDMStreamBufferOverFlow	Unsigned32,
	pSTNCMediaTotalRTPBufferOverFlow		Unsigned32,
	pSTNCMediaTotalLowWaterMark				Unsigned32,
	pSTNCMediaTotalHighWaterMark			Unsigned32
}

pSTNCMediaTotalBytesReceived OBJECT-TYPE
	SYNTAX			Unsigned32
	MAX-ACCESS    	read-only
	STATUS    		current
	DESCRIPTION
        "GVP_PSTNCMediaSummaryTable.MediaTotalBytesReceived: Total bytes of  RTP data received."
::= { pSTNCMediaSummaryEntry 2 }

pSTNCMediaTotalBytesSent OBJECT-TYPE
	SYNTAX			Unsigned32
	MAX-ACCESS    	read-only
	STATUS    		current
	DESCRIPTION
        "GVP_PSTNCMediaSummaryTable.MediaTotalBytesSent: Total bytes of  RTP data sent."
::= { pSTNCMediaSummaryEntry 3 }

pSTNCMediaTotalPacketsLost OBJECT-TYPE
	SYNTAX			Unsigned32
	MAX-ACCESS    	read-only
	STATUS    		current
	DESCRIPTION
        "GVP_PSTNCMediaSummaryTable.MediaTotalPacketsLost: Total number of  RTP packets lost."
::= { pSTNCMediaSummaryEntry 4 }

pSTNCMediaTotalTDMStreamBufferOverFlow OBJECT-TYPE
	SYNTAX			Unsigned32
	MAX-ACCESS    	read-only
	STATUS    		current
	DESCRIPTION
        "GVP_PSTNCMediaSummaryTable.MediaTotalTDMStreamBufferOverFlow: Total instances of TDM stream buffer data overflow."
::= { pSTNCMediaSummaryEntry 5 }

pSTNCMediaTotalRTPBufferOverFlow OBJECT-TYPE
	SYNTAX			Unsigned32
	MAX-ACCESS    	read-only
	STATUS    		current
	DESCRIPTION
        "GVP_PSTNCMediaSummaryTable.MediaTotalRTPBufferOverFlow: Total instances of RTP buffer data overflow."
::= { pSTNCMediaSummaryEntry 6 }

pSTNCMediaTotalLowWaterMark OBJECT-TYPE
	SYNTAX			Unsigned32
	MAX-ACCESS    	read-only
	STATUS    		current
	DESCRIPTION
        "GVP_PSTNCMediaSummaryTable.MediaTotalLowWaterMark: Total instances of low water mark in Dialogic buffer."
::= { pSTNCMediaSummaryEntry 7 }

pSTNCMediaTotalHighWaterMark OBJECT-TYPE
	SYNTAX			Unsigned32
	MAX-ACCESS    	read-only
	STATUS    		current
	DESCRIPTION
        "GVP_PSTNCMediaSummaryTable.MediaTotalHighWaterMark: Total instances of high water mark in Dialogic buffer."
::= { pSTNCMediaSummaryEntry 8 }


---
--- PSTNC BOARD TABLE
---

pSTNCBoardTable OBJECT-TYPE
	SYNTAX      	SEQUENCE OF PSTNCBoardEntry
	MAX-ACCESS     	not-accessible
	STATUS      	current
	DESCRIPTION
		"GVP_PSTNCBoardTable: Table to hold parameters in pSTNCBoardTable"
	::= { pstnc 5 }
	
pSTNCBoardEntry OBJECT-TYPE
	SYNTAX      	PSTNCBoardEntry
	MAX-ACCESS     	not-accessible
	STATUS      	current
	DESCRIPTION
		"GVP_PSTNCBoardTable.pSTNCBoardEntry: An entry (conceptual row) in the pSTNCBoardTable"
    INDEX { gvpConfigDBID, pSTNCBoardId }
	::= { pSTNCBoardTable 1 }

PSTNCBoardEntry ::= SEQUENCE 
{	
	pSTNCBoardId				Unsigned32,
	pSTNCBoardName				DisplayString,
	pSTNCBoardType				DisplayString,
	pSTNCSignallingProtocol		DisplayString,
	pSTNCDChannelStatus			Unsigned32,
	pSTNCRedAlarm				Unsigned32,
	pSTNCYellowAlarm			Unsigned32,
	pSTNCBlueAlarm				Unsigned32,
	pSTNCLossOfSync				INTEGER,
	pSTNCFramingError			INTEGER,
	pSTNCBiPolarViolation		INTEGER
}

pSTNCBoardId OBJECT-TYPE
	SYNTAX			Unsigned32
	MAX-ACCESS    	read-only
	STATUS    		current
	DESCRIPTION
        "GVP_PSTNCBoardTable.BoardId: DialogicManager  - Board identifier."
::= { pSTNCBoardEntry 2 }

pSTNCBoardName OBJECT-TYPE
	SYNTAX			DisplayString
	MAX-ACCESS    	read-only
	STATUS    		current
	DESCRIPTION
        "GVP_PSTNCBoardTable.BoardName: DialogicManager  - Board description."
::= { pSTNCBoardEntry 3 }

pSTNCBoardType OBJECT-TYPE
	SYNTAX			DisplayString
	MAX-ACCESS    	read-only
	STATUS    		current
	DESCRIPTION
        "GVP_PSTNCBoardTable.BoardType: DialogicManager  - Board type."
::= { pSTNCBoardEntry 4 }

pSTNCSignallingProtocol OBJECT-TYPE
	SYNTAX			DisplayString
	MAX-ACCESS    	read-only
	STATUS    		current
	DESCRIPTION
        "GVP_PSTNCBoardTable.SignallingProtocol: DialogicManager  - Board signaling on board."
::= { pSTNCBoardEntry 5 }

pSTNCDChannelStatus OBJECT-TYPE
	SYNTAX			Unsigned32
	MAX-ACCESS    	read-only
	STATUS    		current
	DESCRIPTION
        "GVP_PSTNCBoardTable.DChannelStatus: DialogicManager  -  D-Channel status of the board."
::= { pSTNCBoardEntry 6 }

pSTNCRedAlarm OBJECT-TYPE
	SYNTAX			Unsigned32
	MAX-ACCESS    	read-only
	STATUS    		current
	DESCRIPTION
        "GVP_PSTNCBoardTable.RedAlarm: DialogicManager - RED alarm in board."
::= { pSTNCBoardEntry 7 }

pSTNCYellowAlarm OBJECT-TYPE
	SYNTAX			Unsigned32
	MAX-ACCESS    	read-only
	STATUS    		current
	DESCRIPTION
        "GVP_PSTNCBoardTable.YellowAlarm: DialogicManager - YELLOW alarm on board."
::= { pSTNCBoardEntry 8 }

pSTNCBlueAlarm OBJECT-TYPE
	SYNTAX			Unsigned32
	MAX-ACCESS    	read-only
	STATUS    		current
	DESCRIPTION
        "GVP_PSTNCBoardTable.BlueAlarm: DialogicManager - BLUE alarm on board."
::= { pSTNCBoardEntry 9 }

pSTNCLossOfSync OBJECT-TYPE
	SYNTAX			INTEGER { off(0), on(1) }
	MAX-ACCESS    	read-only
	STATUS    		current
	DESCRIPTION
        "GVP_PSTNCBoardTable.LossOfSync: DialogicManager -  Loss of synchronization on board."
::= { pSTNCBoardEntry 10 }

pSTNCFramingError OBJECT-TYPE
	SYNTAX			INTEGER { off(0), on(1) }
	MAX-ACCESS    	read-only
	STATUS    		current
	DESCRIPTION
        "GVP_PSTNCBoardTable.FramingError: DialogicManager - Framing error on board."
::= { pSTNCBoardEntry 11 }

pSTNCBiPolarViolation OBJECT-TYPE
	SYNTAX			INTEGER { off(0), on(1) }
	MAX-ACCESS    	read-only
	STATUS    		current
	DESCRIPTION
        "GVP_PSTNCBoardTable.BiPolarViolation: DialogicManager - Bipolar violation on board."
::= { pSTNCBoardEntry 12 }

---
--- PSTNC PORT TABLE
---

pSTNCPortTable OBJECT-TYPE
	SYNTAX      	SEQUENCE OF PSTNCPortEntry
	MAX-ACCESS     	not-accessible
	STATUS      	current
	DESCRIPTION
		"GVP_PSTNCPortTable: Table to hold parameters in pSTNCPortTable"
	::= { pstnc 6 }
	
pSTNCPortEntry OBJECT-TYPE
	SYNTAX      	PSTNCPortEntry
	MAX-ACCESS     	not-accessible
	STATUS      	current
	DESCRIPTION
		"GVP_PSTNCPortTable.pSTNCPortEntry: An entry (conceptual row) in the pSTNCPortTable"
    INDEX { gvpConfigDBID, pSTNCPortId }
	::= { pSTNCPortTable 1 }

PSTNCPortEntry ::= SEQUENCE 
{	
	pSTNCPortId						DisplayString,
	pSTNCPortNo						Unsigned32,
	pSTNCPortType					Unsigned32,
	pSTNCPortStatus					Unsigned32,
	pSTNCPortRouteNum				Unsigned32,
	pSTNCPortTotalCallsAttempted	Unsigned32,
	pSTNCPortTotaCallsAnswered		Unsigned32,
	pSTNCPortTotalCallsRejected		Unsigned32
}

pSTNCPortId OBJECT-TYPE
	SYNTAX			DisplayString
	MAX-ACCESS    	read-only
	STATUS    		current
	DESCRIPTION
        "GVP_PSTNCPortTable.PortId: DialogicManager - dlgc port identifier (for e.g. 1:1)."
::= { pSTNCPortEntry 2 }

pSTNCPortNo OBJECT-TYPE
	SYNTAX			Unsigned32
	MAX-ACCESS    	read-only
	STATUS    		current
	DESCRIPTION
        "GVP_PSTNCPortTable.PortNo: DialogicManager - dlgc Port Number."
::= { pSTNCPortEntry 3 }

pSTNCPortType OBJECT-TYPE
	SYNTAX			Unsigned32
	MAX-ACCESS    	read-only
	STATUS    		current
	DESCRIPTION
        "GVP_PSTNCPortTable.PortType: DialogicManager -  dlgc port type."
::= { pSTNCPortEntry 4 }

pSTNCPortStatus OBJECT-TYPE
	SYNTAX			Unsigned32
	MAX-ACCESS    	read-only
	STATUS    		current
	DESCRIPTION
        "GVP_PSTNCPortTable.PortStatus: DialogicManager - dlgc port status."
::= { pSTNCPortEntry 5 }

pSTNCPortRouteNum OBJECT-TYPE
	SYNTAX			Unsigned32
	MAX-ACCESS    	read-only
	STATUS    		current
	DESCRIPTION
        "GVP_PSTNCPortTable.PortRouteNum: DialogicManager -Route Number for the ports."
::= { pSTNCPortEntry 6 }

pSTNCPortTotalCallsAttempted OBJECT-TYPE
	SYNTAX			Unsigned32
	MAX-ACCESS    	read-only
	STATUS    		current
	DESCRIPTION
        "GVP_PSTNCPortTable.PortTotalCallsAttempted: DialogicManager - Total number of calls attempted  on a particular port."
::= { pSTNCPortEntry 7 }

pSTNCPortTotaCallsAnswered OBJECT-TYPE
	SYNTAX			Unsigned32
	MAX-ACCESS    	read-only
	STATUS    		current
	DESCRIPTION
        "GVP_PSTNCPortTable.PortTotaCallsAnswered: DialogicManager - Total number of calls answered on a particular port."
::= { pSTNCPortEntry 8 }

pSTNCPortTotalCallsRejected OBJECT-TYPE
	SYNTAX			Unsigned32
	MAX-ACCESS    	read-only
	STATUS    		current
	DESCRIPTION
        "GVP_PSTNCPortTable.PortTotalCallsRejected: DialogicManager - Total number of calls rejected on a particular port."
::= { pSTNCPortEntry 9 }

---
--- PSTNC ROUTE TABLE
---

pSTNCRouteTable OBJECT-TYPE
	SYNTAX      	SEQUENCE OF PSTNCRouteEntry
	MAX-ACCESS     	not-accessible
	STATUS      	current
	DESCRIPTION
		"GVP_PSTNCRouteTable: Table to hold parameters in pSTNCRouteTable"
	::= { pstnc 7 }
	
pSTNCRouteEntry OBJECT-TYPE
	SYNTAX      	PSTNCRouteEntry
	MAX-ACCESS     	not-accessible
	STATUS      	current
	DESCRIPTION
		"GVP_PSTNCRouteTable.pSTNCRouteEntry: An entry (conceptual row) in the pSTNCRouteTable"
    INDEX { gvpConfigDBID, pSTNCRouteNo }
	::= { pSTNCRouteTable 1 }

PSTNCRouteEntry ::= SEQUENCE 
{	
	pSTNCRouteNo			Unsigned32,
	pSTNCRouteType			DisplayString,
	pSTNCRouteDesc			DisplayString,
	pSTNCRouteSignalling	DisplayString,
	pSTNCRoutePorts			DisplayString 
}

pSTNCRouteNo OBJECT-TYPE
	SYNTAX			Unsigned32
	MAX-ACCESS    	read-only
	STATUS    		current
	DESCRIPTION
        "GVP_PSTNCRouteTable.RouteNo: DialogicManager - Route identifier."
::= { pSTNCRouteEntry 2 }

pSTNCRouteType OBJECT-TYPE
	SYNTAX			DisplayString
	MAX-ACCESS    	read-only
	STATUS    		current
	DESCRIPTION
        "GVP_PSTNCRouteTable.RouteType: DialogicManager - Route type."
::= { pSTNCRouteEntry 3 }

pSTNCRouteDesc OBJECT-TYPE
	SYNTAX			DisplayString
	MAX-ACCESS    	read-only
	STATUS    		current
	DESCRIPTION
        "GVP_PSTNCRouteTable.RouteDesc: DialogicManager - Route description."
::= { pSTNCRouteEntry 4 }

pSTNCRouteSignalling OBJECT-TYPE
	SYNTAX			DisplayString
	MAX-ACCESS    	read-only
	STATUS    		current
	DESCRIPTION
        "GVP_PSTNCRouteTable.RouteSignalling: DialogicManager - Route signaling."
::= { pSTNCRouteEntry 5 }

pSTNCRoutePorts OBJECT-TYPE
	SYNTAX			DisplayString
	MAX-ACCESS    	read-only
	STATUS    		current
	DESCRIPTION
        "GVP_PSTNCRouteTable.RoutePorts: DialogicManager - List of ports configured for the routes."
::= { pSTNCRouteEntry 6 }



-- #############################################################################
-- SSG BRANCH
-- #############################################################################

---
--- SSG SUMMARY TABLE
---

ssgSummaryTable OBJECT-TYPE
	SYNTAX      	SEQUENCE OF SsgSummaryEntry
	MAX-ACCESS     	not-accessible
	STATUS      	current
	DESCRIPTION
		"GVP_SSG_SummaryTable: Table of scalar MIBs containing summary of  SSG High-Level Statistics."
	::= { ssg 1 }

ssgSummaryEntry OBJECT-TYPE
	SYNTAX      	SsgSummaryEntry
	MAX-ACCESS     	not-accessible
	STATUS      	current
	DESCRIPTION
		"GVP_SSG_SummaryTable.ssgSummaryEntry: An entry (conceptual row) in the ssgSummaryTable"
	INDEX { gvpConfigDBID }
	::= { ssgSummaryTable 1 }

SsgSummaryEntry ::= SEQUENCE 
{	
	ssgActiveNode					DisplayString,
	ssgActiveSinceSec				Unsigned32,
	ssgTotalActiveReq				Unsigned32,
	ssgTotalSuccessfulReq				Unsigned32,
	ssgTotalPendingReq				Unsigned32,
	ssgTotalRecvCreateReq				Unsigned32,
	ssgTotalRecvQueryReq				Unsigned32,
	ssgTotalRecvCancelReq				Unsigned32,
	ssgTotalFailedQueryReq				Unsigned32,
	ssgTotalFailedCancelReq				Unsigned32,
	ssgTotalMaxAttemptsExceededReq			Unsigned32,
	ssgTotalTTLExpiredReq				Unsigned32,
	ssgTotalDestinationNotFoundReq			Unsigned32,
	ssgTotalFailedReq				Unsigned32,
	ssgSIPSvrConnNotAvailableRejectedReq		Unsigned32,
	ssgResourceDNUnRegisteredRejectedReq		Unsigned32,
	ssgTenantNotSupportedRejectedReq		Unsigned32,
	ssgTotalRejectedReq				Unsigned32,
	ssgTotalNotificationURLSuccessReq		Unsigned32,
	ssgTotalNotificationURLFailedReq		Unsigned32,
	ssgPeakActiveReq				Unsigned32,
	ssgPeakPendingReq				Unsigned32,
	ssgTotalRecvHTTPReq				Unsigned32,
	ssgTotalRecvHTTPSReq				Unsigned32,
	ssgTotalMaxDBReachedRejectedReq			Unsigned32,
	ssgTotalInMemoryQueueReq			Unsigned32,
	ssgTotalTMPCQueueReq				Unsigned32,
	ssgTotalFailedDigestAuthReq			Unsigned32
	
}


ssgActiveNode OBJECT-TYPE
	SYNTAX			DisplayString
	MAX-ACCESS    		read-only
	STATUS    		current
	DESCRIPTION
        "GVP_SSG_SummaryTable.ActiveNode: FQDN or IP address of the machine where the SSG process is up and running."
::= { ssgSummaryEntry 2 }

ssgActiveSinceSec OBJECT-TYPE
	SYNTAX			Unsigned32
	MAX-ACCESS    		read-only
	STATUS    		current
	DESCRIPTION
        "GVP_SSG_SummaryTable.ActiveSinceSec: Indicates the time when the SSG process was started on the machine."
::= { ssgSummaryEntry 3 }

ssgTotalActiveReq OBJECT-TYPE
	SYNTAX			Unsigned32
	MAX-ACCESS    		read-only
	STATUS    		current
	DESCRIPTION
        "GVP_SSG_SummaryTable.TotalActiveReq: Total number of active requests that are currently being processed for an outbound call."
::= { ssgSummaryEntry 4 }

ssgTotalSuccessfulReq OBJECT-TYPE
	SYNTAX			Unsigned32
	MAX-ACCESS    		read-only
	STATUS    		current
	DESCRIPTION
        "GVP_SSG_SummaryTable.TotalSuccessfulReq: Total number of outbound requests for which call processing is successfully completed."
::= { ssgSummaryEntry 5 }

ssgTotalPendingReq OBJECT-TYPE
	SYNTAX			Unsigned32
	MAX-ACCESS    		read-only
	STATUS    		current
	DESCRIPTION
        "GVP_SSG_SummaryTable.TotalPendingReq: Total number of pending requests that are currently present in the database which are yet to be processed for an outbound call."
::= { ssgSummaryEntry 6 }
	
ssgTotalRecvCreateReq OBJECT-TYPE
	SYNTAX			Unsigned32
	MAX-ACCESS    		read-only
	STATUS    		current
	DESCRIPTION
        "GVP_SSG_SummaryTable.TotalRecvCreateReq: Total number of CREATE requests received from the Trigger Application (TA)."
::= { ssgSummaryEntry 7 }

ssgTotalRecvQueryReq OBJECT-TYPE
	SYNTAX			Unsigned32
	MAX-ACCESS    		read-only
	STATUS    		current
	DESCRIPTION
        "GVP_SSG_SummaryTable.TotalRecvQueryReq: Total number of QUERY requests received from the Trigger Application (TA)."
::= { ssgSummaryEntry 8 }

ssgTotalRecvCancelReq OBJECT-TYPE
	SYNTAX			Unsigned32
	MAX-ACCESS    		read-only
	STATUS    		current
	DESCRIPTION
        "GVP_SSG_SummaryTable.TotalRecvCancelReq: Total number of CANCEL requests received from the Trigger Application (TA)."
::= { ssgSummaryEntry 9 }

ssgTotalFailedQueryReq OBJECT-TYPE
	SYNTAX			Unsigned32
	MAX-ACCESS    		read-only
	STATUS    		current
	DESCRIPTION
        "GVP_SSG_SummaryTable.TotalFailedQueryReq: Total number of QUERY requests which have failed."
::= { ssgSummaryEntry 10 }

ssgTotalFailedCancelReq OBJECT-TYPE
	SYNTAX			Unsigned32
	MAX-ACCESS    		read-only
	STATUS    		current
	DESCRIPTION
        "GVP_SSG_SummaryTable.TotalFailedCancelReq: Total number of CANCEL requests for which cancellation was not performed."
::= { ssgSummaryEntry 11 }

ssgTotalMaxAttemptsExceededReq OBJECT-TYPE
	SYNTAX			Unsigned32
	MAX-ACCESS    		read-only
	STATUS    		current
	DESCRIPTION
        "GVP_SSG_SummaryTable.TotalMaxAttemptsExceededReq: Total number of requests that failed for exceeding the maximum permitted number of attempts."
::= { ssgSummaryEntry 12 }

ssgTotalTTLExpiredReq OBJECT-TYPE
	SYNTAX			Unsigned32
	MAX-ACCESS    		read-only
	STATUS    		current
	DESCRIPTION
        "GVP_SSG_SummaryTable.TotalTTLExpiredReq: Total number of requests that failed because of TTL expiry."
::= { ssgSummaryEntry 13 }

ssgTotalDestinationNotFoundReq OBJECT-TYPE
	SYNTAX			Unsigned32
	MAX-ACCESS    		read-only
	STATUS    		current
	DESCRIPTION
        "GVP_SSG_SummaryTable.TotalDestinationNotFoundReq: Total number of failed requests as destination number has not been found."
::= { ssgSummaryEntry 14 }

ssgTotalFailedReq OBJECT-TYPE
	SYNTAX			Unsigned32
	MAX-ACCESS    		read-only
	STATUS    		current
	DESCRIPTION
        "GVP_SSG_SummaryTable.TotalFailedReq: Total number of failed requests. This includes requests that failed because of TTL expiry, or exceeding the maximum permitted number of attemtps, or because the outbound number was not found."
::= { ssgSummaryEntry 15 }

ssgSIPSvrConnNotAvailableRejectedReq OBJECT-TYPE
	SYNTAX			Unsigned32
	MAX-ACCESS    		read-only
	STATUS    		current
	DESCRIPTION
        "GVP_SSG_SummaryTable.SIPSvrConnNotAvailableRejectedReq: Total number of rejected outbound requests due to SIP Server connection failure."
::= { ssgSummaryEntry 16 }

ssgResourceDNUnRegisteredRejectedReq OBJECT-TYPE
	SYNTAX			Unsigned32
	MAX-ACCESS    		read-only
	STATUS    		current
	DESCRIPTION
        "GVP_SSG_SummaryTable.ResourceDNUnRegisteredRejectedReq: Total number of rejected outbound requests due to Resource DN registration failure."
::= { ssgSummaryEntry 17 }

ssgTenantNotSupportedRejectedReq OBJECT-TYPE
	SYNTAX			Unsigned32
	MAX-ACCESS    		read-only
	STATUS    		current
	DESCRIPTION
        "GVP_SSG_SummaryTable.TenantNotSupportedRejectedReq: Total number of rejected requests as Tenant has not supported."
::= { ssgSummaryEntry 18 }

ssgTotalRejectedReq OBJECT-TYPE
	SYNTAX			Unsigned32
	MAX-ACCESS    		read-only
	STATUS    		current
	DESCRIPTION
        "GVP_SSG_SummaryTable.TotalRejectedReq: Total number of rejected requests due to request validation failures."
::= { ssgSummaryEntry 19 }

ssgTotalNotificationURLSuccessReq OBJECT-TYPE
	SYNTAX			Unsigned32
	MAX-ACCESS    		read-only
	STATUS    		current
	DESCRIPTION
        "GVP_SSG_SummaryTable.TotalNotificationURLSuccessReq: Total number of successful requests posted to Notification URL."
::= { ssgSummaryEntry 20 }

ssgTotalNotificationURLFailedReq OBJECT-TYPE
	SYNTAX			Unsigned32
	MAX-ACCESS    		read-only
	STATUS    		current
	DESCRIPTION
        "GVP_SSG_SummaryTable.TotalNotificationURLFailedReq: Total number of failed requests posted to Notification URL."
::= { ssgSummaryEntry 21 }

ssgPeakActiveReq OBJECT-TYPE
	SYNTAX			Unsigned32
	MAX-ACCESS    		read-only
	STATUS    		current
	DESCRIPTION
        "GVP_SSG_SummaryTable.PeakActiveReq: Maximum number of concurrent active requests that were handled by SSG."
::= { ssgSummaryEntry 22 }

ssgPeakPendingReq OBJECT-TYPE
	SYNTAX			Unsigned32
	MAX-ACCESS    		read-only
	STATUS    		current
	DESCRIPTION
        "GVP_SSG_SummaryTable.PeakPendingReq: Maximum number of concurrent pending requests that were present in SSG database."
::= { ssgSummaryEntry 23 }

ssgTotalRecvHTTPReq OBJECT-TYPE
	SYNTAX			Unsigned32
	MAX-ACCESS    		read-only
	STATUS    		current
	DESCRIPTION
        "GVP_SSG_SummaryTable.TotalRecvHTTPReq: Total number of HTTP requests received from Trigger Application(TA)."
::= { ssgSummaryEntry 24 }

ssgTotalRecvHTTPSReq OBJECT-TYPE
	SYNTAX			Unsigned32
	MAX-ACCESS    		read-only
	STATUS    		current
	DESCRIPTION
        "GVP_SSG_SummaryTable.TotalRecvHTTPSReq: Total number of HTTPS requests received from Trigger Application(TA)."
::= { ssgSummaryEntry 25 }

ssgTotalMaxDBReachedRejectedReq OBJECT-TYPE
	SYNTAX			Unsigned32
	MAX-ACCESS    		read-only
	STATUS    		current
	DESCRIPTION
        "GVP_SSG_SummaryTable.TotalMaxDBReachedRejectedReq: Total number of rejected requests due to maximum allowed record limit of the database reached."
::= { ssgSummaryEntry 26 }

ssgTotalInMemoryQueueReq OBJECT-TYPE
	SYNTAX			Unsigned32
	MAX-ACCESS    		read-only
	STATUS    		current
	DESCRIPTION
        "GVP_SSG_SummaryTable.TotalInMemoryQueueReq: Total number of requests present in InMemory Queue for TMakePredictiveCall processing."
::= { ssgSummaryEntry 27 }

ssgTotalTMPCQueueReq OBJECT-TYPE
	SYNTAX			Unsigned32
	MAX-ACCESS    		read-only
	STATUS    		current
	DESCRIPTION
        "GVP_SSG_SummaryTable.TotalTMPCQueueReq: Total number of requests present in TMakePredictiveCall (TMPC) Queue for outbound call processing."
::= { ssgSummaryEntry 28 }

ssgTotalFailedDigestAuthReq OBJECT-TYPE
	SYNTAX					Unsigned32
	MAX-ACCESS    			read-only
	STATUS    				current
	DESCRIPTION
        "GVP_SSG_SummaryTable.TotalFailedDigestAuthReq: Total number of HTTP/HTTPS requests failed due to Digest Authentication failure."
::= { ssgSummaryEntry 29 }

---
--- SSG SIP SERVER CONNECTION DETAILS TABLE
---

ssgSIPSvrConnTable OBJECT-TYPE
	SYNTAX      	SEQUENCE OF SsgSIPSvrConnEntry
	MAX-ACCESS     	not-accessible
	STATUS      	current
	DESCRIPTION
		"GVP_SSG_SIPSvrConnTable: Table of scalar MIBs containing SSG SIPServer Connection Details"
	::= { ssg 2 }

ssgSIPSvrConnEntry OBJECT-TYPE
	SYNTAX      	SsgSIPSvrConnEntry
	MAX-ACCESS     	not-accessible
	STATUS      	current
	DESCRIPTION
		"GVP_SSG_SIPSvrConnTable.ssgSIPSvrConnEntry: An entry (conceptual row) in the ssgSIPSvrConnTable"
	INDEX { gvpConfigDBID }
	::= { ssgSIPSvrConnTable 1 }

SsgSIPSvrConnEntry ::= SEQUENCE 
{	
	ssgSIPSvrIPAddr				DisplayString,
	ssgSIPSvrPort				Unsigned32,
	ssgSIPSvrResourceDN			DisplayString,
	ssgSIPSvrConnFailures			Unsigned32,
	ssgSIPSvrResourceDNUnRegistrations	Unsigned32,
	ssgSIPSvrConnLastFailTime		Unsigned32,
	ssgSIPSvrResourceDNLastFailTime		Unsigned32
}


ssgSIPSvrIPAddr OBJECT-TYPE
	SYNTAX			DisplayString
	MAX-ACCESS    		read-only
	STATUS    		current
	DESCRIPTION
        "GVP_SSG_SIPSvrConnTable.IPAddress: FQDN or IP Address of the SIP Server with which SSG is connected."
::= { ssgSIPSvrConnEntry 2 }

ssgSIPSvrPort OBJECT-TYPE
	SYNTAX			Unsigned32
	MAX-ACCESS    		read-only
	STATUS    		current
	DESCRIPTION
        "GVP_SSG_SIPSvrConnTable.Port: Communication Port used by SIP Server for SSG connection."
::= { ssgSIPSvrConnEntry 3 }

ssgSIPSvrResourceDN OBJECT-TYPE
	SYNTAX			DisplayString
	MAX-ACCESS    		read-only
	STATUS    		current
	DESCRIPTION
        "GVP_SSG_SIPSvrConnTable.ResourceDN: Tenant Resource DN registered with SIP Server."
::= { ssgSIPSvrConnEntry 4 }

ssgSIPSvrConnFailures OBJECT-TYPE
	SYNTAX			Unsigned32
	MAX-ACCESS    		read-only
	STATUS    		current
	DESCRIPTION
        "GVP_SSG_SIPSvrConnTable.ConnFailures: Total number of  occurrences of EventServerDisconnected event received from SIP Server."
::= { ssgSIPSvrConnEntry 5 }

ssgSIPSvrResourceDNUnRegistrations 	OBJECT-TYPE
	SYNTAX				Unsigned32
	MAX-ACCESS    			read-only
	STATUS    			current
	DESCRIPTION
        "GVP_SSG_SIPSvrConnTable.ResourceDNUnRegistrations: Total number of occurrences of Resource DN unregistration."
::= { ssgSIPSvrConnEntry 6 }

ssgSIPSvrConnLastFailTime OBJECT-TYPE
	SYNTAX			Unsigned32
	MAX-ACCESS    		read-only
	STATUS    		current
	DESCRIPTION
        "GVP_SSG_SIPSvrConnTable.ConnLastFailTime: Time period in seconds since last occurrence of SIP Server connection failure."
::= { ssgSIPSvrConnEntry 7 }

ssgSIPSvrResourceDNLastFailTime OBJECT-TYPE
	SYNTAX			Unsigned32
	MAX-ACCESS    		read-only
	STATUS    		current
	DESCRIPTION
        "GVP_SSG_SIPSvrConnTable.ResourceDNLastFailTime: Time period in seconds since last occurrence of Resource DN unregistration."
::= { ssgSIPSvrConnEntry 8 }


---
--- SSG IVRPROFILE SUMMARY TABLE
---
	
ssgIVRProfileSummaryTable OBJECT-TYPE
	SYNTAX      	SEQUENCE OF SsgIVRProfileSummaryEntry
	MAX-ACCESS     	not-accessible
	STATUS      	current
	DESCRIPTION
		"GVP_SSG_IVRProfileTable: Table containing the details of all SSG IVR Profiles"
	::= { ssg 3 }


ssgIVRProfileSummaryEntry OBJECT-TYPE
	SYNTAX      	SsgIVRProfileSummaryEntry
	MAX-ACCESS     	not-accessible
	STATUS      	current
	DESCRIPTION
		"GVP_SSG_IVRProfileTable.ssgIVRProfileSummaryEntry: An entry (conceptual row) in the ssgIVRProfileSummaryTable"
	INDEX { gvpConfigDBID, ssgIVRProfileName }
	::= { ssgIVRProfileSummaryTable 1 }
	

SsgIVRProfileSummaryEntry ::= SEQUENCE 
{	
	ssgIVRProfileName					DisplayString,
	ssgTenantName						DisplayString,
	ssgIVRProfileTotalActiveReq				Unsigned32,
	ssgIVRProfileTotalSuccessfulReq				Unsigned32,
	ssgIVRProfileTotalPendingReq				Unsigned32,
	ssgIVRProfileTotalMaxAttemptsExceededReq		Unsigned32,
	ssgIVRProfileTotalTTLExpiredReq				Unsigned32,
	ssgIVRProfileTotalDestinationNotFoundReq		Unsigned32,
	ssgIVRProfileTotalFailedReq				Unsigned32,
	ssgIVRProfileTotalNotificationURLSuccessReq		Unsigned32,
	ssgIVRProfileTotalNotificationURLFailedReq		Unsigned32,
	ssgIVRProfileSuccessfulReqCompletionAverageSec		Unsigned32,
	ssgIVRProfileSuccessfulReqRetriesAverage		Unsigned32,
	ssgIVRProfileFailedReqCompletionAverageSec		Unsigned32,
	ssgIVRProfileFailedReqRetriesAverage			Unsigned32
}	


ssgIVRProfileName OBJECT-TYPE
	SYNTAX			DisplayString
	MAX-ACCESS    		read-only
	STATUS    		current
	DESCRIPTION
        "GVP_SSG_IVRProfileTable.IVRProfileName: Name of the IVR Profile."
::= { ssgIVRProfileSummaryEntry 2 }

ssgTenantName OBJECT-TYPE
	SYNTAX			DisplayString
	MAX-ACCESS    		read-only
	STATUS    		current
	DESCRIPTION
        "GVP_SSG_IVRProfileTable.TenantName: Name of the tenant hosting the SSG's IVRProfileName."
::= { ssgIVRProfileSummaryEntry 3 }

ssgIVRProfileTotalActiveReq OBJECT-TYPE
	SYNTAX			Unsigned32
	MAX-ACCESS    		read-only
	STATUS    		current
	DESCRIPTION
        "GVP_SSG_IVRProfileTable.TotalActiveReq: Total number of active Requests that are currently being processed for an outbound call for every IVRProfileName."
::= { ssgIVRProfileSummaryEntry 4 }

ssgIVRProfileTotalSuccessfulReq OBJECT-TYPE
	SYNTAX			Unsigned32
	MAX-ACCESS    		read-only
	STATUS    		current
	DESCRIPTION
        "GVP_SSG_IVRProfileTable.TotalSuccessfulReq: Total number of outbound requests for every IVRProfileName, for which call processing is successfully completed."
::= { ssgIVRProfileSummaryEntry 5 }

ssgIVRProfileTotalPendingReq OBJECT-TYPE
	SYNTAX			Unsigned32
	MAX-ACCESS    		read-only
	STATUS    		current
	DESCRIPTION
        "GVP_SSG_IVRProfileTable.TotalPendingReq: Total number of pending requests that are currently present in the database which are yet to be processed for an outbound call."
::= { ssgIVRProfileSummaryEntry 6 }
	
ssgIVRProfileTotalMaxAttemptsExceededReq OBJECT-TYPE
	SYNTAX			Unsigned32
	MAX-ACCESS    		read-only
	STATUS    		current
	DESCRIPTION
        "GVP_SSG_IVRProfileTable.TotalMaxAttemptsExceededReq: Total number of requests that failed for exceeding the maximum permitted number of attempts, per IVRProfileName."
::= { ssgIVRProfileSummaryEntry 7 }

ssgIVRProfileTotalTTLExpiredReq OBJECT-TYPE
	SYNTAX			Unsigned32
	MAX-ACCESS    		read-only
	STATUS    		current
	DESCRIPTION
        "GVP_SSG_IVRProfileTable.TotalTTLExpiredReq: Total number of requests that failed because of TTL expiry,per IVRProfileName."
::= { ssgIVRProfileSummaryEntry 8 }

ssgIVRProfileTotalDestinationNotFoundReq OBJECT-TYPE
	SYNTAX			Unsigned32
	MAX-ACCESS    		read-only
	STATUS    		current
	DESCRIPTION
        "GVP_SSG_IVRProfileTable.TotalDestinationNotFoundReq: Total number of failed requests for this IVR Profile due to non-existence of destination number."
::= { ssgIVRProfileSummaryEntry 9 }

ssgIVRProfileTotalFailedReq OBJECT-TYPE
	SYNTAX			Unsigned32
	MAX-ACCESS    		read-only
	STATUS    		current
	DESCRIPTION
        "GVP_SSG_IVRProfileTable.TotalFailedReq: Total number of failed requests,per IVRProfileName."
::= { ssgIVRProfileSummaryEntry 10 }

ssgIVRProfileTotalNotificationURLSuccessReq OBJECT-TYPE
	SYNTAX			Unsigned32
	MAX-ACCESS    		read-only
	STATUS    		current
	DESCRIPTION
        "GVP_SSG_IVRProfileTable.TotalNotifyURLSuccessReq: Total number of requests successfully posted to notification URL, per IVRProfileName."
::= { ssgIVRProfileSummaryEntry 11 }

ssgIVRProfileTotalNotificationURLFailedReq OBJECT-TYPE
	SYNTAX			Unsigned32
	MAX-ACCESS    		read-only
	STATUS    		current
	DESCRIPTION
        "GVP_SSG_IVRProfileTable.TotalNotifyURLFailedReq: Total number of requests that failed while posting to notification URL, per IVRProfileName. This could be because of a nonexistent URL, or tbecause of a imeout issue, or because of any other error. For every failed request, a trap is generated."
::= { ssgIVRProfileSummaryEntry 12 }

ssgIVRProfileSuccessfulReqCompletionAverageSec 	OBJECT-TYPE
	SYNTAX					Unsigned32
	MAX-ACCESS    				read-only
	STATUS    				current
	DESCRIPTION
        "GVP_SSG_IVRProfileTable.SuccessfulReqCompletionAverageSec: Average number of completion of successful requests per IVRProfileName in seconds."
::= { ssgIVRProfileSummaryEntry 13 }

ssgIVRProfileSuccessfulReqRetriesAverage 	OBJECT-TYPE
	SYNTAX					Unsigned32
	MAX-ACCESS    				read-only
	STATUS    				current
	DESCRIPTION
        "GVP_SSG_IVRProfileTable.SuccessfulReqRetriesAverage: Number of retries of successful requests per IVRProfileName."
::= { ssgIVRProfileSummaryEntry 14 }

ssgIVRProfileFailedReqCompletionAverageSec	OBJECT-TYPE
	SYNTAX					Unsigned32
	MAX-ACCESS    				read-only
	STATUS    				current
	DESCRIPTION
        "GVP_SSG_IVRProfileTable.FailedReqCompletionAverageSec: Completion average of failed requests per IVRProfileName in seconds."
::= { ssgIVRProfileSummaryEntry 15 }

ssgIVRProfileFailedReqRetriesAverage 	OBJECT-TYPE
	SYNTAX				Unsigned32
	MAX-ACCESS    			read-only
	STATUS    			current
	DESCRIPTION
        "GVP_SSG_IVRProfileTable.FailedReqRetriesAverage: Retries average of failed requests per IVRProfileName."
::= { ssgIVRProfileSummaryEntry 16 }

---
--- SSG SUCCESSFUL REQUESTS STATISTICS TABLE
---
	
ssgSuccessReqStatsTable OBJECT-TYPE
	SYNTAX      	SEQUENCE OF SsgSuccessReqStatsEntry
	MAX-ACCESS     	not-accessible
	STATUS      	current
	DESCRIPTION
		"GVP_SSG_SuccessStatsTable: Table of scalar MIBs containing summary of SSG Successful Requests statistics."
	::= { ssg 4 }

ssgSuccessReqStatsEntry OBJECT-TYPE
	SYNTAX      	SsgSuccessReqStatsEntry
	MAX-ACCESS     	not-accessible
	STATUS      	current
	DESCRIPTION
		"GVP_SSG_SuccessStatsTable.ssgSuccessReqStatsEntry: An entry (conceptual row) in the ssgSuccessReqStatsTable"
	INDEX { gvpConfigDBID }
	::= { ssgSuccessReqStatsTable 1 }

SsgSuccessReqStatsEntry ::= SEQUENCE 
{	
	ssgSuccessfulReqOn1stAttempt				Unsigned32,
	ssgSuccessfulReqOn2ndAttempt				Unsigned32,
	ssgSuccessfulReqOn3rdAttempt				Unsigned32,
	ssgSuccessfulReqOn4PlusAttempts				Unsigned32,
	ssgSuccessfulBetween0And5MinsReqRecv			Unsigned32,
	ssgSuccessfulBetween5And10MinsReqRecv			Unsigned32,
	ssgSuccessfulBetween10And15MinsReqRecv			Unsigned32,
	ssgSuccessfulAbove15MinsReqRecv				Unsigned32,
	ssgSuccessfulReqWith0And5MinsTTLLeft			Unsigned32,
	ssgSuccessfulReqWith5And10MinsTTLLeft			Unsigned32,
	ssgSuccessfulReqWith10And15MinsTTLLeft			Unsigned32,
	ssgSuccessfulReqAbove15MinsTTLLeft			Unsigned32
	
}	

ssgSuccessfulReqOn1stAttempt OBJECT-TYPE
	SYNTAX			Unsigned32
	MAX-ACCESS    		read-only
	STATUS    		current
	DESCRIPTION
        "GVP_SSG_SuccessStatsTable.ReqOn1stAttempt: Total number of outbound requests for which call has been made successfully on first attempt."
::= { ssgSuccessReqStatsEntry 2 }

ssgSuccessfulReqOn2ndAttempt OBJECT-TYPE
	SYNTAX			Unsigned32
	MAX-ACCESS    		read-only
	STATUS    		current
	DESCRIPTION
        "GVP_SSG_SuccessStatsTable.ReqOn2ndAttempt: Total number of outbound requests for which call processing is successfully completed on second attempt."
::= { ssgSuccessReqStatsEntry 3 }

ssgSuccessfulReqOn3rdAttempt OBJECT-TYPE
	SYNTAX			Unsigned32
	MAX-ACCESS    		read-only
	STATUS    		current
	DESCRIPTION
        "GVP_SSG_SuccessStatsTable.ReqOn3rdAttempt: Total number of outbound requests for which call processing is successfully completed on third attempt."
::= { ssgSuccessReqStatsEntry 4 }

ssgSuccessfulReqOn4PlusAttempts OBJECT-TYPE
	SYNTAX			Unsigned32
	MAX-ACCESS    		read-only
	STATUS    		current
	DESCRIPTION
        "GVP_SSG_SuccessStatsTable.ReqOn4PlusAttempts: Total number of outbound requests for which call processing is successfully completed on fourth or higher attempt."
::= { ssgSuccessReqStatsEntry 5 }

ssgSuccessfulBetween0And5MinsReqRecv OBJECT-TYPE
	SYNTAX			Unsigned32
	MAX-ACCESS    		read-only
	STATUS    		current
	DESCRIPTION
        "GVP_SSG_SuccessStatsTable.Between0And5MinsReqRecv: Total number of outbound requests for which call processing is successfully completed with in 0-5 minutes of receiving the request from the Trigger Application (TA)."
::= { ssgSuccessReqStatsEntry 6 }
	
ssgSuccessfulBetween5And10MinsReqRecv OBJECT-TYPE
	SYNTAX			Unsigned32
	MAX-ACCESS    		read-only
	STATUS    		current
	DESCRIPTION
        "GVP_SSG_SuccessStatsTable.Between5And10MinsReqRecv: Total number of outbound requests for which call processing is successfully completed within 5-10 minutes of receiving the request from the Trigger Application (TA)."
::= { ssgSuccessReqStatsEntry 7 }

ssgSuccessfulBetween10And15MinsReqRecv OBJECT-TYPE
	SYNTAX			Unsigned32
	MAX-ACCESS    		read-only
	STATUS    		current
	DESCRIPTION
        "GVP_SSG_SuccessStatsTable.Between10And15MinsReqRecv: Total number of outbound requests for which call processing is successfully completed within 10-15 minutes of receiving the request from the Trigger Application (TA)."
::= { ssgSuccessReqStatsEntry 8 }

ssgSuccessfulAbove15MinsReqRecv OBJECT-TYPE
	SYNTAX			Unsigned32
	MAX-ACCESS    		read-only
	STATUS    		current
	DESCRIPTION
        "GVP_SSG_SuccessStatsTable.Above15MinsReqRecv: Total number of outbound requests for which call processing is successfully completed within an interval of more than 15 minutes of receiving the request from the Trigger Application (TA)."
::= { ssgSuccessReqStatsEntry 9 }

ssgSuccessfulReqWith0And5MinsTTLLeft OBJECT-TYPE
	SYNTAX			Unsigned32
	MAX-ACCESS    		read-only
	STATUS    		current
	DESCRIPTION
        "GVP_SSG_SuccessStatsTable.ReqWith0And5MinsTTLLeft: Total number of outbound requests for which call processing is successfully completed with 0-5 minutes of TTL remaining after being received from the Trigger Application (TA)."
::= { ssgSuccessReqStatsEntry 10 }

ssgSuccessfulReqWith5And10MinsTTLLeft OBJECT-TYPE
	SYNTAX			Unsigned32
	MAX-ACCESS    		read-only
	STATUS    		current
	DESCRIPTION
        "GVP_SSG_SuccessStatsTable.ReqWith5And10MinsTTLLeft: Total number of outbound requests for which call processing is successfully completed with 5-10 minutes of TTL remaining after being received from the Trigger Application (TA)."
::= { ssgSuccessReqStatsEntry 11 }

ssgSuccessfulReqWith10And15MinsTTLLeft OBJECT-TYPE
	SYNTAX			Unsigned32
	MAX-ACCESS    		read-only
	STATUS    		current
	DESCRIPTION
        "GVP_SSG_SuccessStatsTable.ReqWith10And15MinsTTLLeft: Total number of outbound requests for which call processing is successfully completed with 10-15 minutes of TTL remaining after being received from the Trigger Application (TA)."
::= { ssgSuccessReqStatsEntry 12 }

ssgSuccessfulReqAbove15MinsTTLLeft OBJECT-TYPE
	SYNTAX			Unsigned32
	MAX-ACCESS    		read-only
	STATUS    		current
	DESCRIPTION
        "GVP_SSG_SuccessStatsTable.ReqAbove15MinsTTLLeft: Total number of outbound requests for which call processing is successfully completed with 15 minutes or more of TTL remaining after being received from the Trigger Application (TA)."
::= { ssgSuccessReqStatsEntry 13 }


---
--- SSG ACTIVE REQUESTS TABLE
---

ssgActiveRequestsTable OBJECT-TYPE
	SYNTAX      	SEQUENCE OF SsgActiveRequestsEntry
	MAX-ACCESS     	not-accessible
	STATUS      	current
	DESCRIPTION
		"GVP_SSG_ActiveRequestsTable: Table containing the details of all SSG Active Requests."
	::= { ssg 5 }
	
ssgActiveRequestsEntry OBJECT-TYPE
	SYNTAX      	SsgActiveRequestsEntry
	MAX-ACCESS     	not-accessible
	STATUS      	current
	DESCRIPTION
		"GVP_SSG_ActiveRequestsTable.ssgActiveRequestsEntry: An entry (conceptual row) in the ssgActiveRequestsTable"
	INDEX { gvpConfigDBID, ssgActiveReqRequestID }
	::= { ssgActiveRequestsTable 1 }
	

SsgActiveRequestsEntry ::= SEQUENCE 
{	
	ssgActiveReqRequestID			Unsigned32,
	ssgActiveReqToken			DisplayString,
	ssgActiveReqUUID			DisplayString,
	ssgActiveReqReferenceID			Unsigned32,
	ssgActiveReqIVRPRofileName		DisplayString,
	ssgActiveReqTenantName			DisplayString,
	ssgActiveReqOutboundNumber		DisplayString,
	ssgActiveReqMaxAttempts			Unsigned32,
	ssgActiveReqAttemptsMade		Unsigned32,
	ssgActiveReqTotalTTLSec			Unsigned32,
	ssgActiveReqRemainingTTLSec		Unsigned32,
	ssgActiveReqStatus			DisplayString,
	ssgActiveReqReceivedTime		Unsigned32,
	ssgActiveReqStartTime			Unsigned32,
	ssgActiveReqANI				DisplayString
}	


ssgActiveReqRequestID OBJECT-TYPE
	SYNTAX			Unsigned32
	MAX-ACCESS    		read-only
	STATUS    		current
	DESCRIPTION
        "GVP_SSG_ActiveRequestsTable.RequestID: The RequestID of SSG's active request."
::= { ssgActiveRequestsEntry 2 }

ssgActiveReqToken OBJECT-TYPE
	SYNTAX			DisplayString
	MAX-ACCESS    		read-only
	STATUS    		current
	DESCRIPTION
        "GVP_SSG_ActiveRequestsTable.Token: The token identifier (from the Trigger Application) of SSG's active request."
::= { ssgActiveRequestsEntry 3 }

ssgActiveReqUUID OBJECT-TYPE
	SYNTAX			DisplayString
	MAX-ACCESS    		read-only
	STATUS    		current
	DESCRIPTION
        "GVP_SSG_ActiveRequestsTable.UUID: The UUID of SSG's active request. This would be first received from SIP Server for the Event Dialing message and used for debugging SIP Server logs."
::= { ssgActiveRequestsEntry 4 }

ssgActiveReqReferenceID OBJECT-TYPE
	SYNTAX			Unsigned32
	MAX-ACCESS    		read-only
	STATUS    		current
	DESCRIPTION
        "GVP_SSG_ActiveRequestsTable.ReferenceID: The ReferenceID of SSG's active request. It is used for debugging SIP Server logs."
::= { ssgActiveRequestsEntry 5 }

ssgActiveReqIVRPRofileName OBJECT-TYPE
	SYNTAX			DisplayString
	MAX-ACCESS    		read-only
	STATUS    		current
	DESCRIPTION
        "GVP_SSG_ActiveRequestsTable.IVRProfileName: The IVRProfileName of SSG's active request."
::= { ssgActiveRequestsEntry 6 }

ssgActiveReqTenantName OBJECT-TYPE
	SYNTAX			DisplayString
	MAX-ACCESS    		read-only
	STATUS    		current
	DESCRIPTION
        "GVP_SSG_ActiveRequestsTable.TenantName: The TenantName of SSG's active request."
::= { ssgActiveRequestsEntry 7 }

ssgActiveReqOutboundNumber OBJECT-TYPE
	SYNTAX			DisplayString
	MAX-ACCESS    		read-only
	STATUS    		current
	DESCRIPTION
        "GVP_SSG_ActiveRequestsTable.OutboundNumber: The outbound number of SSG's active request."
::= { ssgActiveRequestsEntry 8 }

ssgActiveReqMaxAttempts OBJECT-TYPE
	SYNTAX			Unsigned32
	MAX-ACCESS    		read-only
	STATUS    		current
	DESCRIPTION
        "GVP_SSG_ActiveRequestsTable.MaxAttempts: The maximum permitted number of attempts available for SSG's active request."
::= { ssgActiveRequestsEntry 9 }

ssgActiveReqAttemptsMade OBJECT-TYPE
	SYNTAX			Unsigned32
	MAX-ACCESS    		read-only
	STATUS    		current
	DESCRIPTION
        "GVP_SSG_ActiveRequestsTable.AttemptsMade: The number of attempts actually made by SSG's active request for outbound call processing."
::= { ssgActiveRequestsEntry 10 }

ssgActiveReqTotalTTLSec OBJECT-TYPE
	SYNTAX			Unsigned32
	MAX-ACCESS    		read-only
	STATUS    		current
	DESCRIPTION
        "GVP_SSG_ActiveRequestsTable.TotalTTL: The total time of TTL (in seconds) available to complete outbound call triggering for SSG's active request."
::= { ssgActiveRequestsEntry 11 }

ssgActiveReqRemainingTTLSec OBJECT-TYPE
	SYNTAX			Unsigned32
	MAX-ACCESS    		read-only
	STATUS    		current
	DESCRIPTION
        "GVP_SSG_ActiveRequestsTable.RemainingTTL: The total remaining time of TTL (in seconds) available to complete outbound call triggering for SSG's active request."
::= { ssgActiveRequestsEntry 12 }

ssgActiveReqStatus OBJECT-TYPE
	SYNTAX			DisplayString
	MAX-ACCESS    		read-only
	STATUS    		current
	DESCRIPTION
        "GVP_SSG_ActiveRequestsTable.Status: The event status of SSG's active request."
::= { ssgActiveRequestsEntry 13 }

ssgActiveReqReceivedTime OBJECT-TYPE
	SYNTAX			Unsigned32
	MAX-ACCESS    		read-only
	STATUS    		current
	DESCRIPTION
        "GVP_SSG_ActiveRequestsTable.RequestReceivedTime: Indicates the time when the active request was received from the Trigger Application and stored in the database."
::= { ssgActiveRequestsEntry 14 }

ssgActiveReqStartTime OBJECT-TYPE
	SYNTAX			Unsigned32
	MAX-ACCESS    		read-only
	STATUS    		current
	DESCRIPTION
        "GVP_SSG_ActiveRequestsTable.StartTime: Indicates the time when the active request was triggered for execution i.e., outbound call initiation."
::= { ssgActiveRequestsEntry 15 }

ssgActiveReqANI OBJECT-TYPE
	SYNTAX			DisplayString
	MAX-ACCESS    		read-only
	STATUS    		current
	DESCRIPTION
        "GVP_SSG_ActiveRequestsTable.ANI: The ANI of SSG's active request."
::= { ssgActiveRequestsEntry 16 }


-- #############################################################################

-- #############################################################################
-- CTIC BRANCH
-- #############################################################################

---
--- CTIC SCALAR TABLE
---

cticScalarTable OBJECT-TYPE
	SYNTAX      	SEQUENCE OF CticScalarEntry
	MAX-ACCESS     	not-accessible
	STATUS      	current
	DESCRIPTION
		"GVP_CTIC_NodeTable: Table to hold parameters in cticScalarTable"
	::= { ctic 1 }

cticScalarEntry OBJECT-TYPE
	SYNTAX      	CticScalarEntry
	MAX-ACCESS     	not-accessible
	STATUS      	current
	DESCRIPTION
		"GVP_CTIC_NodeTable.cticScalarEntry: An entry (conceptual row) in the cticScalarTable"
	INDEX { gvpConfigDBID }
	::= { cticScalarTable 1 }

CticScalarEntry ::= SEQUENCE 
{	
	cticActiveNode				DisplayString,
	cticActiveSince				DisplayString,
	cticTenantName				DisplayString,
	cticTotalCalls                  	Unsigned32,
	cticTotalCallsCompleted         	Unsigned32,
	cticTotalCallsFailedAtCTI       	Unsigned32,
	cticTotalCallsFailedAtGVPPlatform	Unsigned32,
	cticTotalActiveCalls			Unsigned32,
	cticTotalQueuedCalls			Unsigned32,
	cticTotalBridgedCalls			Unsigned32,
	cticTotalRouteResponses         	Unsigned32,
	cticTotalDefaultAgentResp       	Unsigned32,
	cticTotalNewCallFailed			Unsigned32,
	cticTotalRouteReqFailed        		Unsigned32,
	cticTotalSIPCalls	     		Unsigned32,
	cticTotalSIPCallsAnswered    	 	Unsigned32,
	cticTotalSIPCallsRejected    	 	Unsigned32,
	cticTotalSIPCallsCompleted   	 	Unsigned32,
	cticTotalCallsCompletedInIVR   	 	Unsigned32,
	cticTotalActiveInboundCalls		Unsigned32,
	cticTotalActiveOutboundCalls		Unsigned32
	
}

cticActiveNode OBJECT-TYPE
	SYNTAX			DisplayString
	MAX-ACCESS    		read-only
	STATUS    		current
	DESCRIPTION
        "GVP_CTIC_NodeTable.ActiveNode: IP and Port of the active RM Node."
::= { cticScalarEntry 2 }

cticActiveSince OBJECT-TYPE
	SYNTAX			DisplayString
	MAX-ACCESS    		read-only
	STATUS    		current
	DESCRIPTION
        "GVP_CTIC_NodeTable.ActiveSince: Time since which this node is active."
::= { cticScalarEntry 3 }

cticTenantName OBJECT-TYPE
	SYNTAX			DisplayString
	MAX-ACCESS    		read-only
	STATUS    		current
	DESCRIPTION
        "GVP_CTIC_NodeTable.TenantName: Tenant Name for which CTI is handling the call."
::= { cticScalarEntry 4 }

cticTotalCalls OBJECT-TYPE
	SYNTAX			Unsigned32
	MAX-ACCESS    		read-only
	STATUS    		current
	DESCRIPTION
        "GVP_CTIC_NodeTable.TotalCalls: Total Number of calls received"
::= { cticScalarEntry 5 }

cticTotalCallsCompleted OBJECT-TYPE
	SYNTAX			Unsigned32
	MAX-ACCESS    		read-only
	STATUS    		current
	DESCRIPTION
        "GVP_CTIC_NodeTable.TotalCallsCompleted: Total number of calls completed."
::= { cticScalarEntry 6 }


cticTotalCallsFailedAtCTI OBJECT-TYPE
	SYNTAX			Unsigned32
	MAX-ACCESS    		read-only
	STATUS    		current
	DESCRIPTION
        "GVP_CTIC_NodeTable.TotalCallsFailedAtCTI: Total number of calls failed at CTI."
::= { cticScalarEntry 7 }

cticTotalCallsFailedAtGVPPlatform OBJECT-TYPE
	SYNTAX			Unsigned32
	MAX-ACCESS    		read-only
	STATUS    		current
	DESCRIPTION
        "GVP_CTIC_NodeTable.TotalCallsFailedAtGVPPlatform: Total number of calls failed at GVP Platform."
::= { cticScalarEntry 8 }

cticTotalActiveCalls OBJECT-TYPE
	SYNTAX			Unsigned32
	MAX-ACCESS    		read-only
	STATUS    		current
	DESCRIPTION
        "GVP_CTIC_NodeTable.TotalActiveCalls: Total number of Active Calls."
::= { cticScalarEntry 9 }

cticTotalQueuedCalls OBJECT-TYPE
	SYNTAX			Unsigned32
	MAX-ACCESS    		read-only
	STATUS    		current
	DESCRIPTION
        "GVP_CTIC_NodeTable.TotalQueuedCalls: Total number of Queued Calls."
::= { cticScalarEntry 10 }

cticTotalBridgedCalls OBJECT-TYPE
	SYNTAX			Unsigned32
	MAX-ACCESS    		read-only
	STATUS    		current
	DESCRIPTION
        "GVP_CTIC_NodeTable.TotalBridgedCalls: Total number of Bridged Calls."
::= { cticScalarEntry 11 }

cticTotalRouteResponses OBJECT-TYPE
	SYNTAX			Unsigned32
	MAX-ACCESS    		read-only
	STATUS    		current
	DESCRIPTION
        "GVP_CTIC_NodeTable.TotalRouteResponses: Total number of Route Responses received."
::= { cticScalarEntry 12 }

cticTotalDefaultAgentResp OBJECT-TYPE
	SYNTAX			Unsigned32
	MAX-ACCESS    		read-only
	STATUS    		current
	DESCRIPTION
        "GVP_CTIC_NodeTable.TotalDefaultAgentResp: Total number of Default Agent responses received."
::= { cticScalarEntry 13 }

cticTotalNewCallFailed OBJECT-TYPE
	SYNTAX			Unsigned32
	MAX-ACCESS    		read-only
	STATUS    		current
	DESCRIPTION
        "GVP_CTIC_NodeTable.TotalNewCallFailed: Total number of NewCall requests failed."
::= { cticScalarEntry 14 }

cticTotalRouteReqFailed OBJECT-TYPE
	SYNTAX			Unsigned32
	MAX-ACCESS    		read-only
	STATUS    		current
	DESCRIPTION
        "GVP_CTIC_NodeTable.TotalRouteReqFailed: Total number of Route Requests failed."
::= { cticScalarEntry 15 }

cticTotalSIPCalls OBJECT-TYPE
	SYNTAX			Unsigned32
	MAX-ACCESS    		read-only
	STATUS    		current
	DESCRIPTION
        "GVP_CTIC_NodeTable.TotalSIPCalls: Total number of SIP calls created."
::= { cticScalarEntry 16 }

cticTotalSIPCallsAnswered OBJECT-TYPE
	SYNTAX			Unsigned32
	MAX-ACCESS    		read-only
	STATUS    		current
	DESCRIPTION
        "GVP_CTIC_NodeTable.TotalSIPCallsAnswered: Total number of SIP calls answered."
::= { cticScalarEntry 17 }

cticTotalSIPCallsRejected OBJECT-TYPE
	SYNTAX			Unsigned32
	MAX-ACCESS    		read-only
	STATUS    		current
	DESCRIPTION
        "GVP_CTIC_NodeTable.TotalSIPCallsRejected: Total number of SIP calls rejected."
::= { cticScalarEntry 18 }

cticTotalSIPCallsCompleted OBJECT-TYPE
	SYNTAX			Unsigned32
	MAX-ACCESS    		read-only
	STATUS    		current
	DESCRIPTION
        "GVP_CTIC_NodeTable.TotalSIPCallsCompleted: Total number of SIP calls completed."
::= { cticScalarEntry 19 }

cticTotalCallsCompletedInIVR OBJECT-TYPE
	SYNTAX			Unsigned32
	MAX-ACCESS    		read-only
	STATUS    		current
	DESCRIPTION
        "GVP_CTIC_NodeTable.TotalCallsCompletedInIVR: Total number of calls completed in IVR."
::= { cticScalarEntry 20 }

cticTotalActiveInboundCalls OBJECT-TYPE
	SYNTAX			Unsigned32
	MAX-ACCESS    		read-only
	STATUS    		current
	DESCRIPTION
        "GVP_CTIC_NodeTable.TotalActiveInboundCalls: Total number of active inbound calls."
::= { cticScalarEntry 21 }

cticTotalActiveOutboundCalls OBJECT-TYPE
	SYNTAX			Unsigned32
	MAX-ACCESS    		read-only
	STATUS    		current
	DESCRIPTION
        "GVP_CTIC_NodeTable.TotalActiveOutboundCalls: Total number of active outbound calls."
::= { cticScalarEntry 22 }


---
--- CTIC ISERVER CONNECTION TABLE
---

cticISvrConnTable OBJECT-TYPE
	SYNTAX      	SEQUENCE OF CticISvrConnEntry
	MAX-ACCESS     	not-accessible
	STATUS      	current
	DESCRIPTION
		"GVP_CTIC_ISvrConnTable: Table to hold parameters in cticISvrConnTable"
	::= { ctic 2 }


cticISvrConnEntry OBJECT-TYPE
	SYNTAX      	CticISvrConnEntry
	MAX-ACCESS     	not-accessible
	STATUS      	current
	DESCRIPTION
		"GVP_CTIC_ISvrConnTable.cticISvrConnEntry: An entry (conceptual row) in the cticISvrConnTable"
	INDEX { gvpConfigDBID, cticISvrAddr }
	::= { cticISvrConnTable 1 }

CticISvrConnEntry ::= SEQUENCE 
{	
	cticISvrAddr			DisplayString,
	cticISvrStatus			DisplayString,
	cticTotalNWFailures		Unsigned32,
	cticLastFailDate		DisplayString
}

cticISvrAddr OBJECT-TYPE
	SYNTAX			DisplayString
	MAX-ACCESS    		read-only
	STATUS    		current
	DESCRIPTION
        "GVP_CTIC_ISvrConnTable.ISvrAddress: The Address of the IServer."
::= { cticISvrConnEntry 2 }

cticISvrStatus OBJECT-TYPE
	SYNTAX			DisplayString
	MAX-ACCESS    		read-only
	STATUS    		current
	DESCRIPTION
        "GVP_CTIC_ISvrConnTable.ConnStatus: The current status of the IServer."
::= { cticISvrConnEntry 3 }

cticTotalNWFailures OBJECT-TYPE
	SYNTAX			Unsigned32
	MAX-ACCESS    		read-only
	STATUS    		current
	DESCRIPTION
        "GVP_CTIC_ISvrConnTable.TotalNWFailures: Total Number of Network Failures."
::= { cticISvrConnEntry 4 }

cticLastFailDate OBJECT-TYPE
	SYNTAX			DisplayString
	MAX-ACCESS    		read-only
	STATUS    		current
	DESCRIPTION
        "GVP_CTIC_ISvrConnTable.LastFailDate: Time and date of Last Failure."
::= { cticISvrConnEntry 5 }


---
--- CTIC ACTIVE CALLS TABLE
---

cticActiveCallsTable OBJECT-TYPE
	SYNTAX      	SEQUENCE OF CticActiveCallsEntry
	MAX-ACCESS     	not-accessible
	STATUS      	current
	DESCRIPTION
		"GVP_CTIC_ActiveCallsTable: Table to hold parameters in cticActiveCallsTable"
	::= { ctic 3 }


cticActiveCallsEntry OBJECT-TYPE
	SYNTAX      	CticActiveCallsEntry
	MAX-ACCESS     	not-accessible
	STATUS      	current
	DESCRIPTION
		"GVP_CTIC_ActiveCallsTable.cticActiveCallsEntry: An entry (conceptual row) in the cticActiveCallsTable"
	INDEX { gvpConfigDBID, cticSessionID }
	::= { cticActiveCallsTable 1 }

CticActiveCallsEntry ::= SEQUENCE 
{	
	cticSessionID			DisplayString,
	cticConnID  			DisplayString,
	cticB2BUAState			DisplayString,
	cticTotalSIPLegs		Unsigned32,
	cticDNIS			DisplayString,
	cticANI				DisplayString,
	cticCTIState			DisplayString,
	cticTreatmentID			DisplayString,
	cticStartTime			DisplayString,
	cticRouteRespRecvTime		DisplayString,
	cticDialedNum			DisplayString,
	cticTransferReqCount		Unsigned32
}

cticSessionID OBJECT-TYPE
	SYNTAX			DisplayString
	MAX-ACCESS    		read-only
	STATUS    		current
	DESCRIPTION
        "GVP_CTIC_ActiveCallsTable.SessionID: Unique SessionID of the Call."
::= { cticActiveCallsEntry 2 }

cticConnID OBJECT-TYPE
	SYNTAX			DisplayString
	MAX-ACCESS    		read-only
	STATUS    		current
	DESCRIPTION
        "GVP_CTIC_ActiveCallsTable.ConnID: ConnectionID returned by IServer for the call."
::= { cticActiveCallsEntry 3 }

cticB2BUAState OBJECT-TYPE
	SYNTAX			DisplayString
	MAX-ACCESS    		read-only
	STATUS    		current
	DESCRIPTION
        "GVP_CTIC_ActiveCallsTable.B2BUAState: B2BUAState state of the call."
::= { cticActiveCallsEntry 4 }

cticTotalSIPLegs OBJECT-TYPE
	SYNTAX			Unsigned32
	MAX-ACCESS    		read-only
	STATUS    		current
	DESCRIPTION
        "GVP_CTIC_ActiveCallsTable.TotalSIPLegs: Total number of SIPCallLegs for the call"
::= { cticActiveCallsEntry 5 }

cticDNIS OBJECT-TYPE
	SYNTAX			DisplayString
	MAX-ACCESS    		read-only
	STATUS    		current
	DESCRIPTION
        "GVP_CTIC_ActiveCallsTable.DNIS: DNIS of the call."
::= { cticActiveCallsEntry 6 }

cticANI OBJECT-TYPE
	SYNTAX			DisplayString
	MAX-ACCESS    		read-only
	STATUS    		current
	DESCRIPTION
        "GVP_CTIC_ActiveCallsTable.ANI: ANI of the call."
::= { cticActiveCallsEntry 7 }

cticCTIState OBJECT-TYPE
	SYNTAX			DisplayString
	MAX-ACCESS    		read-only
	STATUS    		current
	DESCRIPTION
        "GVP_CTIC_ActiveCallsTable.CTIState: CTIState of the call."
::= { cticActiveCallsEntry 8 }

cticTreatmentID OBJECT-TYPE
	SYNTAX			DisplayString
	MAX-ACCESS    		read-only
	STATUS    		current
	DESCRIPTION
        "GVP_CTIC_ActiveCallsTable.TreatmentID: TreatmentID of the call."
::= { cticActiveCallsEntry 9 }

cticStartTime OBJECT-TYPE
	SYNTAX			DisplayString
	MAX-ACCESS    		read-only
	STATUS    		current
	DESCRIPTION
        "GVP_CTIC_ActiveCallsTable.StartTime: Time at which the call has started."
::= { cticActiveCallsEntry 10 }

cticRouteRespRecvTime OBJECT-TYPE
	SYNTAX			DisplayString
	MAX-ACCESS    		read-only
	STATUS    		current
	DESCRIPTION
        "GVP_CTIC_ActiveCallsTable.RouteRespRecvTime: Time at which RouteResponse message received from IServer."
::= { cticActiveCallsEntry 11 }

cticDialedNum OBJECT-TYPE
	SYNTAX			DisplayString
	MAX-ACCESS    		read-only
	STATUS    		current
	DESCRIPTION
        "GVP_CTIC_ActiveCallsTable.DialedNum: Dialed Number sent in the NEW_CALL/ROUTE_REQ_EVENT message to ICM."
::= { cticActiveCallsEntry 12 }

cticTransferReqCount OBJECT-TYPE
	SYNTAX			Unsigned32
	MAX-ACCESS    		read-only
	STATUS    		current
	DESCRIPTION
        "GVP_CTIC_ActiveCallsTable.TransferReqCount: Counts the number of times ICM requests for transfer (CONNECT/CONNECT_TO_RESOURCE)."
::= { cticActiveCallsEntry 13 }

---
--- CTIC SIP CALLS TABLE
---

cticSIPCallsTable OBJECT-TYPE
	SYNTAX      	SEQUENCE OF CticSIPCallsEntry
	MAX-ACCESS     	not-accessible
	STATUS      	current
	DESCRIPTION
		"GVP_CTIC_SIPCallsTable: Table to hold parameters in cticSIPCallsTable"
	::= { ctic 4 }


cticSIPCallsEntry OBJECT-TYPE
	SYNTAX      	CticSIPCallsEntry
	MAX-ACCESS     	not-accessible
	STATUS      	current
	DESCRIPTION
		"GVP_CTIC_SIPCallsTable.cticSIPCallsEntry: An entry (conceptual row) in the cticSIPCallsTable"
	INDEX { gvpConfigDBID, cticSIPCallReference }		
	::= { cticSIPCallsTable 1 }

CticSIPCallsEntry ::= SEQUENCE 
{	
	cticSIPCallReference		DisplayString,
	cticSIPCallSessionID		DisplayString,
	cticSIPCallState		DisplayString,
	cticSIPCallType			DisplayString,
	cticSIPCallID			DisplayString
}

cticSIPCallReference OBJECT-TYPE
	SYNTAX			DisplayString
	MAX-ACCESS    		read-only
	STATUS    		current
	DESCRIPTION
        "GVP_CTIC_SIPCallsTable.SIPCallReference: Reference of the SIPCall Object."
::= { cticSIPCallsEntry 2 }

cticSIPCallSessionID OBJECT-TYPE
	SYNTAX			DisplayString
	MAX-ACCESS    		read-only
	STATUS    		current
	DESCRIPTION
        "GVP_CTIC_SIPCallsTable.SIPCallSessionID: SessionID of the Call for which the SIP Call belongs."
::= { cticSIPCallsEntry 3 }

cticSIPCallState OBJECT-TYPE
	SYNTAX			DisplayString
	MAX-ACCESS    		read-only
	STATUS    		current
	DESCRIPTION
        "GVP_CTIC_SIPCallsTable.SIPCallState: State of the SIPCall."
::= { cticSIPCallsEntry 4 }

cticSIPCallType OBJECT-TYPE
	SYNTAX			DisplayString
	MAX-ACCESS    		read-only
	STATUS    		current
	DESCRIPTION
        "GVP_CTIC_SIPCallsTable.SIPCallType: Type of the SIPCall."
::= { cticSIPCallsEntry 5 }

cticSIPCallID OBJECT-TYPE
	SYNTAX			DisplayString
	MAX-ACCESS    		read-only
	STATUS    		current
	DESCRIPTION
        "GVP_CTIC_SIPCallsTable.SIPCallID: ID of the SIPCall."
::= { cticSIPCallsEntry 6 }

---
--- CTIC ICM CONNECTION TABLE
---

cticICMConnTable OBJECT-TYPE
	SYNTAX      	SEQUENCE OF CticICMConnEntry
	MAX-ACCESS     	not-accessible
	STATUS      	current
	DESCRIPTION
		"GVP_CTIC_ICMConnTable: Table to hold parameters in cticICMConnTable"
	::= { ctic 5 }


cticICMConnEntry OBJECT-TYPE
	SYNTAX      	CticICMConnEntry
	MAX-ACCESS     	not-accessible
	STATUS      	current
	DESCRIPTION
		"GVP_CTIC_ICMConnTable.cticICMConnEntry: An entry (conceptual row) in the cticICMConnTable"
	INDEX { gvpConfigDBID, cticPGCommunicationPort }
	::= { cticICMConnTable 1 }

CticICMConnEntry ::= SEQUENCE 
{	
	cticPGCommunicationPort		Unsigned32,
	cticTenant			DisplayString,
	cticPGAddress			DisplayString,
	cticConnectionState		DisplayString,
	cticConnectionTime		DisplayString,
	cticCurrentActiveCalls		Unsigned32,
	cticCallsCompleted		Unsigned32,
	cticCallsFailed			Unsigned32,
	cticLastFailureTime		DisplayString
}

cticPGCommunicationPort OBJECT-TYPE
	SYNTAX			Unsigned32
	MAX-ACCESS    		read-only
	STATUS    		current
	DESCRIPTION
        "GVP_CTIC_ICMConnTable.PGCommunicationPort: The listening port on which CTIC accepts new connection requests from ICM"
::= { cticICMConnEntry 2 }

cticTenant OBJECT-TYPE
	SYNTAX			DisplayString
	MAX-ACCESS    		read-only
	STATUS    		current
	DESCRIPTION
        "GVP_CTIC_ICMConnTable.TenantName: Name of the tenant for which CTIC handling the calls on this port"
::= { cticICMConnEntry 3 }

cticPGAddress OBJECT-TYPE
	SYNTAX			DisplayString
	MAX-ACCESS    		read-only
	STATUS    		current
	DESCRIPTION
        "GVP_CTIC_ICMConnTable.PGAddress: IP address of ICM from which the connection request is accepted"
::= { cticICMConnEntry 4 }

cticConnectionState OBJECT-TYPE
	SYNTAX			DisplayString
	MAX-ACCESS    		read-only
	STATUS    		current
	DESCRIPTION
        "GVP_CTIC_ICMConnTable.ConnectionState: The state of the connection (either UP or DOWN)"
::= { cticICMConnEntry 5 }

cticConnectionTime OBJECT-TYPE
	SYNTAX			DisplayString
	MAX-ACCESS    		read-only
	STATUS    		current
	DESCRIPTION
        "GVP_CTIC_ICMConnTable.ConnectionTime: The time at which the connection request from ICM is accepted by CTIC"
::= { cticICMConnEntry 6 }

cticCurrentActiveCalls OBJECT-TYPE
	SYNTAX			Unsigned32
	MAX-ACCESS    		read-only
	STATUS    		current
	DESCRIPTION
        "GVP_CTIC_ICMConnTable.CurrentActiveCalls: The current number of active calls on this port"
::= { cticICMConnEntry 7 }

cticCallsCompleted OBJECT-TYPE
	SYNTAX			Unsigned32
	MAX-ACCESS    		read-only
	STATUS    		current
	DESCRIPTION
        "GVP_CTIC_ICMConnTable.CallsCompleted: The total number of calls successfully completed on this port"
::= { cticICMConnEntry 8 }

cticCallsFailed OBJECT-TYPE
	SYNTAX			Unsigned32
	MAX-ACCESS    		read-only
	STATUS    		current
	DESCRIPTION
        "GVP_CTIC_ICMConnTable.CallsFailed: The total number of calls failed on this port"
::= { cticICMConnEntry 9 }

cticLastFailureTime OBJECT-TYPE
	SYNTAX			DisplayString
	MAX-ACCESS    		read-only
	STATUS    		current
	DESCRIPTION
        "GVP_CTIC_ICMConnTable.LastFailureTime: Time and date of the last connection failure with ICM."
::= { cticICMConnEntry 10 }


-- #############################################################################
-- CCP BRANCH
-- #############################################################################

---
--- CCP SCALAR TABLE
---

ccpScalarTable OBJECT-TYPE
	SYNTAX      	SEQUENCE OF CcpScalarEntry
	MAX-ACCESS     	not-accessible
	STATUS      	current
	DESCRIPTION
		"GVP_CallControlPlatform: Table to hold parameters in ccpScalarTable"
	::= { ccp 1 }

ccpScalarEntry OBJECT-TYPE
	SYNTAX      	CcpScalarEntry
	MAX-ACCESS     	not-accessible
	STATUS      	current
	DESCRIPTION
		"GVP_CallControlPlatform.ccpScalarEntry: An entry (conceptual row) in the ccpScalarTable"
	INDEX { gvpConfigDBID }
	::= { ccpScalarTable 1 }

CcpScalarEntry ::= SEQUENCE 
{	
	ccpCurrentConnections		Unsigned32,
	ccpPeakConnections		Unsigned32,
	ccpTotalConnections		Unsigned32,
	ccpCurrentDialogs		Unsigned32,
	ccpPeakDialogs			Unsigned32,
	ccpTotalDialogs			Unsigned32,
	ccpCurrentConferences		Unsigned32,
	ccpPeakConferences		Unsigned32,
	ccpTotalConferences		Unsigned32,	
	ccpCurrentConferenceParticipants	Unsigned32,
	ccpPeakConferenceParticipants	Unsigned32,
	ccpTotalConferenceParticipants	Unsigned32,
	ccpCurrentBridgeParticipants	Unsigned32,
	ccpPeakBridgeParticipants	Unsigned32,
	ccpTotalBridgeParticipants	Unsigned32,
	ccpCurrentSessions		Unsigned32,
	ccpPeakSessions			Unsigned32,
	ccpTotalSessions		Unsigned32,
	ccpConnectedToMF		Unsigned32
}

ccpCurrentConnections OBJECT-TYPE
	SYNTAX			Unsigned32
	MAX-ACCESS    		read-only
	STATUS    		current
	DESCRIPTION
        "GVP_CallControlPlatform.Current_Connections: Number of connections that currently are established."
::= { ccpScalarEntry 2 }

ccpPeakConnections OBJECT-TYPE
	SYNTAX			Unsigned32
	MAX-ACCESS    		read-only
	STATUS    		current
	DESCRIPTION
        "GVP_CallControlPlatform.Peak_Connections: Maximum number of connections."
::= { ccpScalarEntry 3 }

ccpTotalConnections OBJECT-TYPE
	SYNTAX			Unsigned32
	MAX-ACCESS    		read-only
	STATUS    		current
	DESCRIPTION
        "GVP_CallControlPlatform.Total_Connections: Total number of connections."
::= { ccpScalarEntry 4 }

ccpCurrentDialogs OBJECT-TYPE
	SYNTAX			Unsigned32
	MAX-ACCESS    		read-only
	STATUS    		current
	DESCRIPTION
        "GVP_CallControlPlatform.Current_Dialogs: Number of dialogs that currently are established."
::= { ccpScalarEntry 5 }

ccpPeakDialogs OBJECT-TYPE
	SYNTAX			Unsigned32
	MAX-ACCESS    		read-only
	STATUS    		current
	DESCRIPTION
        "GVP_CallControlPlatform.Peak_Dialogs: Maximum number of dialogs."
::= { ccpScalarEntry 6 }

ccpTotalDialogs OBJECT-TYPE
	SYNTAX			Unsigned32
	MAX-ACCESS    		read-only
	STATUS    		current
	DESCRIPTION
        "GVP_CallControlPlatform.Total_Dialogs: Total number of dialogs."
::= { ccpScalarEntry 7 }

ccpCurrentConferences OBJECT-TYPE
	SYNTAX			Unsigned32
	MAX-ACCESS    		read-only
	STATUS    		current
	DESCRIPTION
        "GVP_CallControlPlatform.Current_Conferences: Number of conferences that currently are created."
::= { ccpScalarEntry 8 }

ccpPeakConferences OBJECT-TYPE
	SYNTAX			Unsigned32
	MAX-ACCESS    		read-only
	STATUS    		current
	DESCRIPTION
        "GVP_CallControlPlatform.Peak_Conferences: Maximum number of conferences."
::= { ccpScalarEntry 9 }

ccpTotalConferences OBJECT-TYPE
	SYNTAX			Unsigned32
	MAX-ACCESS    		read-only
	STATUS    		current
	DESCRIPTION
        "GVP_CallControlPlatform.Total_Conferences: Total number of conferences."
::= { ccpScalarEntry 10 }

ccpCurrentConferenceParticipants OBJECT-TYPE
	SYNTAX			Unsigned32
	MAX-ACCESS    		read-only
	STATUS    		current
	DESCRIPTION
        "GVP_CallControlPlatform.Current_Conference_Participants: Current number of conference participants."
::= { ccpScalarEntry 11 }

ccpPeakConferenceParticipants OBJECT-TYPE
	SYNTAX			Unsigned32
	MAX-ACCESS    		read-only
	STATUS    		current
	DESCRIPTION
        "GVP_CallControlPlatform.Peak_Conference_Participants: Maximum number of conference participants."
::= { ccpScalarEntry 12 }

ccpTotalConferenceParticipants OBJECT-TYPE
	SYNTAX			Unsigned32
	MAX-ACCESS    		read-only
	STATUS    		current
	DESCRIPTION
        "GVP_CallControlPlatform.Total_Conference_Participants: Total number of conference participants."
::= { ccpScalarEntry 13 }

ccpCurrentBridgeParticipants OBJECT-TYPE
	SYNTAX			Unsigned32
	MAX-ACCESS    		read-only
	STATUS    		current
	DESCRIPTION
        "GVP_CallControlPlatform.Current_Bridge_Participants: Current bridging server participants."
::= { ccpScalarEntry 14 }

ccpPeakBridgeParticipants OBJECT-TYPE
	SYNTAX			Unsigned32
	MAX-ACCESS    		read-only
	STATUS    		current
	DESCRIPTION
        "GVP_CallControlPlatform.Peak_Bridge_Participants: Peak bridging server participants."
::= { ccpScalarEntry 15 }

ccpTotalBridgeParticipants OBJECT-TYPE
	SYNTAX			Unsigned32
	MAX-ACCESS    		read-only
	STATUS    		current
	DESCRIPTION
        "GVP_CallControlPlatform.Total_Bridge_Participants: Total bridging server participants."
::= { ccpScalarEntry 16 }

ccpCurrentSessions OBJECT-TYPE
	SYNTAX			Unsigned32
	MAX-ACCESS    		read-only
	STATUS    		current
	DESCRIPTION
        "GVP_CallControlPlatform.Current_Sessions: Number of current sessions."
::= { ccpScalarEntry 17 }

ccpPeakSessions OBJECT-TYPE
	SYNTAX			Unsigned32
	MAX-ACCESS    		read-only
	STATUS    		current
	DESCRIPTION
        "GVP_CallControlPlatform.Peak_Sessions: Maximum number of sessions."
::= { ccpScalarEntry 18 }

ccpTotalSessions OBJECT-TYPE
	SYNTAX			Unsigned32
	MAX-ACCESS    		read-only
	STATUS    		current
	DESCRIPTION
        "GVP_CallControlPlatform.Total_Sessions: Total number of sessions."
::= { ccpScalarEntry 19 }

ccpConnectedToMF OBJECT-TYPE
	SYNTAX			Unsigned32
	MAX-ACCESS    		read-only
	STATUS    		current
	DESCRIPTION
        "GVP_CallControlPlatform.Connected_To_MF: Status of CCP connection to Management Framework."
::= { ccpScalarEntry 20 }


-- #############################################################################
-- RM BRANCH
-- #############################################################################

---
--- RM SCALAR TABLE
---

rmScalarTable OBJECT-TYPE
	SYNTAX      	SEQUENCE OF RmScalarEntry
	MAX-ACCESS     	not-accessible
	STATUS      	current
	DESCRIPTION
		"GVP_RM_NodeTable: Table to hold parameters in rmScalarTable"
	::= { rm 1 }

rmScalarEntry OBJECT-TYPE
	SYNTAX      	RmScalarEntry
	MAX-ACCESS     	not-accessible
	STATUS      	current
	DESCRIPTION
		"GVP_RM_NodeTable.rmScalarEntry: An entry (conceptual row) in the rmScalarTable"
	INDEX { gvpConfigDBID }
	::= { rmScalarTable 1 }

RmScalarEntry ::= SEQUENCE 
{	
	rmActiveNode			DisplayString,
	rmSuccessfulCalls		Unsigned32,
	rmRejectedCalls			Unsigned32,
	rmActiveSince			DisplayString,
	rmTotalInboundSessions		Unsigned32,
	rmTotalOutboundSessions		Unsigned32,
	rmTotalRequestsForwarded	Unsigned32,
	rmRequestsForwardedPast5mins	Unsigned32,
	rmPeakRequestsForwarded		Unsigned32,
	rmTotalRetransmissions		Unsigned32,
	rmTotalInviteReceived		Unsigned32,
	rmTotalAckReceived		Unsigned32,
	rmTotalByeReceived		Unsigned32,
	rmTotalCancelReceived		Unsigned32,
	rmTotalInfoReceived		Unsigned32,
	rmTotalOptionsReceived		Unsigned32,
	rmTotalUnknownReceived		Unsigned32,
	rmTotal1xxInviteReceived	Unsigned32,
	rmTotal1xxByeReceived		Unsigned32,
	rmTotal1xxCancelReceived	Unsigned32,
	rmTotal1xxInfoReceived		Unsigned32,
	rmTotal1xxOptionsReceived	Unsigned32,
	rmTotal1xxUnknownReceived	Unsigned32,
	rmTotal2xxInviteReceived	Unsigned32,
	rmTotal2xxByeReceived		Unsigned32,
	rmTotal2xxCancelReceived	Unsigned32,
	rmTotal2xxInfoReceived		Unsigned32,
	rmTotal2xxOptionsReceived	Unsigned32,
	rmTotal2xxUnknownReceived	Unsigned32,
	rmTotal3xxInviteReceived	Unsigned32,
	rmTotal3xxByeReceived		Unsigned32,
	rmTotal3xxCancelReceived	Unsigned32,
	rmTotal3xxInfoReceived		Unsigned32,
	rmTotal3xxOptionsReceived	Unsigned32,
	rmTotal3xxUnknownReceived	Unsigned32,
	rmTotal4xxInviteReceived	Unsigned32,
	rmTotal4xxByeReceived		Unsigned32,
	rmTotal4xxCancelReceived	Unsigned32,
	rmTotal4xxInfoReceived		Unsigned32,
	rmTotal4xxOptionsReceived	Unsigned32,
	rmTotal4xxUnknownReceived	Unsigned32,
	rmTotal5xxInviteReceived	Unsigned32,
	rmTotal5xxByeReceived		Unsigned32,
	rmTotal5xxCancelReceived	Unsigned32,
	rmTotal5xxInfoReceived		Unsigned32,
	rmTotal5xxOptionsReceived	Unsigned32,
	rmTotal5xxUnknownReceived	Unsigned32,
	rmTotal6xxInviteReceived	Unsigned32,
	rmTotal6xxByeReceived		Unsigned32,
	rmTotal6xxCancelReceived	Unsigned32,
	rmTotal6xxInfoReceived		Unsigned32,
	rmTotal6xxOptionsReceived	Unsigned32,
	rmTotal6xxUnknownReceived	Unsigned32,
	rmTotalInviteSent		Unsigned32,
	rmTotalAckSent			Unsigned32,
	rmTotalByeSent			Unsigned32,
	rmTotalCancelSent		Unsigned32,
	rmTotalInfoSent			Unsigned32,
	rmTotalOptionsSent		Unsigned32,
	rmTotalUnknownSent		Unsigned32,
	rmTotal1xxInviteSent		Unsigned32,
	rmTotal1xxByeSent		Unsigned32,
	rmTotal1xxCancelSent		Unsigned32,
	rmTotal1xxInfoSent		Unsigned32,
	rmTotal1xxOptionsSent		Unsigned32,
	rmTotal1xxUnknownSent		Unsigned32,
	rmTotal2xxInviteSent		Unsigned32,
	rmTotal2xxByeSent		Unsigned32,
	rmTotal2xxCancelSent		Unsigned32,
	rmTotal2xxInfoSent		Unsigned32,
	rmTotal2xxOptionsSent		Unsigned32,
	rmTotal2xxUnknownSent		Unsigned32,
	rmTotal3xxInviteSent		Unsigned32,
	rmTotal3xxByeSent		Unsigned32,
	rmTotal3xxCancelSent		Unsigned32,
	rmTotal3xxInfoSent		Unsigned32,
	rmTotal3xxOptionsSent		Unsigned32,
	rmTotal3xxUnknownSent		Unsigned32,
	rmTotal4xxInviteSent		Unsigned32,
	rmTotal4xxByeSent		Unsigned32,
	rmTotal4xxCancelSent		Unsigned32,
	rmTotal4xxInfoSent		Unsigned32,
	rmTotal4xxOptionsSent		Unsigned32,
	rmTotal4xxUnknownSent		Unsigned32,
	rmTotal5xxInviteSent		Unsigned32,
	rmTotal5xxByeSent		Unsigned32,
	rmTotal5xxCancelSent		Unsigned32,
	rmTotal5xxInfoSent		Unsigned32,
	rmTotal5xxOptionsSent		Unsigned32,
	rmTotal5xxUnknownSent		Unsigned32,
	rmTotal6xxInviteSent		Unsigned32,
	rmTotal6xxByeSent		Unsigned32,
	rmTotal6xxCancelSent		Unsigned32,
	rmTotal6xxInfoSent		Unsigned32,
	rmTotal6xxOptionsSent		Unsigned32,
	rmTotal6xxUnknownSent		Unsigned32,
	rmTotalBadMessageReceived	Unsigned32,
	rmTotalConfCreated		Unsigned32,
	rmSipTransports			DisplayString,
	rmMode				DisplayString
}

rmActiveNode OBJECT-TYPE
	SYNTAX			DisplayString
	MAX-ACCESS    		read-only
	STATUS    		current
	DESCRIPTION
        "GVP_RM_NodeTable.ActiveNode: IP Address of the active RM Node."
::= { rmScalarEntry 2 }

rmSuccessfulCalls OBJECT-TYPE
	SYNTAX			Unsigned32
	MAX-ACCESS    		read-only
	STATUS    		current
	DESCRIPTION
        "GVP_RM_NodeTable.SuccessfulCalls: Total number of successful calls."
::= { rmScalarEntry 3 }

rmRejectedCalls OBJECT-TYPE
	SYNTAX			Unsigned32
	MAX-ACCESS    		read-only
	STATUS    		current
	DESCRIPTION
        "GVP_RM_NodeTable.RejectedCalls: Total number of rejected calls."
::= { rmScalarEntry 4 }

rmActiveSince OBJECT-TYPE
	SYNTAX			DisplayString
	MAX-ACCESS    		read-only
	STATUS    		current
	DESCRIPTION
        "GVP_RM_NodeTable.ActiveSince: Time that has elapsed since this node became active."
::= { rmScalarEntry 5 }

rmTotalInboundSessions OBJECT-TYPE
	SYNTAX			Unsigned32
	MAX-ACCESS    		read-only
	STATUS    		current
	DESCRIPTION
        "GVP_RM_NodeTable.TotalInboundSessions: Number of calls that were generated outside the platform to RM."
::= { rmScalarEntry 6 }

rmTotalOutboundSessions OBJECT-TYPE
	SYNTAX			Unsigned32
	MAX-ACCESS    		read-only
	STATUS    		current
	DESCRIPTION
        "GVP_RM_NodeTable.TotalOutboundSessions: Number of calls that were generated from the platform to outside of RM."
::= { rmScalarEntry 7 }

rmTotalRequestsForwarded OBJECT-TYPE
	SYNTAX			Unsigned32
	MAX-ACCESS    		read-only
	STATUS    		current
	DESCRIPTION
        "GVP_RM_NodeTable.TotalRequestsForwarded: Number of requests that were forwarded by RM."
::= { rmScalarEntry 8 }

rmRequestsForwardedPast5mins OBJECT-TYPE
	SYNTAX			Unsigned32
	MAX-ACCESS    		read-only
	STATUS    		current
	DESCRIPTION
        "GVP_RM_NodeTable.RequestsForwardedPast5mins: Number of requests that were forwarded by RM in the last five minutes."
::= { rmScalarEntry 9 }

rmPeakRequestsForwarded OBJECT-TYPE
	SYNTAX			Unsigned32
	MAX-ACCESS    		read-only
	STATUS    		current
	DESCRIPTION
        "GVP_RM_NodeTable.PeakRequestsForwarded: Number of peak requests that were forwarded by RM."
::= { rmScalarEntry 10 }

rmTotalRetransmissions OBJECT-TYPE
	SYNTAX			Unsigned32
	MAX-ACCESS    		read-only
	STATUS    		current
	DESCRIPTION
        "GVP_RM_NodeTable.TotalRetransmissions: Number of retransmissions by RM"
::= { rmScalarEntry 11 }

rmTotalInviteReceived OBJECT-TYPE
	SYNTAX			Unsigned32
	MAX-ACCESS    		read-only
	STATUS    		current
	DESCRIPTION
        "GVP_RM_NodeTable.TotalInviteReceived: Number of INVITE messages that were received by RM."
::= { rmScalarEntry 12 }

rmTotalAckReceived OBJECT-TYPE
	SYNTAX			Unsigned32
	MAX-ACCESS    		read-only
	STATUS    		current
	DESCRIPTION
        "GVP_RM_NodeTable.TotalAckReceived: Number of ACK that were messages received by RM"
::= { rmScalarEntry 13 }

rmTotalByeReceived OBJECT-TYPE
	SYNTAX			Unsigned32
	MAX-ACCESS    		read-only
	STATUS    		current
	DESCRIPTION
        "GVP_RM_NodeTable.TotalByeReceived: Number of BYE messages that were received by RM"
::= { rmScalarEntry 14 }

rmTotalCancelReceived OBJECT-TYPE
	SYNTAX			Unsigned32
	MAX-ACCESS    		read-only
	STATUS    		current
	DESCRIPTION
        "GVP_RM_NodeTable.TotalCancelReceived: Number of CANCEL messages that were received by RM"
::= { rmScalarEntry 15 }

rmTotalInfoReceived OBJECT-TYPE
	SYNTAX			Unsigned32
	MAX-ACCESS    		read-only
	STATUS    		current
	DESCRIPTION
        "GVP_RM_NodeTable.TotalInfoReceived: Number of INFO messages that were received by RM"
::= { rmScalarEntry 16 }

rmTotalOptionsReceived OBJECT-TYPE
	SYNTAX			Unsigned32
	MAX-ACCESS    		read-only
	STATUS    		current
	DESCRIPTION
        "GVP_RM_NodeTable.TotalOptionsReceived: Number of OPTIONS messages that were received by RM"
::= { rmScalarEntry 17 }

rmTotalUnknownReceived OBJECT-TYPE
	SYNTAX			Unsigned32
	MAX-ACCESS    		read-only
	STATUS    		current
	DESCRIPTION
        "GVP_RM_NodeTable.TotalUnknownReceived: Number of UNKNOWN messages that were received by RM"
::= { rmScalarEntry 18 }

rmTotal1xxInviteReceived OBJECT-TYPE
	SYNTAX			Unsigned32
	MAX-ACCESS    		read-only
	STATUS    		current
	DESCRIPTION
        "GVP_RM_NodeTable.Total1xxInviteReceived: Number of 1xx that were generated by RM for INVITE"
::= { rmScalarEntry 19 }

rmTotal1xxByeReceived OBJECT-TYPE
	SYNTAX			Unsigned32
	MAX-ACCESS    		read-only
	STATUS    		current
	DESCRIPTION
        "GVP_RM_NodeTable.Total1xxByeReceived: Number of 1xx that were generated by RM for BYE"
::= { rmScalarEntry 20 }

rmTotal1xxCancelReceived OBJECT-TYPE
	SYNTAX			Unsigned32
	MAX-ACCESS    		read-only
	STATUS    		current
	DESCRIPTION
        "GVP_RM_NodeTable.Total1xxCancelReceived: Number of 1xx that were generated by RM for CANCEL"
::= { rmScalarEntry 21 }

rmTotal1xxInfoReceived OBJECT-TYPE
	SYNTAX			Unsigned32
	MAX-ACCESS    		read-only
	STATUS    		current
	DESCRIPTION
        "GVP_RM_NodeTable.Total1xxInfoReceived: Number of 1xx that were generated by RM for INFO"
::= { rmScalarEntry 22 }

rmTotal1xxOptionsReceived OBJECT-TYPE
	SYNTAX			Unsigned32
	MAX-ACCESS    		read-only
	STATUS    		current
	DESCRIPTION
        "GVP_RM_NodeTable.Total1xxOptionsReceived: Number of 1xx that were generated by RM for OPTIONS"
::= { rmScalarEntry 23 }

rmTotal1xxUnknownReceived OBJECT-TYPE
	SYNTAX			Unsigned32
	MAX-ACCESS    		read-only
	STATUS    		current
	DESCRIPTION
        "GVP_RM_NodeTable.Total1xxUnknownReceived: Number of 1xx that were generated by RM for UNKNOWN"
::= { rmScalarEntry 24 }

rmTotal2xxInviteReceived OBJECT-TYPE
	SYNTAX			Unsigned32
	MAX-ACCESS    		read-only
	STATUS    		current
	DESCRIPTION
        "GVP_RM_NodeTable.Total2xxInviteReceived: Number of 2xx that were generated by RM for INVITE"
::= { rmScalarEntry 25 }

rmTotal2xxByeReceived OBJECT-TYPE
	SYNTAX			Unsigned32
	MAX-ACCESS    		read-only
	STATUS    		current
	DESCRIPTION
        "GVP_RM_NodeTable.Total2xxByeReceived: Number of 2xx that were generated by RM for BYE"
::= { rmScalarEntry 26 }

rmTotal2xxCancelReceived OBJECT-TYPE
	SYNTAX			Unsigned32
	MAX-ACCESS    		read-only
	STATUS    		current
	DESCRIPTION
        "GVP_RM_NodeTable.Total2xxCancelReceived: Number of 2xx that were generated by RM for CANCEL"
::= { rmScalarEntry 27 }

rmTotal2xxInfoReceived OBJECT-TYPE
	SYNTAX			Unsigned32
	MAX-ACCESS    		read-only
	STATUS    		current
	DESCRIPTION
        "GVP_RM_NodeTable.Total2xxInfoReceived: Number of 2xx that were generated by RM for INFO"
::= { rmScalarEntry 28 }

rmTotal2xxOptionsReceived OBJECT-TYPE
	SYNTAX			Unsigned32
	MAX-ACCESS    		read-only
	STATUS    		current
	DESCRIPTION
        "GVP_RM_NodeTable.Total2xxOptionsReceived: Number of 2xx that were generated by RM for OPTIONS"
::= { rmScalarEntry 29 }

rmTotal2xxUnknownReceived OBJECT-TYPE
	SYNTAX			Unsigned32
	MAX-ACCESS    		read-only
	STATUS    		current
	DESCRIPTION
        "GVP_RM_NodeTable.Total2xxUnknownReceived: Number of 2xx that were generated by RM for UNKNOWN"
::= { rmScalarEntry 30 }

rmTotal3xxInviteReceived OBJECT-TYPE
	SYNTAX			Unsigned32
	MAX-ACCESS    		read-only
	STATUS    		current
	DESCRIPTION
        "GVP_RM_NodeTable.Total3xxInviteReceived: Number of 3xx that were generated by RM for INVITE"
::= { rmScalarEntry 31 }

rmTotal3xxByeReceived OBJECT-TYPE
	SYNTAX			Unsigned32
	MAX-ACCESS    		read-only
	STATUS    		current
	DESCRIPTION
        "GVP_RM_NodeTable.Total3xxByeReceived: Number of 3xx that were generated by RM for BYE"
::= { rmScalarEntry 32 }

rmTotal3xxCancelReceived OBJECT-TYPE
	SYNTAX			Unsigned32
	MAX-ACCESS    		read-only
	STATUS    		current
	DESCRIPTION
        "GVP_RM_NodeTable.Total3xxCancelReceived: Number of 3xx that were generated by RM for CANCEL"
::= { rmScalarEntry 33 }

rmTotal3xxInfoReceived OBJECT-TYPE
	SYNTAX			Unsigned32
	MAX-ACCESS    		read-only
	STATUS    		current
	DESCRIPTION
        "GVP_RM_NodeTable.Total3xxInfoReceived: Number of 3xx that were generated by RM for INFO"
::= { rmScalarEntry 34 }

rmTotal3xxOptionsReceived OBJECT-TYPE
	SYNTAX			Unsigned32
	MAX-ACCESS    		read-only
	STATUS    		current
	DESCRIPTION
        "GVP_RM_NodeTable.Total3xxOptionsReceived: Number of 3xx that were generated by RM for OPTIONS"
::= { rmScalarEntry 35 }

rmTotal3xxUnknownReceived OBJECT-TYPE
	SYNTAX			Unsigned32
	MAX-ACCESS    		read-only
	STATUS    		current
	DESCRIPTION
        "GVP_RM_NodeTable.Total3xxUnknownReceived: Number of 3xx that were generated by RM for UNKNOWN"
::= { rmScalarEntry 36 }

rmTotal4xxInviteReceived OBJECT-TYPE
	SYNTAX			Unsigned32
	MAX-ACCESS    		read-only
	STATUS    		current
	DESCRIPTION
        "GVP_RM_NodeTable.Total4xxInviteReceived: Number of 4xx that were generated by RM for INVITE"
::= { rmScalarEntry 37 }

rmTotal4xxByeReceived OBJECT-TYPE
	SYNTAX			Unsigned32
	MAX-ACCESS    		read-only
	STATUS    		current
	DESCRIPTION
        "GVP_RM_NodeTable.Total4xxByeReceived: Number of 4xx that were generated by RM for BYE"
::= { rmScalarEntry 38 }

rmTotal4xxCancelReceived OBJECT-TYPE
	SYNTAX			Unsigned32
	MAX-ACCESS    		read-only
	STATUS    		current
	DESCRIPTION
        "GVP_RM_NodeTable.Total4xxCancelReceived: Number of 4xx that were generated by RM for CANCEL"
::= { rmScalarEntry 39 }

rmTotal4xxInfoReceived OBJECT-TYPE
	SYNTAX			Unsigned32
	MAX-ACCESS    		read-only
	STATUS    		current
	DESCRIPTION
        "GVP_RM_NodeTable.Total4xxInfoReceived: Number of 4xx that were generated by RM for INFO"
::= { rmScalarEntry 40 }

rmTotal4xxOptionsReceived OBJECT-TYPE
	SYNTAX			Unsigned32
	MAX-ACCESS    		read-only
	STATUS    		current
	DESCRIPTION
        "GVP_RM_NodeTable.Total4xxOptionsReceived: Number of 4xx that were generated by RM for OPTIONS"
::= { rmScalarEntry 41 }

rmTotal4xxUnknownReceived OBJECT-TYPE
	SYNTAX			Unsigned32
	MAX-ACCESS    		read-only
	STATUS    		current
	DESCRIPTION
        "GVP_RM_NodeTable.Total4xxUnknownReceived: Number of 4xx that were generated by RM for UNKNOWN"
::= { rmScalarEntry 42 }

rmTotal5xxInviteReceived OBJECT-TYPE
	SYNTAX			Unsigned32
	MAX-ACCESS    		read-only
	STATUS    		current
	DESCRIPTION
        "GVP_RM_NodeTable.Total5xxInviteReceived: Number of 5xx that were generated by RM for INVITE"
::= { rmScalarEntry 43 }

rmTotal5xxByeReceived OBJECT-TYPE
	SYNTAX			Unsigned32
	MAX-ACCESS    		read-only
	STATUS    		current
	DESCRIPTION
        "GVP_RM_NodeTable.Total5xxByeReceived: Number of 5xx that were generated by RM for BYE"
::= { rmScalarEntry 44 }

rmTotal5xxCancelReceived OBJECT-TYPE
	SYNTAX			Unsigned32
	MAX-ACCESS    		read-only
	STATUS    		current
	DESCRIPTION
        "GVP_RM_NodeTable.Total5xxCancelReceived: Number of 5xx that were generated by RM for CANCEL"
::= { rmScalarEntry 45 }

rmTotal5xxInfoReceived OBJECT-TYPE
	SYNTAX			Unsigned32
	MAX-ACCESS    		read-only
	STATUS    		current
	DESCRIPTION
        "GVP_RM_NodeTable.Total5xxInfoReceived: Number of 5xx that were enerated by RM for INFO"
::= { rmScalarEntry 46 }

rmTotal5xxOptionsReceived OBJECT-TYPE
	SYNTAX			Unsigned32
	MAX-ACCESS    		read-only
	STATUS    		current
	DESCRIPTION
        "GVP_RM_NodeTable.Total5xxOptionsReceived: Number of 5xx that were generated by RM for OPTIONS"
::= { rmScalarEntry 47 }

rmTotal5xxUnknownReceived OBJECT-TYPE
	SYNTAX			Unsigned32
	MAX-ACCESS    		read-only
	STATUS    		current
	DESCRIPTION
        "GVP_RM_NodeTable.Total5xxUnknownReceived: Number of 5xx that were generated by RM for UNKNOWN"
::= { rmScalarEntry 48 }

rmTotal6xxInviteReceived OBJECT-TYPE
	SYNTAX			Unsigned32
	MAX-ACCESS    		read-only
	STATUS    		current
	DESCRIPTION
        "GVP_RM_NodeTable.Total6xxInviteReceived: Number of 6xx that were generated by RM for INVITE"
::= { rmScalarEntry 49 }

rmTotal6xxByeReceived OBJECT-TYPE
	SYNTAX			Unsigned32
	MAX-ACCESS    		read-only
	STATUS    		current
	DESCRIPTION
        "GVP_RM_NodeTable.Total6xxByeReceived: Number of 6xx that were generated by RM for BYE"
::= { rmScalarEntry 50 }

rmTotal6xxCancelReceived OBJECT-TYPE
	SYNTAX			Unsigned32
	MAX-ACCESS    		read-only
	STATUS    		current
	DESCRIPTION
        "GVP_RM_NodeTable.Total6xxCancelReceived: Number of 6xx that were generated by RM for CANCEL"
::= { rmScalarEntry 51 }

rmTotal6xxInfoReceived OBJECT-TYPE
	SYNTAX			Unsigned32
	MAX-ACCESS    		read-only
	STATUS    		current
	DESCRIPTION
        "GVP_RM_NodeTable.Total6xxInfoReceived: Number of 6xx that were generated by RM for INFO"
::= { rmScalarEntry 52 }

rmTotal6xxOptionsReceived OBJECT-TYPE
	SYNTAX			Unsigned32
	MAX-ACCESS    		read-only
	STATUS    		current
	DESCRIPTION
        "GVP_RM_NodeTable.Total6xxOptionsReceived: Number of 6xx that were generated by RM for OPTIONS"
::= { rmScalarEntry 53 }

rmTotal6xxUnknownReceived OBJECT-TYPE
	SYNTAX			Unsigned32
	MAX-ACCESS    		read-only
	STATUS    		current
	DESCRIPTION
        "GVP_RM_NodeTable.Total6xxUnknownReceived: Number of 6xx that were generated by RM for UNKNOWN"
::= { rmScalarEntry 54 }

rmTotalInviteSent OBJECT-TYPE
	SYNTAX			Unsigned32
	MAX-ACCESS    		read-only
	STATUS    		current
	DESCRIPTION
        "GVP_RM_NodeTable.TotalInviteSent: Number of INVITE messages that were sent by RM"
::= { rmScalarEntry 55 }

rmTotalAckSent OBJECT-TYPE
	SYNTAX			Unsigned32
	MAX-ACCESS    		read-only
	STATUS    		current
	DESCRIPTION
        "GVP_RM_NodeTable.TotalAckSent: Number of ACK messages that were sent by RM"
::= { rmScalarEntry 56 }

rmTotalByeSent OBJECT-TYPE
	SYNTAX			Unsigned32
	MAX-ACCESS    		read-only
	STATUS    		current
	DESCRIPTION
        "GVP_RM_NodeTable.TotalByeSent: Number of BYE messages that were sent by RM"
::= { rmScalarEntry 57 }

rmTotalCancelSent OBJECT-TYPE
	SYNTAX			Unsigned32
	MAX-ACCESS    		read-only
	STATUS    		current
	DESCRIPTION
        "GVP_RM_NodeTable.TotalCancelSent: Number of CANCEL messages that were sent by RM"
::= { rmScalarEntry 58 }

rmTotalInfoSent OBJECT-TYPE
	SYNTAX			Unsigned32
	MAX-ACCESS    		read-only
	STATUS    		current
	DESCRIPTION
        "GVP_RM_NodeTable.TotalInfoSent: Number of INFO messages that were sent by RM"
::= { rmScalarEntry 59 }

rmTotalOptionsSent OBJECT-TYPE
	SYNTAX			Unsigned32
	MAX-ACCESS    		read-only
	STATUS    		current
	DESCRIPTION
        "GVP_RM_NodeTable.TotalOptionsSent: Number of OPTIONS messages that were sent by RM"
::= { rmScalarEntry 60 }

rmTotalUnknownSent OBJECT-TYPE
	SYNTAX			Unsigned32
	MAX-ACCESS    		read-only
	STATUS    		current
	DESCRIPTION
        "GVP_RM_NodeTable.TotalUnknownSent: Number of UNKNOWN messages that were sent by RM"
::= { rmScalarEntry 61 }

rmTotal1xxInviteSent OBJECT-TYPE
	SYNTAX			Unsigned32
	MAX-ACCESS    		read-only
	STATUS    		current
	DESCRIPTION
        "GVP_RM_NodeTable.Total1xxInviteSent: Number of 1xx that were received for INVITE sent by RM"
::= { rmScalarEntry 62 }

rmTotal1xxByeSent OBJECT-TYPE
	SYNTAX			Unsigned32
	MAX-ACCESS    		read-only
	STATUS    		current
	DESCRIPTION
        "GVP_RM_NodeTable.Total1xxByeSent: Number of 1xx that were received for BYE sent by RM"
::= { rmScalarEntry 63 }

rmTotal1xxCancelSent OBJECT-TYPE
	SYNTAX			Unsigned32
	MAX-ACCESS    		read-only
	STATUS    		current
	DESCRIPTION
        "GVP_RM_NodeTable.Total1xxCancelSent: Number of 1xx that were received for CANCEL sent by RM"
::= { rmScalarEntry 64 }

rmTotal1xxInfoSent OBJECT-TYPE
	SYNTAX			Unsigned32
	MAX-ACCESS    		read-only
	STATUS    		current
	DESCRIPTION
        "GVP_RM_NodeTable.Total1xxInfoSent: Number of 1xx that were received for INFO sent by RM"
::= { rmScalarEntry 65 }

rmTotal1xxOptionsSent OBJECT-TYPE
	SYNTAX			Unsigned32
	MAX-ACCESS    		read-only
	STATUS    		current
	DESCRIPTION
        "GVP_RM_NodeTable.Total1xxOptionsSent: Number of 1xx that were received for OPTIONS sent by RM"
::= { rmScalarEntry 66 }

rmTotal1xxUnknownSent OBJECT-TYPE
	SYNTAX			Unsigned32
	MAX-ACCESS    		read-only
	STATUS    		current
	DESCRIPTION
        "GVP_RM_NodeTable.Total1xxUnknownSent: Number of 1xx that were received for UNKNOWN sent by RM"
::= { rmScalarEntry 67 }

rmTotal2xxInviteSent OBJECT-TYPE
	SYNTAX			Unsigned32
	MAX-ACCESS    		read-only
	STATUS    		current
	DESCRIPTION
        "GVP_RM_NodeTable.Total2xxInviteSent: Number of 2xx that were received for INVITE sent by RM"
::= { rmScalarEntry 68 }

rmTotal2xxByeSent OBJECT-TYPE
	SYNTAX			Unsigned32
	MAX-ACCESS    		read-only
	STATUS    		current
	DESCRIPTION
        "GVP_RM_NodeTable.Total2xxByeSent: Number of 2xx that were received for BYE sent by RM"
::= { rmScalarEntry 69 }

rmTotal2xxCancelSent OBJECT-TYPE
	SYNTAX			Unsigned32
	MAX-ACCESS    		read-only
	STATUS    		current
	DESCRIPTION
        "GVP_RM_NodeTable.Total2xxCancelSent: Number of 2xx that were received for CANCEL sent by RM"
::= { rmScalarEntry 70 }

rmTotal2xxInfoSent OBJECT-TYPE
	SYNTAX			Unsigned32
	MAX-ACCESS    		read-only
	STATUS    		current
	DESCRIPTION
        "GVP_RM_NodeTable.Total2xxInfoSent: Number of 2xx that were received for INFO sent by RM"
::= { rmScalarEntry 71 }

rmTotal2xxOptionsSent OBJECT-TYPE
	SYNTAX			Unsigned32
	MAX-ACCESS    		read-only
	STATUS    		current
	DESCRIPTION
        "GVP_RM_NodeTable.Total2xxOptionsSent: Number of 2xx that were received for OPTIONS sent by RM"
::= { rmScalarEntry 72 }

rmTotal2xxUnknownSent OBJECT-TYPE
	SYNTAX			Unsigned32
	MAX-ACCESS    		read-only
	STATUS    		current
	DESCRIPTION
        "GVP_RM_NodeTable.Total2xxUnknownSent: Number of 2xx that were received for UNKNOWN sent by RM"
::= { rmScalarEntry 73 }

rmTotal3xxInviteSent OBJECT-TYPE
	SYNTAX			Unsigned32
	MAX-ACCESS    		read-only
	STATUS    		current
	DESCRIPTION
        "GVP_RM_NodeTable.Total3xxInviteSent: Number of 3xx that were received for INVITE sent by RM"
::= { rmScalarEntry 74 }

rmTotal3xxByeSent OBJECT-TYPE
	SYNTAX			Unsigned32
	MAX-ACCESS    		read-only
	STATUS    		current
	DESCRIPTION
        "GVP_RM_NodeTable.Total3xxByeSent: Number of 3xx that were received for BYE sent by RM"
::= { rmScalarEntry 75 }

rmTotal3xxCancelSent OBJECT-TYPE
	SYNTAX			Unsigned32
	MAX-ACCESS    		read-only
	STATUS    		current
	DESCRIPTION
        "GVP_RM_NodeTable.Total3xxCancelSent: Number of 3xx that were received for CANCEL sent by RM"
::= { rmScalarEntry 76 }

rmTotal3xxInfoSent OBJECT-TYPE
	SYNTAX			Unsigned32
	MAX-ACCESS    		read-only
	STATUS    		current
	DESCRIPTION
        "GVP_RM_NodeTable.Total3xxInfoSent: Number of 3xx that were received for INFO sent by RM"
::= { rmScalarEntry 77 }

rmTotal3xxOptionsSent OBJECT-TYPE
	SYNTAX			Unsigned32
	MAX-ACCESS    		read-only
	STATUS    		current
	DESCRIPTION
        "GVP_RM_NodeTable.Total3xxOptionsSent: Number of 3xx that were received for OPTIONS sent by RM"
::= { rmScalarEntry 78 }

rmTotal3xxUnknownSent OBJECT-TYPE
	SYNTAX			Unsigned32
	MAX-ACCESS    		read-only
	STATUS    		current
	DESCRIPTION
        "GVP_RM_NodeTable.Total3xxUnknownSent: Number of 3xx that were received for UNKNOWN sent by RM"
::= { rmScalarEntry 79 }

rmTotal4xxInviteSent OBJECT-TYPE
	SYNTAX			Unsigned32
	MAX-ACCESS    		read-only
	STATUS    		current
	DESCRIPTION
        "GVP_RM_NodeTable.Total4xxInviteSent: Number of 4xx that were received for INVITE sent by RM"
::= { rmScalarEntry 80 }

rmTotal4xxByeSent OBJECT-TYPE
	SYNTAX			Unsigned32
	MAX-ACCESS    		read-only
	STATUS    		current
	DESCRIPTION
        "GVP_RM_NodeTable.Total4xxByeSent: Number of 4xx that were received for BYE sent by RM"
::= { rmScalarEntry 81 }

rmTotal4xxCancelSent OBJECT-TYPE
	SYNTAX			Unsigned32
	MAX-ACCESS    		read-only
	STATUS    		current
	DESCRIPTION
        "GVP_RM_NodeTable.Total4xxCancelSent: Number of 4xx that were received for CANCEL sent by RM"
::= { rmScalarEntry 82 }

rmTotal4xxInfoSent OBJECT-TYPE
	SYNTAX			Unsigned32
	MAX-ACCESS    		read-only
	STATUS    		current
	DESCRIPTION
        "GVP_RM_NodeTable.Total4xxInfoSent: Number of 4xx that were received for INFO sent by RM"
::= { rmScalarEntry 83 }

rmTotal4xxOptionsSent OBJECT-TYPE
	SYNTAX			Unsigned32
	MAX-ACCESS    		read-only
	STATUS    		current
	DESCRIPTION
        "GVP_RM_NodeTable.Total4xxOptionsSent: Number of 4xx that were received for OPTIONS sent by RM"
::= { rmScalarEntry 84 }

rmTotal4xxUnknownSent OBJECT-TYPE
	SYNTAX			Unsigned32
	MAX-ACCESS    		read-only
	STATUS    		current
	DESCRIPTION
        "GVP_RM_NodeTable.Total4xxUnknownSent: Number of 4xx that were received for UNKNOWN sent by RM"
::= { rmScalarEntry 85 }

rmTotal5xxInviteSent OBJECT-TYPE
	SYNTAX			Unsigned32
	MAX-ACCESS    		read-only
	STATUS    		current
	DESCRIPTION
        "GVP_RM_NodeTable.Total5xxInviteSent: Number of 5xx that were received for INVITE sent by RM"
::= { rmScalarEntry 86 }

rmTotal5xxByeSent OBJECT-TYPE
	SYNTAX			Unsigned32
	MAX-ACCESS    		read-only
	STATUS    		current
	DESCRIPTION
        "GVP_RM_NodeTable.Total5xxByeSent: Number of 5xx that were received for BYE sent by RM"
::= { rmScalarEntry 87 }

rmTotal5xxCancelSent OBJECT-TYPE
	SYNTAX			Unsigned32
	MAX-ACCESS    		read-only
	STATUS    		current
	DESCRIPTION
        "GVP_RM_NodeTable.Total5xxCancelSent: Number of 5xx that were received for CANCEL sent by RM"
::= { rmScalarEntry 88 }

rmTotal5xxInfoSent OBJECT-TYPE
	SYNTAX			Unsigned32
	MAX-ACCESS    		read-only
	STATUS    		current
	DESCRIPTION
        "GVP_RM_NodeTable.Total5xxInfoSent: Number of 5xx that were received for INFO sent by RM"
::= { rmScalarEntry 89 }

rmTotal5xxOptionsSent OBJECT-TYPE
	SYNTAX			Unsigned32
	MAX-ACCESS    		read-only
	STATUS    		current
	DESCRIPTION
        "GVP_RM_NodeTable.Total5xxOptionsSent: Number of 5xx that were received for OPTIONS sent by RM"
::= { rmScalarEntry 90 }

rmTotal5xxUnknownSent OBJECT-TYPE
	SYNTAX			Unsigned32
	MAX-ACCESS    		read-only
	STATUS    		current
	DESCRIPTION
        "GVP_RM_NodeTable.Total5xxUnknownSent: Number of 5xx that were received for UNKNOWN sent by RM"
::= { rmScalarEntry 91 }

rmTotal6xxInviteSent OBJECT-TYPE
	SYNTAX			Unsigned32
	MAX-ACCESS    		read-only
	STATUS    		current
	DESCRIPTION
        "GVP_RM_NodeTable.Total6xxInviteSent: Number of 6xx that were received for INVITE sent by RM"
::= { rmScalarEntry 92 }

rmTotal6xxByeSent OBJECT-TYPE
	SYNTAX			Unsigned32
	MAX-ACCESS    		read-only
	STATUS    		current
	DESCRIPTION
        "GVP_RM_NodeTable.Total6xxByeSent: Number of 6xx that were received for BYE sent by RM"
::= { rmScalarEntry 93 }

rmTotal6xxCancelSent OBJECT-TYPE
	SYNTAX			Unsigned32
	MAX-ACCESS    		read-only
	STATUS    		current
	DESCRIPTION
        "GVP_RM_NodeTable.Total6xxCancelSent: Number of 6xx that were received for CANCEL sent by RM"
::= { rmScalarEntry 94 }

rmTotal6xxInfoSent OBJECT-TYPE
	SYNTAX			Unsigned32
	MAX-ACCESS    		read-only
	STATUS    		current
	DESCRIPTION
        "GVP_RM_NodeTable.Total6xxInfoSent: Number of 6xx that were received for INFO sent by RM"
::= { rmScalarEntry 95 }

rmTotal6xxOptionsSent OBJECT-TYPE
	SYNTAX			Unsigned32
	MAX-ACCESS    		read-only
	STATUS    		current
	DESCRIPTION
        "GVP_RM_NodeTable.Total6xxOptionsSent: Number of 6xx that were received for OPTIONS sent by RM"
::= { rmScalarEntry 96 }

rmTotal6xxUnknownSent OBJECT-TYPE
	SYNTAX			Unsigned32
	MAX-ACCESS    		read-only
	STATUS    		current
	DESCRIPTION
        "GVP_RM_NodeTable.Total6xxUnknownSent: Number of 6xx that were received for UNKNOWN sent by RM"
::= { rmScalarEntry 97 }

rmTotalBadMessageReceived OBJECT-TYPE
	SYNTAX			Unsigned32
	MAX-ACCESS    		read-only
	STATUS    		current
	DESCRIPTION
        "GVP_RM_NodeTable.TotalBadMessageReceived: Number of Bad Messages that were received by RM"
::= { rmScalarEntry 98 }

rmTotalConfCreated OBJECT-TYPE
	SYNTAX			Unsigned32
	MAX-ACCESS    		read-only
	STATUS    		current
	DESCRIPTION
        "GVP_RM_NodeTable.TotalConfCreated: Number of conferences that were created by RM"
::= { rmScalarEntry 99 }

rmSipTransports OBJECT-TYPE
	SYNTAX			DisplayString
	MAX-ACCESS    		read-only
	STATUS    		current
	DESCRIPTION
        "GVP_RM_NodeTable.SipTransports: Details of SIP Tansports that were configured in RM"
::= { rmScalarEntry 100 }

rmMode OBJECT-TYPE
	SYNTAX			DisplayString
	MAX-ACCESS    		read-only
	STATUS    		current
	DESCRIPTION
        "GVP_RM_NodeTable.Mode: Indicates Active/Standby node for HA configuration"
::= { rmScalarEntry 101 }


---
--- RM PHYSICAL RESOURCE TABLE
---

rmPRTable OBJECT-TYPE
	SYNTAX      	SEQUENCE OF RmPREntry
	MAX-ACCESS     	not-accessible
	STATUS      	current
	DESCRIPTION
		"GVP_RM_PhysicalResourceTable: Table to hold parameters in rmPRTable"
	::= { rm 2 }


rmPREntry OBJECT-TYPE
	SYNTAX      	RmPREntry
	MAX-ACCESS     	not-accessible
	STATUS      	current
	DESCRIPTION
		"GVP_RM_PhysicalResourceTable.rmPREntry: An entry (conceptual row) in the rmPRTable"
	INDEX { gvpConfigDBID, rmPRName }
	::= { rmPRTable 1 }

RmPREntry ::= SEQUENCE 
{	
	rmPRName			DisplayString,
	rmPRCapacity			Unsigned32,
	rmPRStatus			DisplayString,
	rmPRRegistrationStatus		DisplayString,
	rmPRActiveCalls			Unsigned32,
	rmPRActiveSince			DisplayString,
	rmPRInboundCalls		Unsigned32,
	rmPROutboundCalls		Unsigned32,
	rmPRPeakCalls			Unsigned32,
	rmPRTotalCalls			Unsigned32
}

rmPRName OBJECT-TYPE
	SYNTAX			DisplayString
	MAX-ACCESS    		read-only
	STATUS    		current
	DESCRIPTION
        "GVP_RM_PhysicalResourceTable.Name: Name of the resource."
::= { rmPREntry 2 }

rmPRCapacity OBJECT-TYPE
	SYNTAX			Unsigned32
	MAX-ACCESS    		read-only
	STATUS    		current
	DESCRIPTION
        "GVP_RM_PhysicalResourceTable.Capacity: Capacity of the resource."
::= { rmPREntry 3 }

rmPRStatus OBJECT-TYPE
	SYNTAX			DisplayString
	MAX-ACCESS    		read-only
	STATUS    		current
	DESCRIPTION
        "GVP_RM_PhysicalResourceTable.Status: Current state of the resource."
::= { rmPREntry 4 }

rmPRRegistrationStatus OBJECT-TYPE
	SYNTAX			DisplayString
	MAX-ACCESS    		read-only
	STATUS    		current
	DESCRIPTION
        "GVP_RM_PhysicalResourceTable.RegistrationStatus: SIP registration status-that is, whether a 
        REGISTER has beenreceived, and, if one has already been received, the time until the registration expires."
::= { rmPREntry 5 }

rmPRActiveCalls OBJECT-TYPE
	SYNTAX			Unsigned32
	MAX-ACCESS    		read-only
	STATUS    		current
	DESCRIPTION
        "GVP_RM_PhysicalResourceTable.ActiveCalls: Number of calls that currently are handled by the resource."
::= { rmPREntry 6 }

rmPRActiveSince OBJECT-TYPE
	SYNTAX			DisplayString
	MAX-ACCESS    		read-only
	STATUS    		current
	DESCRIPTION
        "GVP_RM_PhysicalResourceTable.ActiveSince: Time that has elapsed since this resource was first linked to RM."
::= { rmPREntry 7 }

rmPRInboundCalls OBJECT-TYPE
	SYNTAX			Unsigned32
	MAX-ACCESS    		read-only
	STATUS    		current
	DESCRIPTION
        "GVP_RM_PhysicalResourceTable.InboundCalls: Number of inbound calls that are
	generated by a resource of port usage type in-out. For all other port usage types, this will be 0."
::= { rmPREntry 8 }

rmPROutboundCalls OBJECT-TYPE
	SYNTAX			Unsigned32
	MAX-ACCESS    		read-only
	STATUS    		current
	DESCRIPTION
        "GVP_RM_PhysicalResourceTable.OutboundCalls: Number of outbound calls that are
	generated by a resource of port usage type in-out. For all other port usage types, this will be 0."
::= { rmPREntry 9 }

rmPRPeakCalls OBJECT-TYPE
	SYNTAX			Unsigned32
	MAX-ACCESS    		read-only
	STATUS    		current
	DESCRIPTION
        "GVP_RM_PhysicalResourceTable.PeakCalls: Maximum number of concurrent calls that have 
        been handled by this resource since it became active."
::= { rmPREntry 10 }

rmPRTotalCalls OBJECT-TYPE
	SYNTAX			Unsigned32
	MAX-ACCESS    		read-only
	STATUS    		current
	DESCRIPTION
        "GVP_RM_PhysicalResourceTable.TotalCalls: Total number of calls that have
	been handled by this resource since it was connected to RM."
::= { rmPREntry 11 }

---
--- RM LOGICAL RESOURCE TABLE
---

rmLRTable OBJECT-TYPE
	SYNTAX      	SEQUENCE OF RmLREntry
	MAX-ACCESS     	not-accessible
	STATUS      	current
	DESCRIPTION
		"GVP_RM_LogicalResourceTable: Table to hold parameters in rmLRTable"
	::= { rm 3 }


rmLREntry OBJECT-TYPE
	SYNTAX      	RmLREntry
	MAX-ACCESS     	not-accessible
	STATUS      	current
	DESCRIPTION
		"GVP_RM_LogicalResourceTable.rmLREntry: An entry (conceptual row) in the rmLRTable"
	INDEX { gvpConfigDBID, rmLRName }
	::= { rmLRTable 1 }

RmLREntry ::= SEQUENCE 
{	
	rmLRName			DisplayString,
	rmLRListOfPhysicalResources	DisplayString,
	rmLRParentTenant		DisplayString,
	rmLRActiveCalls			Unsigned32,
	rmLRPeakCalls			Unsigned32,
	rmLRTotalCalls			Unsigned32
}

rmLRName OBJECT-TYPE
	SYNTAX			DisplayString
	MAX-ACCESS    		read-only
	STATUS    		current
	DESCRIPTION
        "GVP_RM_LogicalResourceTable.Name: Name of the logical resource group."
::= { rmLREntry 2 }

rmLRListOfPhysicalResources OBJECT-TYPE
	SYNTAX			DisplayString
	MAX-ACCESS    		read-only
	STATUS    		current
	DESCRIPTION
        "GVP_RM_LogicalResourceTable.ListOfPhysicalResources: List of physical resource names that
	belong to the logical resource, separated by a semicolon (;)."
::= { rmLREntry 3 }

rmLRParentTenant OBJECT-TYPE
	SYNTAX			DisplayString
	MAX-ACCESS    		read-only
	STATUS    		current
	DESCRIPTION
        "GVP_RM_LogicalResourceTable.ParentTenant: Name of the tenant to which this resource belongs."
::= { rmLREntry 4 }

rmLRActiveCalls OBJECT-TYPE
	SYNTAX			Unsigned32
	MAX-ACCESS    		read-only
	STATUS    		current
	DESCRIPTION
        "GVP_RM_LogicalResourceTable.ActiveCalls: Number of calls that currently are routed to this resource group."
::= { rmLREntry 5 }

rmLRPeakCalls OBJECT-TYPE
	SYNTAX			Unsigned32
	MAX-ACCESS    		read-only
	STATUS    		current
	DESCRIPTION
        "GVP_RM_LogicalResourceTable.PeakCalls: Maximum number of concurrent calls that have been handled by this
	resource group since it became active."
::= { rmLREntry 6 }

rmLRTotalCalls OBJECT-TYPE
	SYNTAX			Unsigned32
	MAX-ACCESS    		read-only
	STATUS    		current
	DESCRIPTION
        "GVP_RM_LogicalResourceTable.TotalCalls: Total number of calls that have been handled by this resource since
	it was connected to RM."
::= { rmLREntry 7 }


---
--- RM IVR PROFILE TABLE
---

rmIVRTable OBJECT-TYPE
	SYNTAX      	SEQUENCE OF RmIVREntry
	MAX-ACCESS     	not-accessible
	STATUS      	current
	DESCRIPTION
		"GVP_RM_IVRProfileTable: Table to hold parameters in rmIVRTable"
	::= { rm 4 }


rmIVREntry OBJECT-TYPE
	SYNTAX      	RmIVREntry
	MAX-ACCESS     	not-accessible
	STATUS      	current
	DESCRIPTION
		"GVP_RM_IVRProfileTable.rmIVREntry: An entry (conceptual row) in the rmIVRTable"
	INDEX { gvpConfigDBID, rmIVRName }
	::= { rmIVRTable 1 }

RmIVREntry ::= SEQUENCE 
{	
	rmIVRName			DisplayString,
	rmIVRParentTenant		DisplayString,
	rmIVRActiveSince		DisplayString,
	rmIVRUsageLimits		Unsigned32,
	rmIVRCurrentInboundCalls	Unsigned32,
	rmIVRCurrentOutboundCalls	Unsigned32,
	rmIVRCurrentCalls		Unsigned32,
	rmIVRPeakInboundCalls		Unsigned32,
	rmIVRPeakOutboundCalls		Unsigned32,
	rmIVRPeakCalls			Unsigned32,
	rmIVRTotalInboundCalls		Unsigned32,
	rmIVRTotalOutboundCalls		Unsigned32,
	rmIVRTotalCalls			Unsigned32
}

rmIVRName OBJECT-TYPE
	SYNTAX			DisplayString
	MAX-ACCESS    		read-only
	STATUS    		current
	DESCRIPTION
        "GVP_RM_IVRProfileTable.Name: Name of the IVR Profile."
::= { rmIVREntry 2 }

rmIVRParentTenant OBJECT-TYPE
	SYNTAX			DisplayString
	MAX-ACCESS    		read-only
	STATUS    		current
	DESCRIPTION
        "GVP_RM_IVRProfileTable.ParentTenant: Name of the parent tenant for this IVRProfile."
::= { rmIVREntry 3 }

rmIVRActiveSince OBJECT-TYPE
	SYNTAX			DisplayString
	MAX-ACCESS    		read-only
	STATUS    		current
	DESCRIPTION
        "GVP_RM_IVRProfileTable.ActiveSince: Time that has elapsed since this IVR Profile became active."
::= { rmIVREntry 4 }

rmIVRUsageLimits OBJECT-TYPE
	SYNTAX			Unsigned32
	MAX-ACCESS    		read-only
	STATUS    		current
	DESCRIPTION
        "GVP_RM_IVRProfileTable.UsageLimits: Usage limits that are specified in Management Framework for this
	IVR Profile."
::= { rmIVREntry 5 }

rmIVRCurrentInboundCalls OBJECT-TYPE
	SYNTAX			Unsigned32
	MAX-ACCESS    		read-only
	STATUS    		current
	DESCRIPTION
        "GVP_RM_IVRProfileTable.CurrentInboundCalls: Number of active inbound calls that use this IVR Profile."
::= { rmIVREntry 6 }

rmIVRCurrentOutboundCalls OBJECT-TYPE
	SYNTAX			Unsigned32
	MAX-ACCESS    		read-only
	STATUS    		current
	DESCRIPTION
        "GVP_RM_IVRProfileTable.CurrentOutboundCalls: Number of active outbound calls that use this IVR Profile."
::= { rmIVREntry 7 }

rmIVRCurrentCalls OBJECT-TYPE
	SYNTAX			Unsigned32
	MAX-ACCESS    		read-only
	STATUS    		current
	DESCRIPTION
        "GVP_RM_IVRProfileTable.CurrentCalls: Number of calls that currently are using this IVR Profile."
::= { rmIVREntry 8 }

rmIVRPeakInboundCalls OBJECT-TYPE
	SYNTAX			Unsigned32
	MAX-ACCESS    		read-only
	STATUS    		current
	DESCRIPTION
        "GVP_RM_IVRProfileTable.PeakInboundCalls: Maximum number of concurrent inbound calls 
        to this IVR Profile since it became active."
::= { rmIVREntry 9 }

rmIVRPeakOutboundCalls OBJECT-TYPE
	SYNTAX			Unsigned32
	MAX-ACCESS    		read-only
	STATUS    		current
	DESCRIPTION
        "GVP_RM_IVRProfileTable.PeakOutboundCalls: Maximum number of concurrent outbound calls  
        to this IVR Profile since it became active."
::= { rmIVREntry 10 } 

rmIVRPeakCalls OBJECT-TYPE
	SYNTAX			Unsigned32
	MAX-ACCESS    		read-only
	STATUS    		current
	DESCRIPTION
        "GVP_RM_IVRProfileTable.PeakCalls: Maximum number of concurrent calls to this IVR Profile 
        since it became active."
::= { rmIVREntry 11 } 

rmIVRTotalInboundCalls OBJECT-TYPE
	SYNTAX			Unsigned32
	MAX-ACCESS    		read-only
	STATUS    		current
	DESCRIPTION
        "GVP_RM_IVRProfileTable.TotalInboundCalls: Total number of inbound calls to this IVR Profile 
        since it became active"
::= { rmIVREntry 12 } 

rmIVRTotalOutboundCalls OBJECT-TYPE
	SYNTAX			Unsigned32
	MAX-ACCESS    		read-only
	STATUS    		current
	DESCRIPTION
        "GVP_RM_IVRProfileTable.TotalOutboundCalls: Total number of outbound calls to this IVR Profile 
        since it became active."
::= { rmIVREntry 13 }

rmIVRTotalCalls OBJECT-TYPE
	SYNTAX			Unsigned32
	MAX-ACCESS    		read-only
	STATUS    		current
	DESCRIPTION
        "GVP_RM_IVRProfileTable.TotalCalls: Total number of calls to this IVRProfile since this RM node became active."
::= { rmIVREntry 14 }

---
--- RM TENANT PROFILE TABLE
---

rmTenantTable OBJECT-TYPE
	SYNTAX      	SEQUENCE OF RmTenantEntry
	MAX-ACCESS     	not-accessible
	STATUS      	current
	DESCRIPTION
		"GVP_RM_TenantTable: Table to hold parameters in rmTenantTable"
	::= { rm 5 }


rmTenantEntry OBJECT-TYPE
	SYNTAX      	RmTenantEntry
	MAX-ACCESS     	not-accessible
	STATUS      	current
	DESCRIPTION
		"GVP_RM_TenantTable.rmTenantEntry: An entry (conceptual row) in the rmTenantTable"
	INDEX { gvpConfigDBID, rmTenantName }
	::= { rmTenantTable 1 }

RmTenantEntry ::= SEQUENCE 
{	
	rmTenantName			DisplayString,
	rmTenantParentTenant		DisplayString,
	rmTenantActiveSince		DisplayString,
	rmTenantUsageLimits		Unsigned32,
	rmTenantCurrentInboundCalls	Unsigned32,
	rmTenantCurrentOutboundCalls	Unsigned32,
	rmTenantCurrentCalls		Unsigned32,
	rmTenantPeakInboundCalls	Unsigned32,
	rmTenantPeakOutboundCalls	Unsigned32,
	rmTenantPeakCalls		Unsigned32,
	rmTenantTotalInboundCalls	Unsigned32,
	rmTenantTotalOutboundCalls	Unsigned32,
	rmTenantTotalCalls		Unsigned32
}

rmTenantName OBJECT-TYPE
	SYNTAX			DisplayString
	MAX-ACCESS    		read-only
	STATUS    		current
	DESCRIPTION
        "GVP_RM_TenantTable.Name: Name of the Tenant."
::= { rmTenantEntry 2 }

rmTenantParentTenant OBJECT-TYPE
	SYNTAX			DisplayString
	MAX-ACCESS    		read-only
	STATUS    		current
	DESCRIPTION
        "GVP_RM_TenantTable.ParentTenant: Name of the parent tenant."
::= { rmTenantEntry 3 }

rmTenantActiveSince OBJECT-TYPE
	SYNTAX			DisplayString
	MAX-ACCESS    		read-only
	STATUS    		current
	DESCRIPTION
        "GVP_RM_TenantTable.ActiveSince: Time that has elapsed since this tenant became active."
::= { rmTenantEntry 4 }

rmTenantUsageLimits OBJECT-TYPE
	SYNTAX			Unsigned32
	MAX-ACCESS    		read-only
	STATUS    		current
	DESCRIPTION
        "GVP_RM_TenantTable.UsageLimits: Usage limits that are specified in Management Framework for this tenant."
::= { rmTenantEntry 5 }

rmTenantCurrentInboundCalls OBJECT-TYPE
	SYNTAX			Unsigned32
	MAX-ACCESS    		read-only
	STATUS    		current
	DESCRIPTION
        "GVP_RM_TenantTable.CurrentInboundCalls: Number of active inbound calls that use this tenant."
::= { rmTenantEntry 6 }

rmTenantCurrentOutboundCalls OBJECT-TYPE
	SYNTAX			Unsigned32
	MAX-ACCESS    		read-only
	STATUS    		current
	DESCRIPTION
        "GVP_RM_TenantTable.CurrentOutboundCalls: Number of active outbound calls that use this tenant."
::= { rmTenantEntry 7 }

rmTenantCurrentCalls OBJECT-TYPE
	SYNTAX			Unsigned32
	MAX-ACCESS    		read-only
	STATUS    		current
	DESCRIPTION
        "GVP_RM_TenantTable.CurrentCalls: Number of calls that currently use this tenant."
::= { rmTenantEntry 8 }

rmTenantPeakInboundCalls OBJECT-TYPE
	SYNTAX			Unsigned32
	MAX-ACCESS    		read-only
	STATUS    		current
	DESCRIPTION
        "GVP_RM_TenantTable.PeakInboundCalls: Mmaximum number of concurrent inbound calls 
        to this Tenant since it became active."
::= { rmTenantEntry 9 }

rmTenantPeakOutboundCalls OBJECT-TYPE
	SYNTAX			Unsigned32
	MAX-ACCESS    		read-only
	STATUS    		current
	DESCRIPTION
        "GVP_RM_TenantTable.PeakOutboundCalls: Maximum number of concurrent outbound calls  
        to this Tenant since it became active."
::= { rmTenantEntry 10 } 

rmTenantPeakCalls OBJECT-TYPE
	SYNTAX			Unsigned32
	MAX-ACCESS    		read-only
	STATUS    		current
	DESCRIPTION
        "GVP_RM_TenantTable.PeakCalls: Maximum number of concurrent calls to this Tenant 
        since it became active."
::= { rmTenantEntry 11 } 

rmTenantTotalInboundCalls OBJECT-TYPE
	SYNTAX			Unsigned32
	MAX-ACCESS    		read-only
	STATUS    		current
	DESCRIPTION
        "GVP_RM_TenantTable.TotalInboundCalls: Total number of inbound calls to this Tenant 
        since it became active"
::= { rmTenantEntry 12 } 

rmTenantTotalOutboundCalls OBJECT-TYPE
	SYNTAX			Unsigned32
	MAX-ACCESS    		read-only
	STATUS    		current
	DESCRIPTION
        "GVP_RM_TenantTable.TotalOutboundCalls: Total number of outbound calls to this Tenant 
        since it became active."
::= { rmTenantEntry 13 }

rmTenantTotalCalls OBJECT-TYPE
	SYNTAX			Unsigned32
	MAX-ACCESS    		read-only
	STATUS    		current
	DESCRIPTION
        "GVP_RM_TenantTable.TotalCalls: Total number of calls to this Tenant since this RM node became active."
::= { rmTenantEntry 14 }


-- #############################################################################

-- #############################################################################
-- MCP BRANCH
-- #############################################################################

---
--- MCP SCALAR TABLE
---

mcpScalarTable OBJECT-TYPE
	SYNTAX      	SEQUENCE OF McpScalarEntry
	MAX-ACCESS     	not-accessible
	STATUS      	current
	DESCRIPTION
		"GVP_MediaControlPlatform: Table to hold parameters in mcpScalarTable"
	::= { mcp 1 }

mcpScalarEntry OBJECT-TYPE
	SYNTAX      	McpScalarEntry
	MAX-ACCESS     	not-accessible
	STATUS      	current
	DESCRIPTION
		"GVP_MediaControlPlatform.mcpScalarEntry: An entry (conceptual row) in the mcpScalarTable"
	INDEX { gvpConfigDBID }
	::= { mcpScalarTable 1 }

McpScalarEntry ::= SEQUENCE 
{	
	mcpStartTime			DisplayString,
	mcpStatus			DisplayString,
	mcpLoadedAppModules		DisplayString
}

mcpStartTime OBJECT-TYPE
	SYNTAX			DisplayString
	MAX-ACCESS    		read-only
	STATUS    		current
	DESCRIPTION
        "GVP_MediaControlPlatform.mcpStartTime: Start time of MCP."
::= { mcpScalarEntry 2 }

mcpStatus OBJECT-TYPE
	SYNTAX			DisplayString
	MAX-ACCESS    		read-only
	STATUS    		current
	DESCRIPTION
        "GVP_MediaControlPlatform.mcpStatus: Current status of MCP. Currently, it can be RUNNING, SUSPENDING or SUSPENDED."
::= { mcpScalarEntry 3 }

mcpLoadedAppModules OBJECT-TYPE
	SYNTAX			DisplayString
	MAX-ACCESS    		read-only
	STATUS    		current
	DESCRIPTION
        "GVP_MediaControlPlatform.mcpLoadedAppModules: List of currently loaded Application modules."
::= { mcpScalarEntry 4 }

---
--- MCP SIP SCALAR TABLE
---

mcpSipScalarTable OBJECT-TYPE
	SYNTAX      	SEQUENCE OF McpSipScalarEntry
	MAX-ACCESS     	not-accessible
	STATUS      	current
	DESCRIPTION
		"GVP_MediaControlPlatform_SIP: Table to hold parameters in mcpSipScalarTable"
	::= { mcp 2 }

mcpSipScalarEntry OBJECT-TYPE
	SYNTAX      	McpSipScalarEntry
	MAX-ACCESS     	not-accessible
	STATUS      	current
	DESCRIPTION
		"GVP_MediaControlPlatform_SIP.mcpSipScalarEntry: An entry (conceptual row) in the mcpSipScalarTable"
	INDEX { gvpConfigDBID }
	::= { mcpSipScalarTable 1 }

McpSipScalarEntry ::= SEQUENCE 
{	
	mcpSipCurrentInboundSessions	Unsigned32,
	mcpSipPeakInboundSessions	Unsigned32,
	mcpSipTotalInboundSessions	Unsigned32,
	mcpSipCurrentOutboundSessions	Unsigned32,
	mcpSipPeakOutboundSessions	Unsigned32,
	mcpSipTotalOutboundSessions	Unsigned32
}

mcpSipCurrentInboundSessions OBJECT-TYPE
	SYNTAX			Unsigned32
	MAX-ACCESS    		read-only
	STATUS    		current
	DESCRIPTION
        "GVP_MediaControlPlatform_SIP.mcpSipCurrentInboundSessions: Current number of inbound sessions."
::= { mcpSipScalarEntry 2 }

mcpSipPeakInboundSessions OBJECT-TYPE
	SYNTAX			Unsigned32
	MAX-ACCESS    		read-only
	STATUS    		current
	DESCRIPTION
        "GVP_MediaControlPlatform_SIP.mcpSipPeakInboundSessions: Maximum number of simultaneous inbound sessions."
::= { mcpSipScalarEntry 3 }

mcpSipTotalInboundSessions OBJECT-TYPE
	SYNTAX			Unsigned32
	MAX-ACCESS    		read-only
	STATUS    		current
	DESCRIPTION
        "GVP_MediaControlPlatform_SIP.mcpSipTotalInboundSessions: Total number of inbound sessions since MCP started."
::= { mcpSipScalarEntry 4 }

mcpSipCurrentOutboundSessions OBJECT-TYPE
	SYNTAX			Unsigned32
	MAX-ACCESS    		read-only
	STATUS    		current
	DESCRIPTION
        "GVP_MediaControlPlatform_SIP.mcpSipCurrentOutboundSessions: Current number of outbound sessions."
::= { mcpSipScalarEntry 5 }

mcpSipPeakOutboundSessions OBJECT-TYPE
	SYNTAX			Unsigned32
	MAX-ACCESS    		read-only
	STATUS    		current
	DESCRIPTION
        "GVP_MediaControlPlatform_SIP.mcpSipPeakOutboundSessions: Maximum number of simultaneous outbound sessions."
::= { mcpSipScalarEntry 6 }

mcpSipTotalOutboundSessions OBJECT-TYPE
	SYNTAX			Unsigned32
	MAX-ACCESS    		read-only
	STATUS    		current
	DESCRIPTION
        "GVP_MediaControlPlatform_SIP.mcpSipTotalOutboundSessions: Total number of outbound sessions since MCP started."
::= { mcpSipScalarEntry 7 }

---
--- MCP SPEECH SERVER TABLE
---

mcpSpeechServerTable OBJECT-TYPE
	SYNTAX      	SEQUENCE OF McpSpeechServerEntry
	MAX-ACCESS     	not-accessible
	STATUS      	current
	DESCRIPTION
		"GVP_SpeechServers: Table to hold parameters in mcpSpeechServerTable"
	::= { mcp 3 }

mcpSpeechServerEntry OBJECT-TYPE
	SYNTAX      	McpSpeechServerEntry
	MAX-ACCESS     	not-accessible
	STATUS      	current
	DESCRIPTION
		"GVP_SpeechServers.mcpSpeechServerEntry: An entry (conceptual row) in the mcpSpeechServerTable"
	INDEX { gvpConfigDBID, mcpSpeechServerID }
	::= { mcpSpeechServerTable 1 }

McpSpeechServerEntry ::= SEQUENCE 
{	
	mcpSpeechServerID			Unsigned32,
	mcpSpeechResourceName			DisplayString,
	mcpSpeechIPAddress			DisplayString,
	mcpSpeechServerType			DisplayString,
	mcpSpeechProtocol			DisplayString,
	mcpSpeechDefaultEngine			DisplayString,
	mcpSpeechStatus				DisplayString,
	mcpSpeechResourceURL			DisplayString,
	mcpSpeechResourceDied			Unsigned32,
	mcpSpeechResourceQuarantined		Unsigned32,
	mcpSpeechResourceTotalSessions		Unsigned32,
	mcpSpeechResourceSuccessSessions	Unsigned32,
	mcpSpeechResourceFailedSessions		Unsigned32,
	mcpSpeechResourcePeakSessions		Unsigned32,
	mcpSpeechResourceCurrentSessions	Unsigned32,	
	mcpSpeechResourceSuccessRequests	Unsigned32,
	mcpSpeechResourceFailedRequests		Unsigned32,
	mcpSpeechResourceTimeoutRequests	Unsigned32
}

mcpSpeechServerID OBJECT-TYPE
	SYNTAX			Unsigned32
	MAX-ACCESS    		read-only
	STATUS    		current
	DESCRIPTION
        "GVP_SpeechServers.ID: ID of the speech server."
::= { mcpSpeechServerEntry 2 }

mcpSpeechResourceName OBJECT-TYPE
	SYNTAX			DisplayString
	MAX-ACCESS    		read-only
	STATUS    		current
	DESCRIPTION
        "GVP_SpeechServers.SpeechResourceName: Name of the speech resource that can be accessed by an application."
::= { mcpSpeechServerEntry 3 }

mcpSpeechIPAddress OBJECT-TYPE
	SYNTAX			DisplayString
	MAX-ACCESS    		read-only
	STATUS    		current
	DESCRIPTION
        "GVP_SpeechServers.IPAddress: IP address of the speech server."
::= { mcpSpeechServerEntry 4 }

mcpSpeechServerType OBJECT-TYPE
	SYNTAX			DisplayString
	MAX-ACCESS    		read-only
	STATUS    		current
	DESCRIPTION
        "GVP_SpeechServers.ServerType: Type of the speech server."
::= { mcpSpeechServerEntry 5 }

mcpSpeechProtocol OBJECT-TYPE
	SYNTAX			DisplayString
	MAX-ACCESS    		read-only
	STATUS    		current
	DESCRIPTION
        "GVP_SpeechServers.Protocol: Protocol that is used by the speech server."
::= { mcpSpeechServerEntry 6 }

mcpSpeechDefaultEngine OBJECT-TYPE
	SYNTAX			DisplayString
	MAX-ACCESS    		read-only
	STATUS    		current
	DESCRIPTION
        "GVP_SpeechServers.DefaultEngine: Whether this speech server is the default engine."
::= { mcpSpeechServerEntry 7 }

mcpSpeechStatus OBJECT-TYPE
	SYNTAX			DisplayString
	MAX-ACCESS    		read-only
	STATUS    		current
	DESCRIPTION
        "GVP_SpeechServers.Status: Current status of the speech server."
::= { mcpSpeechServerEntry 8 }

mcpSpeechResourceURL OBJECT-TYPE
	SYNTAX			DisplayString
	MAX-ACCESS    		read-only
	STATUS    		current
	DESCRIPTION
        "GVP_SpeechServers.URL: URL of the speech server."
::= { mcpSpeechServerEntry 9 }

mcpSpeechResourceDied OBJECT-TYPE
	SYNTAX			Unsigned32
	MAX-ACCESS    		read-only
	STATUS    		current
	DESCRIPTION
        "GVP_SpeechServers.Died: The number of times this server died since it has first connected to the MCP."
::= { mcpSpeechServerEntry 10 }

mcpSpeechResourceQuarantined OBJECT-TYPE
	SYNTAX			Unsigned32
	MAX-ACCESS    		read-only
	STATUS    		current
	DESCRIPTION
        "GVP_SpeechServers.Quarantined: The number of times this server was quarantined since it has first connected to the MCP."
::= { mcpSpeechServerEntry 11 }

mcpSpeechResourceTotalSessions OBJECT-TYPE
	SYNTAX			Unsigned32
	MAX-ACCESS    		read-only
	STATUS    		current
	DESCRIPTION
        "GVP_SpeechServers.TotalSessions: Total MRCP sessions that have attempted to establish with the speech server."
::= { mcpSpeechServerEntry 12 }

mcpSpeechResourceSuccessSessions OBJECT-TYPE
	SYNTAX			Unsigned32
	MAX-ACCESS    		read-only
	STATUS    		current
	DESCRIPTION
        "GVP_SpeechServers.SuccessSessions: Total MRCP sessions successfully established with the speech server."
::= { mcpSpeechServerEntry 13 }

mcpSpeechResourceFailedSessions OBJECT-TYPE
	SYNTAX			Unsigned32
	MAX-ACCESS    		read-only
	STATUS    		current
	DESCRIPTION
        "GVP_SpeechServers.FailedSessions: Total MRCP sessions failed to establish with the speech server."
::= { mcpSpeechServerEntry 14 }

mcpSpeechResourcePeakSessions OBJECT-TYPE
	SYNTAX			Unsigned32
	MAX-ACCESS    		read-only
	STATUS    		current
	DESCRIPTION
        "GVP_SpeechServers.PeakSessions: The peak concurrent MRCP sessions of the speech server."
::= { mcpSpeechServerEntry 15 }

mcpSpeechResourceCurrentSessions OBJECT-TYPE
	SYNTAX			Unsigned32
	MAX-ACCESS    		read-only
	STATUS    		current
	DESCRIPTION
        "GVP_SpeechServers.CurrentSessions: Current MRCP sessions of the speech server."
::= { mcpSpeechServerEntry 16 }

mcpSpeechResourceSuccessRequests OBJECT-TYPE
	SYNTAX			Unsigned32
	MAX-ACCESS    		read-only
	STATUS    		current
	DESCRIPTION
        "GVP_SpeechServers.SuccessRequests: Total successful MRCP requests of the speech server."
::= { mcpSpeechServerEntry 17 }

mcpSpeechResourceFailedRequests OBJECT-TYPE
	SYNTAX			Unsigned32
	MAX-ACCESS    		read-only
	STATUS    		current
	DESCRIPTION
        "GVP_SpeechServers.FailedRequests: Total failed MRCP requests of the speech server."
::= { mcpSpeechServerEntry 18 }

mcpSpeechResourceTimeoutRequests OBJECT-TYPE
	SYNTAX			Unsigned32
	MAX-ACCESS    		read-only
	STATUS    		current
	DESCRIPTION
        "GVP_SpeechServers.TimeoutRequests: Total timed out MRCP requests of the speech server."
::= { mcpSpeechServerEntry 19 }

---
--- MCP SEECH SESSION SCALAR TABLE
---

mcpSpeechSessionTable OBJECT-TYPE
	SYNTAX      	SEQUENCE OF McpSpeechSessionEntry
	MAX-ACCESS     	not-accessible
	STATUS      	current
	DESCRIPTION
		"GVP_SpeechSessions: Table to hold the overall platform speech session statistic data."
	::= { mcp 4 }

mcpSpeechSessionEntry OBJECT-TYPE
	SYNTAX      	McpSpeechSessionEntry
	MAX-ACCESS     	not-accessible
	STATUS      	current
	DESCRIPTION
		"GVP_SpeechSessions.mcpSpeechSessionEntry: An entry (conceptual row) in the mcpSpeechSessionEntry"
	INDEX { gvpConfigDBID }
	::= { mcpSpeechSessionTable 1 }

McpSpeechSessionEntry ::= SEQUENCE 
{	
	mcpTotalRecogSessions		Unsigned32,
	mcpSucceedRecogSessions		Unsigned32,
	mcpFailedRecogSessions		Unsigned32,
	mcpCurrRecogSessions		Unsigned32,
	mcpPeakRecogSessions		Unsigned32,	
	mcpTotalSynthSessions		Unsigned32,
	mcpSucceedSynthSessions		Unsigned32,
	mcpFailedSynthSessions		Unsigned32,
	mcpCurrSynthSessions		Unsigned32,
	mcpPeakSynthSessions		Unsigned32
}

mcpTotalRecogSessions OBJECT-TYPE
	SYNTAX			Unsigned32
	MAX-ACCESS    		read-only
	STATUS    		current
	DESCRIPTION
        "GVP_SpeechSessions.mcpTotalRecogSessions: Total number of speech recognition sessions since MCP has started."
::= { mcpSpeechSessionEntry 2 }

mcpSucceedRecogSessions OBJECT-TYPE
	SYNTAX			Unsigned32
	MAX-ACCESS    		read-only
	STATUS    		current
	DESCRIPTION
        "GVP_SpeechSessions.mcpSucceedRecogSessions: Total number of speech recognition sessions that have successfully established since MCP has started."
::= { mcpSpeechSessionEntry 3 }

mcpFailedRecogSessions OBJECT-TYPE
	SYNTAX			Unsigned32
	MAX-ACCESS    		read-only
	STATUS    		current
	DESCRIPTION
        "GVP_SpeechSessions.mcpFailedRecogSessions: Total number of speech recognition sessions that have failed to establish since MCP has started."
::= { mcpSpeechSessionEntry 4 }

mcpCurrRecogSessions OBJECT-TYPE
	SYNTAX			Unsigned32
	MAX-ACCESS    		read-only
	STATUS    		current
	DESCRIPTION
        "GVP_SpeechSessions.mcpCurrRecogSessions: Current number of speech recognition sessions."
::= { mcpSpeechSessionEntry 5 }

mcpPeakRecogSessions OBJECT-TYPE
	SYNTAX			Unsigned32
	MAX-ACCESS    		read-only
	STATUS    		current
	DESCRIPTION
        "GVP_SpeechSessions.mcpPeakRecogSessions: Maximum number of simultaneous speech recognition sessions."
::= { mcpSpeechSessionEntry 6 }

mcpTotalSynthSessions OBJECT-TYPE
	SYNTAX			Unsigned32
	MAX-ACCESS    		read-only
	STATUS    		current
	DESCRIPTION
        "GVP_SpeechSessions.mcpTotalSynthSessions: Total number of speech synthesis sessions since MCP has started."
::= { mcpSpeechSessionEntry 7 }

mcpSucceedSynthSessions OBJECT-TYPE
	SYNTAX			Unsigned32
	MAX-ACCESS    		read-only
	STATUS    		current
	DESCRIPTION
        "GVP_SpeechSessions.mcpSucceedSynthSessions: Total number of speech synthesis sessions that have successfully established since MCP has started."
::= { mcpSpeechSessionEntry 8 }

mcpFailedSynthSessions OBJECT-TYPE
	SYNTAX			Unsigned32
	MAX-ACCESS    		read-only
	STATUS    		current
	DESCRIPTION
        "GVP_SpeechSessions.mcpFailedSynthSessions: Total number of speech synthesis sessions that have failed to establish since MCP has started."
::= { mcpSpeechSessionEntry 9 }

mcpCurrSynthSessions OBJECT-TYPE
	SYNTAX			Unsigned32
	MAX-ACCESS    		read-only
	STATUS    		current
	DESCRIPTION
        "GVP_SpeechSessions.mcpCurrSynthSessions: Current number of speech synthesis sessions sessions."
::= { mcpSpeechSessionEntry 10 }

mcpPeakSynthSessions OBJECT-TYPE
	SYNTAX			Unsigned32
	MAX-ACCESS    		read-only
	STATUS    		current
	DESCRIPTION
        "GVP_SpeechSessions.mcpPeakSynthSessions: Maximum number of simultaneous speech synthesis sessions."
::= { mcpSpeechSessionEntry 11 }


---
--- MCP Media RTP SCALAR TABLE
---

mcpMediaRtpScalarTable OBJECT-TYPE
	SYNTAX      	SEQUENCE OF McpMediaRtpScalarEntry
	MAX-ACCESS     	not-accessible
	STATUS      	deprecated
	DESCRIPTION
		"GVP_MediaRTPTable: Table to hold parameters in mcpMediaRtpScalarTable"
	::= { mcp 5 }

mcpMediaRtpScalarEntry OBJECT-TYPE
	SYNTAX      	McpMediaRtpScalarEntry
	MAX-ACCESS     	not-accessible
	STATUS      	deprecated
	DESCRIPTION
		"GVP_MediaRTPTable.mcpMediaRtpScalarEntry: An entry (conceptual row) in the mcpMediaRtpScalarTable"
	INDEX { gvpConfigDBID }
	::= { mcpMediaRtpScalarTable 1 }

McpMediaRtpScalarEntry ::= SEQUENCE 
{	
	mcpRtcpPacketsRcvd			  Counter64,
	mcpRtcpPacketsSent			  Counter64,
	mcpRtpPacketsRcvd			  Counter64,
	mcpRtpPacketsSent			  Counter64,
	mcpRtpBytesRcvd			  Counter64,
	mcpRtpBytesSent			  Counter64,
	mcpRfc2833PacketsRcvd		  Counter64
}

mcpRtcpPacketsRcvd OBJECT-TYPE
	SYNTAX			Counter64
	MAX-ACCESS    	read-only
	STATUS    		deprecated
	DESCRIPTION
        "GVP_MediaRTPTable.mcpRtcpPacketsRcvd: The number of RTCP packets received by MCP."
::= { mcpMediaRtpScalarEntry 2 }

mcpRtcpPacketsSent OBJECT-TYPE
	SYNTAX			Counter64
	MAX-ACCESS    	read-only
	STATUS    		deprecated
	DESCRIPTION
        "GVP_MediaRTPTable.mcpRtcpPacketsSent: The number of RTCP packets sent by MCP."
::= { mcpMediaRtpScalarEntry 3 }

mcpRtpPacketsRcvd OBJECT-TYPE
	SYNTAX			Counter64
	MAX-ACCESS    	read-only
	STATUS    		deprecated
	DESCRIPTION
        "GVP_MediaRTPTable.mcpRtpPacketsRcvd: The number of RTP packets received by MCP."
::= { mcpMediaRtpScalarEntry 4 }

mcpRtpPacketsSent OBJECT-TYPE
	SYNTAX			Counter64
	MAX-ACCESS    	read-only
	STATUS    		deprecated
	DESCRIPTION
        "GVP_MediaRTPTable.mcpRtpPacketsSent: The number of RTP packets sent by MCP."
::= { mcpMediaRtpScalarEntry 5 }

mcpRtpBytesRcvd OBJECT-TYPE
	SYNTAX			Counter64
	MAX-ACCESS    	read-only
	STATUS    		deprecated
	DESCRIPTION
        "GVP_MediaRTPTable.mcpRtpBytesRcvd: The number of RTP bytes received by MCP."
::= { mcpMediaRtpScalarEntry 6 }

mcpRtpBytesSent OBJECT-TYPE
	SYNTAX			Counter64
	MAX-ACCESS    	read-only
	STATUS    		deprecated
	DESCRIPTION
        "GVP_MediaRTPTable.mcpRtpBytesSent: The number of RTP bytes sent by MCP."
::= { mcpMediaRtpScalarEntry 7 }

mcpRfc2833PacketsRcvd OBJECT-TYPE
	SYNTAX			Counter64
	MAX-ACCESS    	read-only
	STATUS    		deprecated
	DESCRIPTION
        "GVP_MediaRTPTable.mcpRfc2833PacketsRcvd: The number of RFC 2833 packets received by MCP."
::= { mcpMediaRtpScalarEntry 8 }


---
--- MCP Media End Point SCALAR TABLE
---

mcpMediaEndPointScalarTable OBJECT-TYPE
	SYNTAX      	SEQUENCE OF McpMediaEndPointScalarEntry
	MAX-ACCESS     	not-accessible
	STATUS      	deprecated
	DESCRIPTION
		"GVP_MediaEndPointTable: Table to hold parameters in mcpMediaEndPointScalarTable"
	::= { mcp 6 }

mcpMediaEndPointScalarEntry OBJECT-TYPE
	SYNTAX      	McpMediaEndPointScalarEntry
	MAX-ACCESS     	not-accessible
	STATUS      	deprecated
	DESCRIPTION
		"GVP_MediaEndPointTable.mcpMediaEndPointScalarEntry: An entry (conceptual row) in the mcpMediaEndPointScalarTable"
	INDEX { gvpConfigDBID }
	::= { mcpMediaEndPointScalarTable 1 }

McpMediaEndPointScalarEntry ::= SEQUENCE 
{	
	mcpRequest		  Unsigned32,
	mcpReInvite		  Unsigned32,
	mcpRtpFailure	  Unsigned32,
	mcpNoMedia	      Unsigned32,
	mcpNoResource	  Unsigned32
}

mcpRequest OBJECT-TYPE
	SYNTAX			Unsigned32
	MAX-ACCESS    	read-only
	STATUS    		deprecated
	DESCRIPTION
        "GVP_MediaEndPointTable.mcpRequest: RTP Endpoints ended on Request."
::= { mcpMediaEndPointScalarEntry 2 }

mcpReInvite OBJECT-TYPE
	SYNTAX			Unsigned32
	MAX-ACCESS    	read-only
	STATUS    		deprecated
	DESCRIPTION
        "GVP_MediaEndPointTable.mcpReInvite: RTP Endpoints ended because a Re-Invite arrived."
::= { mcpMediaEndPointScalarEntry 3 }

mcpRtpFailure OBJECT-TYPE
	SYNTAX			Unsigned32
	MAX-ACCESS    	read-only
	STATUS    		deprecated
	DESCRIPTION
        "GVP_MediaEndPointTable.mcpRtpFailure: RTP Endpoints ended because no more RTCP and RTP packets during configurable period."
::= { mcpMediaEndPointScalarEntry 4 }

mcpNoMedia OBJECT-TYPE
	SYNTAX			Unsigned32
	MAX-ACCESS    	read-only
	STATUS    		deprecated
	DESCRIPTION
        "GVP_MediaEndPointTable.mcpNoMedia: RTP Endpoints ended because no valid media was present in the SDP at Invite."
::= { mcpMediaEndPointScalarEntry 5 }

mcpNoResource OBJECT-TYPE
	SYNTAX			Unsigned32
	MAX-ACCESS    	read-only
	STATUS    		deprecated
	DESCRIPTION
        "GVP_MediaEndPointTable.mcpNoResource: RTP Endpoints ended because no resources were available."
::= { mcpMediaEndPointScalarEntry 6 }

-- #############################################################################
-- FM BRANCH
-- #############################################################################

---
--- FM SCALAR TABLE
---

fmScalarTable OBJECT-TYPE
	SYNTAX      	SEQUENCE OF FmScalarEntry
	MAX-ACCESS     	not-accessible
	STATUS      	obsolete
	DESCRIPTION
		"GVP_FetchingModule: Table to hold parameters in fmScalarTable"
	::= { fm 1 }

fmScalarEntry OBJECT-TYPE
	SYNTAX      	FmScalarEntry
	MAX-ACCESS     	not-accessible
	STATUS      	obsolete
	DESCRIPTION
		"GVP_FetchingModule.fmScalarEntry: An entry (conceptual row) in the fmScalarTable"
	INDEX { gvpConfigDBID }
	::= { fmScalarTable 1 }

FmScalarEntry ::= SEQUENCE 
{	
	fmStartTime			DisplayString,
	fmNumCurrentActiveSessions	Unsigned32,
	fmNumPeakActiveSessions		Unsigned32,
	fmNumCurrentOpenSessions	Unsigned32,
	fmNumPeakOpenSessions		Unsigned32,
	fmNumTotalSessions		Unsigned32,
	fmCurrentCacheSize		Unsigned32,
	fmPeakCacheSize			Unsigned32,
	fmCacheMaxSize			Unsigned32,
	fmCacheMaxAge			Unsigned32,
	fmFailedFetches			Unsigned32,
	fmNumCurrentFetches		Unsigned32,
	fmNumPeakFetches		Unsigned32,
	fmMaxFetches			Unsigned32,
	fmNumCurrentCachedEntries	Unsigned32,
	fmNumPeakCachedEntries		Unsigned32,
	fmNumTotalHttpFetches		Unsigned32,
	fmNumTotalFileFetches		Unsigned32,
	fmTotalHttpFetchDataSize	Unsigned32,
	fmTotalFileFetchDataSize	Unsigned32,
	fmNumCurrentQueuedRequests	Unsigned32,
	fmNumPeakQueuedRequests		Unsigned32,
	fmNumCurrentOpenRequests	Unsigned32,
	fmNumPeakOpenRequests		Unsigned32,
	fmNumTotalHttpRequests		Unsigned32,
	fmNumTotalFileRequests		Unsigned32,
	fmTotalHttpRequestDataSize	Unsigned32,
	fmTotalFileRequestDataSize	Unsigned32
}

fmStartTime OBJECT-TYPE
	SYNTAX			DisplayString
	MAX-ACCESS    		read-only
	STATUS    		obsolete
	DESCRIPTION
        "GVP_FetchingModule.FMStartTime: Start time for Fetching Module (FM)."
::= { fmScalarEntry 2 }

fmNumCurrentActiveSessions OBJECT-TYPE
	SYNTAX			Unsigned32
	MAX-ACCESS    		read-only
	STATUS    		obsolete
	DESCRIPTION
        "GVP_FetchingModule.FMNumCurrentActiveSessions: Number of currently active sessions that have active clients."
::= { fmScalarEntry 3 }

fmNumPeakActiveSessions OBJECT-TYPE
	SYNTAX			Unsigned32
	MAX-ACCESS    		read-only
	STATUS    		obsolete
	DESCRIPTION
        "GVP_FetchingModule.FMNumPeakActiveSessions: Peak number of concurrent active sections."
::= { fmScalarEntry 4 }

fmNumCurrentOpenSessions OBJECT-TYPE
	SYNTAX			Unsigned32
	MAX-ACCESS    		read-only
	STATUS    		obsolete
	DESCRIPTION
        "GVP_FetchingModule.FMNumCurrentOpenSessions: Number of currently open sessions, whether they are active and inactive."
::= { fmScalarEntry 5 }

fmNumPeakOpenSessions OBJECT-TYPE
	SYNTAX			Unsigned32
	MAX-ACCESS    		read-only
	STATUS    		obsolete
	DESCRIPTION
        "GVP_FetchingModule.FMNumPeakOpenSessions: Peak number of concurrent open sessions."
::= { fmScalarEntry 6 }

fmNumTotalSessions OBJECT-TYPE
	SYNTAX			Unsigned32
	MAX-ACCESS    		read-only
	STATUS    		obsolete
	DESCRIPTION
        "GVP_FetchingModule.FMNumTotalSessions: Total number of sessions."
::= { fmScalarEntry 7 }

fmCurrentCacheSize OBJECT-TYPE
	SYNTAX			Unsigned32
	MAX-ACCESS    		read-only
	STATUS    		obsolete
	DESCRIPTION
        "GVP_FetchingModule.FMNumCurrentCacheSize: Size of the shared memory cache that is being used in MB."
::= { fmScalarEntry 8 }

fmPeakCacheSize OBJECT-TYPE
	SYNTAX			Unsigned32
	MAX-ACCESS    		read-only
	STATUS    		obsolete
	DESCRIPTION
        "GVP_FetchingModule.FMPeakCacheSize: Peak size of the shared memory cache that is concurrently is being used in MB."
::= { fmScalarEntry 9 }

fmCacheMaxSize OBJECT-TYPE
	SYNTAX			Unsigned32
	MAX-ACCESS    		read-only
	STATUS    		obsolete
	DESCRIPTION
        "GVP_FetchingModule.FMCacheMaxSize: Limit of the shared memory cache in MB."
::= { fmScalarEntry 10 }

fmCacheMaxAge OBJECT-TYPE
	SYNTAX			Unsigned32
	MAX-ACCESS    		read-only
	STATUS    		obsolete
	DESCRIPTION
        "GVP_FetchingModule.FMCacheMaxAge: Maximum age for data cached in the Fetching Module, in seconds."
::= { fmScalarEntry 11 }

fmFailedFetches OBJECT-TYPE
	SYNTAX			Unsigned32
	MAX-ACCESS    		read-only
	STATUS    		obsolete
	DESCRIPTION
        "GVP_FetchingModule.FMFailedFetches: Total number of failed fetches."
::= { fmScalarEntry 12 }

fmNumCurrentFetches OBJECT-TYPE
	SYNTAX			Unsigned32
	MAX-ACCESS    		read-only
	STATUS    		obsolete
	DESCRIPTION
        "GVP_FetchingModule.FMNumCurrentFetches: Number of currently active fetches that are initiated by the Fetching Module to the HTTP proxy/server."
::= { fmScalarEntry 13 }

fmNumPeakFetches OBJECT-TYPE
	SYNTAX			Unsigned32
	MAX-ACCESS    		read-only
	STATUS    		obsolete
	DESCRIPTION
        "GVP_FetchingModule.FMNumPeakFetches: Peak number of concurrent active fetches that are initiated by the Fetching Module to the HTTP proxy/server."
::= { fmScalarEntry 14 }

fmMaxFetches OBJECT-TYPE
	SYNTAX			Unsigned32
	MAX-ACCESS    		read-only
	STATUS    		obsolete
	DESCRIPTION
        "GVP_FetchingModule.FMMaxFetches: Maximum number of concurrent active fetches that are allowed to be initiated by the Fetching Module to the HTTP proxy/server."
::= { fmScalarEntry 15 }

fmNumCurrentCachedEntries OBJECT-TYPE
	SYNTAX			Unsigned32
	MAX-ACCESS    		read-only
	STATUS    		obsolete
	DESCRIPTION
        "GVP_FetchingModule.FMNumCurrentCachedEntries: Number of entries that currently are in the fetching module cache."
::= { fmScalarEntry 16 }

fmNumPeakCachedEntries OBJECT-TYPE
	SYNTAX			Unsigned32
	MAX-ACCESS    		read-only
	STATUS    		obsolete
	DESCRIPTION
        "GVP_FetchingModule.FMNumPeakCachedEntries: Peak number of cached entries."
::= { fmScalarEntry 17 }

fmNumTotalHttpFetches OBJECT-TYPE
	SYNTAX			Unsigned32
	MAX-ACCESS    		read-only
	STATUS    		obsolete
	DESCRIPTION
        "GVP_FetchingModule.FMNumTotalHttpFetches: Total number of fetches that are initiated by the Fetching Module to the HTTP proxy/server."
::= { fmScalarEntry 18 }

fmNumTotalFileFetches OBJECT-TYPE
	SYNTAX			Unsigned32
	MAX-ACCESS    		read-only
	STATUS    		obsolete
	DESCRIPTION
        "GVP_FetchingModule.FMNumTotalFileFetches: Total number of fetches to retrieve files from local computer or remote computers."
::= { fmScalarEntry 19 }

fmTotalHttpFetchDataSize OBJECT-TYPE
	SYNTAX			Unsigned32
	MAX-ACCESS    		read-only
	STATUS    		obsolete
	DESCRIPTION
        "GVP_FetchingModule.FMTotalHttpFetchDataSize: Total data size that is obtained 
        from fetches initiated by the Fetching Module to the HTTP proxy/server."
::= { fmScalarEntry 20 }

fmTotalFileFetchDataSize OBJECT-TYPE
	SYNTAX			Unsigned32
	MAX-ACCESS    		read-only
	STATUS    		obsolete
	DESCRIPTION
        "GVP_FetchingModule.FMTotalFileFetchDataSize: Total data size that is obtained from fetches 
        to retrieve files from local computer or remote computers."
::= { fmScalarEntry 21 }

fmNumCurrentQueuedRequests OBJECT-TYPE
	SYNTAX			Unsigned32
	MAX-ACCESS    		read-only
	STATUS    		obsolete
	DESCRIPTION
        "GVP_FetchingModule.FMNumCurrentQueuedRequests: Number of currently pending requests that are received from clients."
::= { fmScalarEntry 22 }

fmNumPeakQueuedRequests OBJECT-TYPE
	SYNTAX			Unsigned32
	MAX-ACCESS    		read-only
	STATUS    		obsolete
	DESCRIPTION
        "GVP_FetchingModule.FMNumPeakQueuedRequests: Peak size of the pending request queue."
::= { fmScalarEntry 23 }

fmNumCurrentOpenRequests OBJECT-TYPE
	SYNTAX			Unsigned32
	MAX-ACCESS    		read-only
	STATUS    		obsolete
	DESCRIPTION
        "GVP_FetchingModule.FMNumCurrentOpenRequests: Total number of HTTP requests received that are from clients. 
		Note: Not every request that is received from a client will initiate a fetch to the HTTP server/proxy. 
        If a fresh response is cached, the cached response will be sent back to the client.."
::= { fmScalarEntry 24 }

fmNumPeakOpenRequests OBJECT-TYPE
	SYNTAX			Unsigned32
	MAX-ACCESS    		read-only
	STATUS    		obsolete
	DESCRIPTION
        "GVP_FetchingModule.FMNumPeakOpenRequests: Peak number of concurrently opened requests that are received from clients, 
        including active requests and pending requests."
::= { fmScalarEntry 25 }

fmNumTotalHttpRequests OBJECT-TYPE
	SYNTAX			Unsigned32
	MAX-ACCESS    		read-only
	STATUS    		obsolete
	DESCRIPTION
        "GVP_FetchingModule.FMNumTotalHttpRequests: Total number of HTTP requests that are received from clients. 
        Note: Not every request that is received from a client will initiate a fetch to the HTTP server/proxy. 
        If a fresh response is cached, the cached response will be sent back to the client.."
::= { fmScalarEntry 26 }

fmNumTotalFileRequests OBJECT-TYPE
	SYNTAX			Unsigned32
	MAX-ACCESS    		read-only
	STATUS    		obsolete
	DESCRIPTION
        "GVP_FetchingModule.FMNumTotalFileRequests: Total number of requests that are received from clients to retrieve a file from the local computer or remote computers. 
        Note: If a client requests a file that is in the cache, the Fetching Module will return the cached file to the client."
::= { fmScalarEntry 27 }

fmTotalHttpRequestDataSize OBJECT-TYPE
	SYNTAX			Unsigned32
	MAX-ACCESS    		read-only
	STATUS    		obsolete
	DESCRIPTION
        "GVP_FetchingModule.FMTotalHttpRequestDataSize: Total data size that is sent to clients upon HTTP requests."
::= { fmScalarEntry 28 }

fmTotalFileRequestDataSize OBJECT-TYPE
	SYNTAX			Unsigned32
	MAX-ACCESS    		read-only
	STATUS    		obsolete
	DESCRIPTION
        "GVP_FetchingModule.FMTotalFileRequestDataSize: Total file size that is sent to clients."
::= { fmScalarEntry 29 }


-- #############################################################################
-- LibFM BRANCH
-- #############################################################################

---
--- LibFM SCALAR TABLE
---

libFMScalarTable OBJECT-TYPE
	SYNTAX      	SEQUENCE OF LibFMScalarEntry
	MAX-ACCESS     	not-accessible
	STATUS      	current
	DESCRIPTION
		"GVP_LibFetchingModule: Table to hold parameters in libFMScalarTable"
	::= { fm 2 }

libFMScalarEntry OBJECT-TYPE
	SYNTAX      	LibFMScalarEntry
	MAX-ACCESS     	not-accessible
	STATUS      	current
	DESCRIPTION
		"GVP_LibFetchingModule.libFMScalarEntry: An entry (conceptual row) in the libFMScalarTable"
	INDEX { gvpConfigDBID }
	::= { libFMScalarTable 1 }

LibFMScalarEntry ::= SEQUENCE 
{	
	libfmNumCurrentOpenSessions		Unsigned32,
	libfmNumPeakOpenSessions		Unsigned32,
	libfmNumTotalSessions			Unsigned32,
	libfmCurrentCacheSize			Unsigned32,
	libfmPeakCacheSize				Unsigned32,
	libfmCacheMaxSize				Unsigned32,
	libfmNumCurrentFetches			Unsigned32,
	libfmNumPeakFetches				Unsigned32,
	libfmNumCurrentCachedEntries	Unsigned32,
	libfmNumPeakCachedEntries		Unsigned32,
	libfmNumTotalHttpFetches		Unsigned32,
	libfmNumTotalFileFetches		Unsigned32,
	libfmNumCurrentOpenRequests		Unsigned32,
	libfmNumPeakOpenRequests		Unsigned32,
	libfmNumTotalHttpRequests		Unsigned32,
	libfmNumTotalFileRequests		Unsigned32,
	libfmFileCacheMaxAge			Unsigned32,
	libfmNumFileCacheHit			Unsigned32,
	libfmNumHttpCacheHit			Unsigned32,
	libfmNumHttpProxyCacheHit		Unsigned32,
	libfmNumHttpProxyRevalidate		Unsigned32,
	libfmNumFetchFromServer			Unsigned32,
	libfmNumHttpServerRevalidate	Unsigned32,
	libfmNumFailedHttpFetches		Unsigned32,
	libfmNumFailedFileFetches		Unsigned32,
	libfmAvgTimeHttpResponse		Unsigned32,
	libfmAvgTimeHttpProxyCacheHit	Unsigned32,
	libfmAvgTimeHttpProxyRevalidate		Unsigned32,
	libfmAvgTimeHttpServer			Unsigned32,
	libfmAvgTimeHttpServerRevalidate	Unsigned32,
	libfmAvgTimeHttpFailed			Unsigned32,
	libfmHttpFetchDataSizeTotal		DisplayString,
	libfmFileFetchDataSizeTotal		DisplayString,
	libfmHttpRequestDataSizeTotal	DisplayString,
	libfmFileRequestDataSizeTotal	DisplayString,
	libfmTop10CachedEntries			DisplayString
}

libfmNumCurrentOpenSessions OBJECT-TYPE
	SYNTAX			Unsigned32
	MAX-ACCESS    		read-only
	STATUS    		current
	DESCRIPTION
        "GVP_LibFetchingModule.LibFMNumCurrentOpenSessions: Number of currently open sessions, whether they are active or inactive."
::= { libFMScalarEntry 2 }

libfmNumPeakOpenSessions OBJECT-TYPE
	SYNTAX			Unsigned32
	MAX-ACCESS    		read-only
	STATUS    		current
	DESCRIPTION
        "GVP_LibFetchingModule.LibFMNumPeakOpenSessions: Peak number of concurrent open sessions."
::= { libFMScalarEntry 3 }

libfmNumTotalSessions OBJECT-TYPE
	SYNTAX			Unsigned32
	MAX-ACCESS    		read-only
	STATUS    		current
	DESCRIPTION
        "GVP_LibFetchingModule.LibFMNumTotalSessions: Total number of sessions."
::= { libFMScalarEntry 4 }

libfmCurrentCacheSize OBJECT-TYPE
	SYNTAX			Unsigned32
	MAX-ACCESS    		read-only
	STATUS    		current
	DESCRIPTION
        "GVP_LibFetchingModule.LibFMNumCurrentCacheSize: Current size of the cache in bytes."
::= { libFMScalarEntry 5 }

libfmPeakCacheSize OBJECT-TYPE
	SYNTAX			Unsigned32
	MAX-ACCESS    		read-only
	STATUS    		current
	DESCRIPTION
        "GVP_LibFetchingModule.LibFMPeakCacheSize: Peak size of the cache in bytes."
::= { libFMScalarEntry 6 }

libfmCacheMaxSize OBJECT-TYPE
	SYNTAX			Unsigned32
	MAX-ACCESS    		read-only
	STATUS    		current
	DESCRIPTION
        "GVP_LibFetchingModule.LibFMCacheMaxSize: Size limit of the cache in bytes."
::= { libFMScalarEntry 7 }

libfmNumCurrentFetches OBJECT-TYPE
	SYNTAX			Unsigned32
	MAX-ACCESS    		read-only
	STATUS    		current
	DESCRIPTION
        "GVP_LibFetchingModule.LibFMNumCurrentFetches: Number of currently active HTTP fetches."
::= { libFMScalarEntry 8 }

libfmNumPeakFetches OBJECT-TYPE
	SYNTAX			Unsigned32
	MAX-ACCESS    		read-only
	STATUS    		current
	DESCRIPTION
        "GVP_LibFetchingModule.LibFMNumPeakFetches: Peak number of concurrent active HTTP fetches."
::= { libFMScalarEntry 9 }

libfmNumCurrentCachedEntries OBJECT-TYPE
	SYNTAX			Unsigned32
	MAX-ACCESS    		read-only
	STATUS    		current
	DESCRIPTION
        "GVP_LibFetchingModule.LibFMNumCurrentCachedEntries: Number of entries in the cache."
::= { libFMScalarEntry 10 }

libfmNumPeakCachedEntries OBJECT-TYPE
	SYNTAX			Unsigned32
	MAX-ACCESS    		read-only
	STATUS    		current
	DESCRIPTION
        "GVP_LibFetchingModule.LibFMNumPeakCachedEntries: Peak number of cached entries."
::= { libFMScalarEntry 11 }

libfmNumTotalHttpFetches OBJECT-TYPE
	SYNTAX			Unsigned32
	MAX-ACCESS    		read-only
	STATUS    		current
	DESCRIPTION
        "GVP_LibFetchingModule.LibFMNumTotalHttpFetches: Total number of HTTP fetches."
::= { libFMScalarEntry 12 }

libfmNumTotalFileFetches OBJECT-TYPE
	SYNTAX			Unsigned32
	MAX-ACCESS    		read-only
	STATUS    		current
	DESCRIPTION
        "GVP_LibFetchingModule.LibFMNumTotalFileFetches: Total number of local file fetches."
::= { libFMScalarEntry 13 }

libfmNumCurrentOpenRequests OBJECT-TYPE
	SYNTAX			Unsigned32
	MAX-ACCESS    		read-only
	STATUS    		current
	DESCRIPTION
        "GVP_LibFetchingModule.LibFMNumCurrentOpenRequests: Number of fetch requests currently in progress."
::= { libFMScalarEntry 14 }

libfmNumPeakOpenRequests OBJECT-TYPE
	SYNTAX			Unsigned32
	MAX-ACCESS    		read-only
	STATUS    		current
	DESCRIPTION
        "GVP_LibFetchingModule.LibFMNumPeakOpenRequests: Peak number of concurrent fetch requests in progress."
::= { libFMScalarEntry 15 }

libfmNumTotalHttpRequests OBJECT-TYPE
	SYNTAX			Unsigned32
	MAX-ACCESS    		read-only
	STATUS    		current
	DESCRIPTION
        "GVP_LibFetchingModule.LibFMNumTotalHttpRequests: Total number of HTTP requests processed. 
        This number includes the requests that were satisfied by the cache."
::= { libFMScalarEntry 16 }

libfmNumTotalFileRequests OBJECT-TYPE
	SYNTAX			Unsigned32
	MAX-ACCESS    		read-only
	STATUS    		current
	DESCRIPTION
        "GVP_LibFetchingModule.LibFMNumTotalFileRequests: Total number of local file fetch requests processed. 
        This number includes the requests that were satisfied by the cache."
::= { libFMScalarEntry 17 }

libfmFileCacheMaxAge OBJECT-TYPE
	SYNTAX			Unsigned32
	MAX-ACCESS    		read-only
	STATUS    		current
	DESCRIPTION
        "GVP_LibFetchingModule.LibFMFileCacheMaxAge: Maxage for cached local files in seconds."
::= { libFMScalarEntry 18 }

libfmNumFileCacheHit OBJECT-TYPE
	SYNTAX			Unsigned32
	MAX-ACCESS    		read-only
	STATUS    		current
	DESCRIPTION
        "GVP_LibFetchingModule.LibFMNumFileCacheHit: Number of successful local file fetch requets that were satisfied by the Fetching Module cache without revalidation."
::= { libFMScalarEntry 19 }

libfmNumHttpCacheHit OBJECT-TYPE
	SYNTAX			Unsigned32
	MAX-ACCESS    		read-only
	STATUS    		current
	DESCRIPTION
        "GVP_LibFetchingModule.LibFMNumHttpCacheHit: Number of successful HTTP fetch requests that were satisfied by the Fetching Module cache without revalidation."
::= { libFMScalarEntry 20 }

libfmNumHttpProxyCacheHit OBJECT-TYPE
	SYNTAX			Unsigned32
	MAX-ACCESS    		read-only
	STATUS    		current
	DESCRIPTION
        "GVP_LibFetchingModule.LibFMNumHttpProxyCacheHit: Number of successful HTTP fetch requests that were satisfied by the HTTP proxy&apos;s cache."
::= { libFMScalarEntry 21 }

libfmNumHttpProxyRevalidate OBJECT-TYPE
	SYNTAX			Unsigned32
	MAX-ACCESS    		read-only
	STATUS    		current
	DESCRIPTION
        "GVP_LibFetchingModule.LibFMNumHttpProxyRevalidate: Number of HTTP fetch requests that were satisfied by the Fetching Module cache after revalidated by the HTTP proxy."
::= { libFMScalarEntry 22 }

libfmNumFetchFromServer OBJECT-TYPE
	SYNTAX			Unsigned32
	MAX-ACCESS    		read-only
	STATUS    		current
	DESCRIPTION
        "GVP_LibFetchingModule.LibFMNumFetchFromServer: Number of successful HTTP fetch requests that were satisfied by the origin HTTP server."
::= { libFMScalarEntry 23 }

libfmNumHttpServerRevalidate OBJECT-TYPE
	SYNTAX			Unsigned32
	MAX-ACCESS    		read-only
	STATUS    		current
	DESCRIPTION
        "GVP_LibFetchingModule.LibFMNumHttpServerRevalidate: Number of HTTP fetch requests that were satisfied by the Fetching Module cache after revalidated by the origin HTTP server."
::= { libFMScalarEntry 24 }

libfmNumFailedHttpFetches OBJECT-TYPE
	SYNTAX			Unsigned32
	MAX-ACCESS    		read-only
	STATUS    		current
	DESCRIPTION
        "GVP_LibFetchingModule.LibFMNumFailedHttpFetches: Total number of failed HTTP fetch requests."
::= { libFMScalarEntry 25 }

libfmNumFailedFileFetches OBJECT-TYPE
	SYNTAX			Unsigned32
	MAX-ACCESS    		read-only
	STATUS    		current
	DESCRIPTION
        "GVP_LibFetchingModule.LibFMNumFailedFileFetches: Total number of failed local file fetch requests."
::= { libFMScalarEntry 26 }

libfmAvgTimeHttpResponse OBJECT-TYPE
	SYNTAX			Unsigned32
	MAX-ACCESS    		read-only
	STATUS    		current
	DESCRIPTION
        "GVP_LibFetchingModule.LibFMAvgTimeHttpResponse: Average HTTP request response time in ms."
::= { libFMScalarEntry 27 }

libfmAvgTimeHttpProxyCacheHit OBJECT-TYPE
	SYNTAX			Unsigned32
	MAX-ACCESS    		read-only
	STATUS    		current
	DESCRIPTION
        "GVP_LibFetchingModule.LibFMAvgTimeHttpProxyCacheHit: Average response time in ms of HTTP requests that were satisfied by the HTTP proxy cache."
::= { libFMScalarEntry 28 }

libfmAvgTimeHttpProxyRevalidate OBJECT-TYPE
	SYNTAX			Unsigned32
	MAX-ACCESS    		read-only
	STATUS    		current
	DESCRIPTION
        "GVP_LibFetchingModule.LibFMAvgTimeHttpProxyRevalidate: Average response time in ms of the HTTP requests that were revalidated by the HTTP proxy."
::= { libFMScalarEntry 29 }

libfmAvgTimeHttpServer OBJECT-TYPE
	SYNTAX			Unsigned32
	MAX-ACCESS    		read-only
	STATUS    		current
	DESCRIPTION
        "GVP_LibFetchingModule.LibFMAvgTimeHttpServer: Average response time in ms of the successful HTTP fetch requests satisfied by the origin HTTP server."
::= { libFMScalarEntry 30 }

libfmAvgTimeHttpServerRevalidate OBJECT-TYPE
	SYNTAX			Unsigned32
	MAX-ACCESS    		read-only
	STATUS    		current
	DESCRIPTION
        "GVP_LibFetchingModule.LibFMAvgTimeHttpServerRevalidate: Average response time in ms of the HTTP requests that were revalidated by the origin HTTP server."
::= { libFMScalarEntry 31 }

libfmAvgTimeHttpFailed OBJECT-TYPE
	SYNTAX			Unsigned32
	MAX-ACCESS    		read-only
	STATUS    		current
	DESCRIPTION
        "GVP_LibFetchingModule.LibFMAvgTimeHttpFailed: Average response time in ms of the failed HTTP fetch requests."
::= { libFMScalarEntry 32 }

libfmHttpFetchDataSizeTotal OBJECT-TYPE
	SYNTAX			DisplayString
	MAX-ACCESS    		read-only
	STATUS    		current
	DESCRIPTION
        "GVP_LibFetchingModule.LibFMHttpFetchDataSizeTotal: Total data size in bytes received in all HTTP responses."
::= { libFMScalarEntry 33 }

libfmFileFetchDataSizeTotal OBJECT-TYPE
	SYNTAX			DisplayString
	MAX-ACCESS    		read-only
	STATUS    		current
	DESCRIPTION
        "GVP_LibFetchingModule.LibFMFileFetchDataSizeTotal: Total size of data read from local files in bytes."
::= { libFMScalarEntry 34 }

libfmHttpRequestDataSizeTotal OBJECT-TYPE
	SYNTAX			DisplayString
	MAX-ACCESS    		read-only
	STATUS    		current
	DESCRIPTION
        "GVP_LibFetchingModule.LibFMHttpRequestDataSizeTotal: Total data size in bytes returned by the Fetching Module for HTTP fetch requests."
::= { libFMScalarEntry 35 }

libfmFileRequestDataSizeTotal OBJECT-TYPE
	SYNTAX			DisplayString
	MAX-ACCESS    		read-only
	STATUS    		current
	DESCRIPTION
        "GVP_LibFetchingModule.LibFMFileRequestDataSizeTotal: Total data size in bytes returned by the Fetching Module for local file fetch requests."
::= { libFMScalarEntry 36 }

libfmTop10CachedEntries OBJECT-TYPE
	SYNTAX			DisplayString
	MAX-ACCESS    		read-only
	STATUS    		current
	DESCRIPTION
        "GVP_LibFetchingModule.LibFMTop10CachedEntries: The top 10 entries in the cache and the number of times they were returned."
::= { libFMScalarEntry 37 }

-- #############################################################################
-- RS BRANCH
-- #############################################################################

---
--- RS SCALAR TABLE
---

rsScalarTable OBJECT-TYPE
        SYNTAX          SEQUENCE OF RsScalarEntry
        MAX-ACCESS      not-accessible
        STATUS          current
        DESCRIPTION
                "GVP_ReportingServer: Table to hold parameters in rsScalarTable"
        ::= { rs 1 }

rsScalarEntry OBJECT-TYPE
        SYNTAX          RsScalarEntry
        MAX-ACCESS      not-accessible
        STATUS          current
        DESCRIPTION
                "GVP_ReportingServer.rsScalarEntry: An entry (conceptual row) in the rsScalarTable"
        INDEX { gvpConfigDBID }
        ::= { rsScalarTable 1 }

RsScalarEntry ::= SEQUENCE 
{       
        rsStartTime                     Counter64,
        rsUptime                        TimeTicks,
        rsSQLDialect                    DisplayString,
        rsMemoryMax                     Unsigned32,
        rsStatus                        DisplayString
}

rsStartTime OBJECT-TYPE
        SYNTAX                  Counter64
        MAX-ACCESS              read-only
        STATUS                  current
        DESCRIPTION
        "GVP_ReportingServer.rsStartTime: Start time of RS."
::= { rsScalarEntry 2 }

rsUptime OBJECT-TYPE
        SYNTAX                  TimeTicks
        MAX-ACCESS              read-only
        STATUS                  current
        DESCRIPTION
        "GVP_ReportingServer.rsUptime: The time (in hundredths of a second) since the RS was started."
::= { rsScalarEntry 3 }

rsSQLDialect OBJECT-TYPE
        SYNTAX                  DisplayString
        MAX-ACCESS              read-only
        STATUS                  current
        DESCRIPTION
        "GVP_ReportingServer.rsSQLDialect: SQL dialect of the underlying database."
::= { rsScalarEntry 4 }

rsMemoryMax OBJECT-TYPE
        SYNTAX                  Unsigned32
        MAX-ACCESS              read-only
        STATUS                  current
        DESCRIPTION
        "GVP_ReportingServer.rsMemoryMax: Maximum heap memory allocated (in KBytes)."
::= { rsScalarEntry 5 }

rsStatus OBJECT-TYPE
        SYNTAX                  DisplayString
        MAX-ACCESS              read-only
        STATUS                  current
        DESCRIPTION
        "GVP_ReportingServer.rsStatus: RS status as defined in Genesys Management Framework."
::= { rsScalarEntry 6 }


---
--- RS Storage Table
---

rsStorageStatsTable OBJECT-TYPE
        SYNTAX          SEQUENCE OF RsStorageStatsEntry
        MAX-ACCESS      not-accessible
        STATUS          current
        DESCRIPTION
                "GVP_ReportingServer: Statistics on the performance of RS JMS consumers."
        ::= { rs 3 }


rsStorageStatsEntry OBJECT-TYPE
        SYNTAX          RsStorageStatsEntry
        MAX-ACCESS      not-accessible
        STATUS          current
        DESCRIPTION
                "GVP_ReportingServer.rsStorageStatsEntry: An entry (conceptual row) in the rsStorageStatsTable"
        INDEX { gvpConfigDBID, rsStorageStatsIndex }
        ::= { rsStorageStatsTable 1 }

RsStorageStatsEntry ::= SEQUENCE 
{       
        rsStorageStatsIndex     Unsigned32,
        rsStorageName           DisplayString,
        rsStorageStatus         DisplayString,
        rsDbAccessAverage       Unsigned32,
        rsDbAccessCount         Counter64,
        rsDbAccessLast          Unsigned32,
        rsDbAccessMax           Unsigned32,
        rsDbAccessMin           Unsigned32,
        rsDbFutureAccessLast    Unsigned32,
        rsDbStage1AccessLast    Unsigned32,
        rsDbStage2AccessLast    Unsigned32,
        rsDbStage3AccessLast    Unsigned32,
        rsJmsMessageAverage     Unsigned32,
        rsJmsMessageCount       Counter64,
        rsJmsMessageLast        Unsigned32,
        rsJmsMessageLastSize    Unsigned32,
        rsJmsMessageMax         Unsigned32,
        rsJmsMessageMin         Unsigned32
}

rsStorageStatsIndex OBJECT-TYPE
        SYNTAX                  Unsigned32
        MAX-ACCESS              read-only
        STATUS                  current
        DESCRIPTION
        "GVP_ReportingServer.rsStorageStatsIndex: Reference index for each storage stats."
::= { rsStorageStatsEntry 1 }

rsStorageName OBJECT-TYPE
        SYNTAX                  DisplayString
        MAX-ACCESS              read-only
        STATUS                  current
        DESCRIPTION
        "GVP_ReportingServer.rsStorageName: Name of the storage stats."
::= { rsStorageStatsEntry 2 }

rsStorageStatus OBJECT-TYPE
        SYNTAX                  DisplayString
        MAX-ACCESS              read-only
        STATUS                  current
        DESCRIPTION
        "GVP_ReportingServer.rsStorageStatus: The status of the storage class that can be one of WAITING_JMS, 
        PROCESSING or DB_ACCESS."
::= { rsStorageStatsEntry 3 }

rsDbAccessAverage OBJECT-TYPE
        SYNTAX                  Unsigned32
        MAX-ACCESS              read-only
        STATUS                  current
        DESCRIPTION
        "GVP_ReportingServer.rsDbAccessAverage: The average elapsed time, in milliseconds, spent on database operations."
::= { rsStorageStatsEntry 4 }

rsDbAccessCount OBJECT-TYPE
        SYNTAX                  Counter64
        MAX-ACCESS              read-only
        STATUS                  current
        DESCRIPTION
        "GVP_ReportingServer.rsDbAccessCount: The count of database access for this storage class."
::= { rsStorageStatsEntry 5 }

rsDbAccessLast OBJECT-TYPE
        SYNTAX                  Unsigned32
        MAX-ACCESS              read-only
        STATUS                  current
        DESCRIPTION
        "GVP_ReportingServer.rsDbAccessLast: The elapsed time, in milliseconds, spent on the last database access."
::= { rsStorageStatsEntry 6 }

rsDbAccessMax OBJECT-TYPE
        SYNTAX                  Unsigned32
        MAX-ACCESS              read-only
        STATUS                  current
        DESCRIPTION
        "GVP_ReportingServer.rsDbAccessMax: The maximum elapsed time, in milliseconds, spent on database access."
::= { rsStorageStatsEntry 7 }

rsDbAccessMin OBJECT-TYPE
        SYNTAX                  Unsigned32
        MAX-ACCESS              read-only
        STATUS                  current
        DESCRIPTION
        "GVP_ReportingServer.rsDbAccessMin: The minimum elapsed time, in milliseconds, spent on database access."
::= { rsStorageStatsEntry 8 }

rsDbFutureAccessLast OBJECT-TYPE
        SYNTAX                  Unsigned32
        MAX-ACCESS              read-only
        STATUS                  current
        DESCRIPTION
        "GVP_ReportingServer.rsDbFutureAccessLast: The elapsed time, in milliseconds, spent on the last database access 
        to the future table (only apply to partitioning enabled schema)."
::= { rsStorageStatsEntry 9 }

rsDbStage1AccessLast OBJECT-TYPE
        SYNTAX                  Unsigned32
        MAX-ACCESS              read-only
        STATUS                  current
        DESCRIPTION
        "GVP_ReportingServer.rsDbStage1AccessLast: The elapsed time, in milliseconds, spent on the last database access 
        to the stage1 table (only apply to partitioning enabled schema.)"
::= { rsStorageStatsEntry 10 }

rsDbStage2AccessLast OBJECT-TYPE
        SYNTAX                  Unsigned32
        MAX-ACCESS              read-only
        STATUS                  current
        DESCRIPTION
        "GVP_ReportingServer.rsDbStage2AccessLast: The elapsed time, in milliseconds, spent on the last database access 
        to the stage2 table (only apply to partitioning enabled schema)."
::= { rsStorageStatsEntry 11 }

rsDbStage3AccessLast OBJECT-TYPE
        SYNTAX                  Unsigned32
        MAX-ACCESS              read-only
        STATUS                  current
        DESCRIPTION
        "GVP_ReportingServer.rsDbStage3AccessLast: The elapsed time, in milliseconds, spent on the last database access 
        to the stage3 table (only apply to partitioning enabled schema)."
::= { rsStorageStatsEntry 12 }

rsJmsMessageAverage OBJECT-TYPE
        SYNTAX                  Unsigned32
        MAX-ACCESS              read-only
        STATUS                  current
        DESCRIPTION
        "GVP_ReportingServer.rsJmsMessageAverage: The elapsed time, in milliseconds, spent on processing JMS messages."
::= { rsStorageStatsEntry 13 }

rsJmsMessageCount OBJECT-TYPE
        SYNTAX                  Counter64
        MAX-ACCESS              read-only
        STATUS                  current
        DESCRIPTION
        "GVP_ReportingServer.rsJmsMessageCount: The count of JMS messages."
::= { rsStorageStatsEntry 14 }

rsJmsMessageLast OBJECT-TYPE
        SYNTAX                  Unsigned32
        MAX-ACCESS              read-only
        STATUS                  current
        DESCRIPTION
        "GVP_ReportingServer.rsJmsMessageLast: The elapsed time, in milliseconds, spent on processing the last JMS message."
::= { rsStorageStatsEntry 15 }

rsJmsMessageLastSize OBJECT-TYPE
        SYNTAX                  Unsigned32
        MAX-ACCESS              read-only
        STATUS                  current
        DESCRIPTION
        "GVP_ReportingServer.rsJmsMessageLastSize: The size of the last JMS message."
::= { rsStorageStatsEntry 16 }

rsJmsMessageMax OBJECT-TYPE
        SYNTAX                  Unsigned32
        MAX-ACCESS              read-only
        STATUS                  current
        DESCRIPTION
        "GVP_ReportingServer.rsJmsMessageMax: The maximum elapsed time, in milliseconds, spent on processing JMS message."
::= { rsStorageStatsEntry 17 }

rsJmsMessageMin OBJECT-TYPE
        SYNTAX                  Unsigned32
        MAX-ACCESS              read-only
        STATUS                  current
        DESCRIPTION
        "GVP_ReportingServer.rsJmsMessageMin: The minimum elapsed time, in milliseconds, spent on processing JMS message."
::= { rsStorageStatsEntry 18 }

---
--- RS Message Queue Table
---

rsQueueTable OBJECT-TYPE
        SYNTAX          SEQUENCE OF RsQueueEntry
        MAX-ACCESS      not-accessible
        STATUS          current
        DESCRIPTION
                "GVP_ReportingServer: Statistics on RS Message queues."
        ::= { rs 4 }


rsQueueEntry OBJECT-TYPE
        SYNTAX          RsQueueEntry
        MAX-ACCESS      not-accessible
        STATUS          current
        DESCRIPTION
                "GVP_ReportingServer.rsQueueEntry: An entry (conceptual row) in the rsQueueTable"
        INDEX { gvpConfigDBID, rsQueueIndex }
        ::= { rsQueueTable 1 }

RsQueueEntry ::= SEQUENCE 
{       
        rsQueueIndex            Unsigned32,
        rsQueueName             DisplayString,
        rsProducerCount         Counter64,
        rsQueueSize             Unsigned32,
        rsDequeueCount          Counter64,
        rsEnqueueCount          Counter64
}

rsQueueIndex OBJECT-TYPE
        SYNTAX                  Unsigned32
        MAX-ACCESS              read-only
        STATUS                  current
        DESCRIPTION
        "GVP_ReportingServer.rsQueueIndex: Reference index for each message queue."
::= { rsQueueEntry 1 }

rsQueueName OBJECT-TYPE
        SYNTAX                  DisplayString
        MAX-ACCESS              read-only
        STATUS                  current
        DESCRIPTION
        "GVP_ReportingServer.rsQueueName: The name of the message queue."
::= { rsQueueEntry 2 }

rsProducerCount OBJECT-TYPE
        SYNTAX                  Counter64
        MAX-ACCESS              read-only
        STATUS                  current
        DESCRIPTION
        "GVP_ReportingServer.rsProducerCount: The producer count of the message queue."
::= { rsQueueEntry 3 }

rsQueueSize OBJECT-TYPE
        SYNTAX                  Unsigned32
        MAX-ACCESS              read-only
        STATUS                  current
        DESCRIPTION
        "GVP_ReportingServer.rsQueueSize: The size of the message queue."
::= { rsQueueEntry 4 }

rsDequeueCount OBJECT-TYPE
        SYNTAX                  Counter64
        MAX-ACCESS              read-only
        STATUS                  current
        DESCRIPTION
        "GVP_ReportingServer.rsDequeueCount: The dequeue count of the message queue."
::= { rsQueueEntry 5 }

rsEnqueueCount OBJECT-TYPE
        SYNTAX                  Counter64
        MAX-ACCESS              read-only
        STATUS                  current
        DESCRIPTION
        "GVP_ReportingServer.rsEnqueueCount: The enqueue count of the message queue."
::= { rsQueueEntry 6 }

END
