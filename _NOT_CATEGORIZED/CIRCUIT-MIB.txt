ALARM-MIB DEFINITIONS ::= BEGIN

-- ==================================================================
-- Copyright @ 2013 Unify GmbH & Co. KG
--
-- All Rights Reserved.
--
-- Reproduction of this document is authorized on condition that
-- this copyright notice is included.
--
-- This MIB document embodies proprietary intellectual property of Unify,
-- which retains all title and ownership in this MIB, including any revisions.
--
-- This module will be extended, as required.
--
-- Unify reserves the right to make changes in specification and other
-- information contained in this document without prior notice. The reader
-- should consult Unify to determine whether any such changes have been made.
--
-- Copyright @ 2013 Unify GmbH & Co. KG

-- ==================================================================


-- ==================================================================
-- Revision History V1R0                (Date needs to match LAST-UPDATED below)
--  2013-12-18  Uwe Grothe                    Initial issue
--  2014-07-28  Nigel Feavyour (Com US)       V1R0 version of MIB
--  2014-08-18  Nigel Feavyour (Com US)       Automatically generated MIB
--                                            Added alarm04047 alarmC04047
--                                            Added alarm04048 alarmC04048
--  2014-08-29  Nigel Feavyour (Com US)       Automatically generated MIB
--                                            Added alarm01004 alarmC01004
--                                            Added alarm01005 alarmC01005
--                                            Added alarm01006 alarmC01006
--                                            Added alarm01007 alarmC01007
--                                            Added alarm04026 alarmC04026
--                                            Added alarm09009 alarmC09009
--                                            Added alarm13001 alarmC13001
--                                            Added alarm50011 alarmC50011
--                                            Added alarm50015 alarmC50015
--                                            Added alarm50016 alarmC50016
--                                            Added alarm50017 alarmC50017
--                                            Added alarm50018 alarmC50018
--                                            Added alarm56992 alarmC56992
--                                            Added alarm57013 alarmC57013
--                                            Added alarm57014 alarmC57014
--                                            Added alarm57015 alarmC57015
--                                            Added alarm57016 alarmC57016
--                                            Added alarm57017 alarmC57017
--                                            Deprecated alarm50002 alarmC50002
--  2014-09-10  Nigel Feavyour (Com US)       Automatically generated MIB
--                                            Added alarm50021 alarmC50021
--                                            Deprecated alarm08023 alarmC08023
--  2014-09-15  Nigel Feavyour (Com US)       Automatically generated MIB
--                                            Added alarm55002 alarmC55002
-- ==================================================================


IMPORTS
    MODULE-IDENTITY, OBJECT-TYPE, Integer32, NOTIFICATION-TYPE, enterprises        FROM SNMPv2-SMI
    DisplayString, RowStatus                                                                                     FROM SNMPv2-TC
    senProducts                                                                                                        FROM SEN-ROOT-MIB;

        ansible                OBJECT IDENTIFIER ::= { senProducts 6 }
                                -- Ansible product-specific MIBs
                                --                = senProducts         6
                                --                = enterprises sen   1 6
                                --                = enterprises 32804 1 6
                                --                = 1 3 6 1 4 1 32804 1 6

        
        alarms                MODULE-IDENTITY
        LAST-UPDATED        "201409150000Z"
        ORGANIZATION        "Unify"
        CONTACT-INFO        "Uwe Grothe
                                        Postal:        5500 Broken Sound Blvd NW
                                                        Boca Raton, FL 33487-3501                                                
                                        E-mail:        uwe.grothe@unify.com"

        DESCRIPTION        "This MIB module implements SNMP Alarms.
                            An alarm is uniquely identified by the trap name
                            (mainly the last two numbers of the trap OID)
                            and the neName.
                            An alarm trap is a trap with a non-cleared severity.
                            It is cleared by the same trap
                            with the same neName and a severity of clear.
                            An existing alarm can be modified by a trap with the
                            same OID and neName but with one or more modified values,
                            e.g. for severity, nodes, or faultyObject"

        ::= { ansible 1 }

        trapParameters              OBJECT IDENTIFIER ::= { alarms 1 }
        eventCommon                 OBJECT IDENTIFIER ::= { alarms 2 }
        eventGroups                 OBJECT IDENTIFIER ::= { alarms 3 }
        eventGroupsC                OBJECT IDENTIFIER ::= { alarms 4 }

        eventGroup01                OBJECT IDENTIFIER ::= { eventGroups  1 }
        eventGroup02                OBJECT IDENTIFIER ::= { eventGroups  2 }        -- deprecated
        eventGroup03                OBJECT IDENTIFIER ::= { eventGroups  3 }
        eventGroup04                OBJECT IDENTIFIER ::= { eventGroups  4 }
        eventGroup05                OBJECT IDENTIFIER ::= { eventGroups  5 }
        eventGroup06                OBJECT IDENTIFIER ::= { eventGroups  6 }
        eventGroup07                OBJECT IDENTIFIER ::= { eventGroups  7 }        -- deprecated
        eventGroup08                OBJECT IDENTIFIER ::= { eventGroups  8 }
        eventGroup09                OBJECT IDENTIFIER ::= { eventGroups  9 }
        eventGroup10                OBJECT IDENTIFIER ::= { eventGroups 10 }
        eventGroup11                OBJECT IDENTIFIER ::= { eventGroups 11 }        -- deprecated
        eventGroup12                OBJECT IDENTIFIER ::= { eventGroups 12 }
        eventGroup13                OBJECT IDENTIFIER ::= { eventGroups 13 }
        eventGroup14                OBJECT IDENTIFIER ::= { eventGroups 14 }
        eventGroup15                OBJECT IDENTIFIER ::= { eventGroups 15 }        -- deprecated
        eventGroup16                OBJECT IDENTIFIER ::= { eventGroups 16 }        -- deprecated
        eventGroup17                OBJECT IDENTIFIER ::= { eventGroups 17 }
        eventGroup18                OBJECT IDENTIFIER ::= { eventGroups 18 }        -- deprecated
        eventGroup19                OBJECT IDENTIFIER ::= { eventGroups 19 }        -- deprecated
        eventGroup20                OBJECT IDENTIFIER ::= { eventGroups 20 }
        eventGroup21                OBJECT IDENTIFIER ::= { eventGroups 21 }
        eventGroup22                OBJECT IDENTIFIER ::= { eventGroups 22 }
        eventGroup23                OBJECT IDENTIFIER ::= { eventGroups 23 }
        eventGroup50                OBJECT IDENTIFIER ::= { eventGroups 50 }
        eventGroup53                OBJECT IDENTIFIER ::= { eventGroups 53 }
        eventGroup54                OBJECT IDENTIFIER ::= { eventGroups 54 }
        eventGroup55                OBJECT IDENTIFIER ::= { eventGroups 55 }
        eventGroup56                OBJECT IDENTIFIER ::= { eventGroups 56 }
        eventGroup57                OBJECT IDENTIFIER ::= { eventGroups 57 }
        eventGroup58                OBJECT IDENTIFIER ::= { eventGroups 58 }
        eventGroup59                OBJECT IDENTIFIER ::= { eventGroups 59 }
        eventGroup60                OBJECT IDENTIFIER ::= { eventGroups 60 }
        eventGroup80                OBJECT IDENTIFIER ::= { eventGroups 80 }
        eventGroup81                OBJECT IDENTIFIER ::= { eventGroups 81 }
        eventGroup82                OBJECT IDENTIFIER ::= { eventGroups 82 }

        eventGroupC01               OBJECT IDENTIFIER ::= { eventGroupsC  1 }
        eventGroupC02               OBJECT IDENTIFIER ::= { eventGroupsC  2 }        -- deprecated
        eventGroupC03               OBJECT IDENTIFIER ::= { eventGroupsC  3 }
        eventGroupC04               OBJECT IDENTIFIER ::= { eventGroupsC  4 }
        eventGroupC05               OBJECT IDENTIFIER ::= { eventGroupsC  5 }
        eventGroupC06               OBJECT IDENTIFIER ::= { eventGroupsC  6 }
        eventGroupC07               OBJECT IDENTIFIER ::= { eventGroupsC  7 }        -- deprecated
        eventGroupC08               OBJECT IDENTIFIER ::= { eventGroupsC  8 }
        eventGroupC09               OBJECT IDENTIFIER ::= { eventGroupsC  9 }
        eventGroupC10               OBJECT IDENTIFIER ::= { eventGroupsC 10 }
        eventGroupC11               OBJECT IDENTIFIER ::= { eventGroupsC 11 }        -- deprecated
        eventGroupC12               OBJECT IDENTIFIER ::= { eventGroupsC 12 }
        eventGroupC13               OBJECT IDENTIFIER ::= { eventGroupsC 13 }
        eventGroupC14               OBJECT IDENTIFIER ::= { eventGroupsC 14 }
        eventGroupC15               OBJECT IDENTIFIER ::= { eventGroupsC 15 }        -- deprecated
        eventGroupC16               OBJECT IDENTIFIER ::= { eventGroupsC 16 }        -- deprecated
        eventGroupC17               OBJECT IDENTIFIER ::= { eventGroupsC 17 }
        eventGroupC18               OBJECT IDENTIFIER ::= { eventGroupsC 18 }        -- deprecated
        eventGroupC19               OBJECT IDENTIFIER ::= { eventGroupsC 19 }        -- deprecated
        eventGroupC20               OBJECT IDENTIFIER ::= { eventGroupsC 20 }
        eventGroupC21               OBJECT IDENTIFIER ::= { eventGroupsC 21 }
        eventGroupC22               OBJECT IDENTIFIER ::= { eventGroupsC 22 }
        eventGroupC23               OBJECT IDENTIFIER ::= { eventGroupsC 23 }
        eventGroupC50               OBJECT IDENTIFIER ::= { eventGroupsC 50 }
        eventGroupC53               OBJECT IDENTIFIER ::= { eventGroupsC 53 }
        eventGroupC54               OBJECT IDENTIFIER ::= { eventGroupsC 54 }
        eventGroupC55               OBJECT IDENTIFIER ::= { eventGroupsC 55 }
        eventGroupC56               OBJECT IDENTIFIER ::= { eventGroupsC 56 }
        eventGroupC57               OBJECT IDENTIFIER ::= { eventGroupsC 57 }
        eventGroupC58               OBJECT IDENTIFIER ::= { eventGroupsC 58 }
        eventGroupC59               OBJECT IDENTIFIER ::= { eventGroupsC 59 }
        eventGroupC60               OBJECT IDENTIFIER ::= { eventGroupsC 60 }
        eventGroupC80               OBJECT IDENTIFIER ::= { eventGroupsC 80 }
        eventGroupC81               OBJECT IDENTIFIER ::= { eventGroupsC 81 }
        eventGroupC82               OBJECT IDENTIFIER ::= { eventGroupsC 82 }

        --********************************************************************
        -- Alarm Trap Parameters:
        --********************************************************************

        neName                     OBJECT-TYPE
        SYNTAX                     DisplayString
        MAX-ACCESS                 not-accessible
        STATUS                     current
        DESCRIPTION                "name of the network element sending the alarm"
        ::= { trapParameters 1 }


        neType                     OBJECT-TYPE
        SYNTAX                     DisplayString
        MAX-ACCESS                 not-accessible
        STATUS                     current
        DESCRIPTION                "Indicate the network element type"
        ::= { trapParameters 2 }

   
        eventGroupName             OBJECT-TYPE
        SYNTAX                     DisplayString
        MAX-ACCESS                 not-accessible
        STATUS                     current
        DESCRIPTION                "corresponds to the eventGroup, 
                                    the second last number of the trap OID."
        ::= { trapParameters 3 }


        eventName                  OBJECT-TYPE
        SYNTAX                     DisplayString
        MAX-ACCESS                 not-accessible
        STATUS                     current
        DESCRIPTION                "corresponds to the event within the eventGroup
                                    reported by the trap, the last number of the trap OID."
        ::= { trapParameters 4 }


        correlationId              OBJECT-TYPE
        SYNTAX                     DisplayString
        MAX-ACCESS                 not-accessible
        STATUS                     current
        DESCRIPTION                "same value for traps associated with the same active alarm."
        ::= { trapParameters 5 }


        severity                   OBJECT-TYPE
        SYNTAX                     INTEGER        {indeterminate(0),   -- not used
                                        critical(1),
                                        major(2),
                                        minor(3),
                                        warning(4),                    -- not used
                                        cleared(5) }
        MAX-ACCESS                 not-accessible
        STATUS                     current
        DESCRIPTION                "corresponds to X.721/X.733:PerceivedSeverity.
                                    indeterminate and warning are not used.
                                    critical, major, ,and minor correspond to an alarm.
                                    cleared corresponds to an alarm clearance event, which clears
                                    all alarms of the network element that 
                                    had been reported by this trap."
        ::= { trapParameters 6 }

     
        eventTime                  OBJECT-TYPE
        SYNTAX                     DisplayString
        MAX-ACCESS                 not-accessible
        STATUS                     current
        DESCRIPTION                "An element of X.710: Parameter contains
                                    the time of generation of the event,
                                    The EventTime is a GeneralizedTime (defined in X.208),
                                    format is YYYYMMDDhhmmss.f+hhmm where 
                                    Y year 
                                    M month in year
                                    D day in month
                                    h hour in day (0-23)
                                    m minute in hour
                                    s second in minute
                                    f tenth part of second
                                    +hhmm        local time offset(+-) to UTC time. 
                                    Time represents the local time (t1), and the time 
                                    differential (t2) enables UTC time to be determined as follows:
                                    UTC time = t1 - t2"
        ::= { trapParameters 7 } 


        nodes                      OBJECT-TYPE
        SYNTAX                     DisplayString
        MAX-ACCESS                 not-accessible
        STATUS                     current
        DESCRIPTION                "comma delimited list of node names associated with the alarm"
        ::= { trapParameters 8 }


        faultyObject               OBJECT-TYPE
        SYNTAX                     DisplayString
        MAX-ACCESS                 not-accessible
        STATUS                     current
        DESCRIPTION                "Specifies the component of the network element at fault."
        ::= { trapParameters 9 }
  

        monitoredValue             OBJECT-TYPE
        SYNTAX                     DisplayString
        MAX-ACCESS                 not-accessible
        STATUS                     current
        DESCRIPTION                "Specifies the value of the current condition of the system
                                    for this particular alarm"
        ::= { trapParameters 10 }


        thresholdValues            OBJECT-TYPE
        SYNTAX                     DisplayString
        MAX-ACCESS                 not-accessible
        STATUS                     current
        DESCRIPTION                "Specifies the values that needs to be crossed by
                                    monitored-value for an alarm to be generated.
                                    Up to 3 values separated by comma can be defined
                                    associated with the severities minor,major,critical.
                                    e.g. ,3,8 means major alarm when monitored value is 3 or higher
                                    and critical alarm when 8 or higher. No minor alarm"
        ::= { trapParameters 11 }


        info                       OBJECT-TYPE
        SYNTAX                     DisplayString
        MAX-ACCESS                 not-accessible
        STATUS                     current
        DESCRIPTION                "Indicate the network element type"
        ::= { trapParameters 12 }


        --********************************************************************
        -- Common Trap Definitions
        --********************************************************************


        networkElementStarting     NOTIFICATION-TYPE
        OBJECTS        {        neName,
                                neType,
                                eventTime }
        STATUS                     current
        DESCRIPTION                "This trap reports that the network element is starting up.
                                    All alarms of this network element shall be deleted."
        ::= { eventCommon 1 }

        --********************************************************************
        -- Alarm Trap Definitions for alarms sent by a particular node
        -- (using eventGroup)
        --********************************************************************

        --********************************************************************
        -- Alarm Trap Definitions for event group 01: Platform
        --********************************************************************

        alarm01001 NOTIFICATION-TYPE
        OBJECTS        {        neName,
                                neType,
                                eventGroupName,                        -- 01: Platform
                                eventName,                             -- 001: InvalidAlarmConfiguration
                                correlationId,
                                severity,
                                eventTime,
                                faultyObject,
                                monitoredValue,
                                thresholdValues,
                                info   }
        STATUS                current
        DESCRIPTION        "Spontaneous Alarm from the managed network element:
                            The alarm configuration has problems.
                            Check the problem listed in the faulty object and correct."
        ::= { eventGroup01 1 }

        alarm01002 NOTIFICATION-TYPE
        OBJECTS        {        neName,
                                neType,
                                eventGroupName,                        -- 01: Platform
                                eventName,                             -- 002: InvalidTimezoneConfiguration
                                correlationId,
                                severity,
                                eventTime,
                                faultyObject,
                                monitoredValue,
                                thresholdValues,
                                info   }
        STATUS                current
        DESCRIPTION        "Spontaneous Alarm from the managed network element:
                            The timezone configured in the datacenter configuration in the ZooKeeper database is not one of values supported by the Linux Operating System. An invalid timezone will be ignored so the timezone will remain as the default timezone (UTC) or the last valid timezone that was successfully configured.
                            Manually change the timezone in the datacenter configuration in the ZooKeeper database to a valid timezone. Valid timezones can be found under directory /usr/share/zoneinfo (e.g. US/Eastern)."
        ::= { eventGroup01 2 }

        alarm01003 NOTIFICATION-TYPE
        OBJECTS        {        neName,
                                neType,
                                eventGroupName,                        -- 01: Platform
                                eventName,                             -- 003: UnknownAlarmId
                                correlationId,
                                severity,
                                eventTime,
                                faultyObject,
                                monitoredValue,
                                thresholdValues,
                                info   }
        STATUS                current
        DESCRIPTION        "Spontaneous Alarm from the managed network element:
                            An alarm has been raised or used with an unknown group ID and/or event ID.
                            Check if the alarm should be raised/used. If correct, add alarm to alarm configuration."
        ::= { eventGroup01 3 }

        alarm01004 NOTIFICATION-TYPE
        OBJECTS        {        neName,
                                neType,
                                eventGroupName,                        -- 01: Platform
                                eventName,                             -- 004: InvalidMonitoredValue
                                correlationId,
                                severity,
                                eventTime,
                                faultyObject,
                                monitoredValue,
                                thresholdValues,
                                info   }
        STATUS                current
        DESCRIPTION        "Spontaneous Alarm from the managed network element:
                            An alarm has been raised or used with an invalid monitored attribute value.
                            Correct code raising the alarm."
        ::= { eventGroup01 4 }

        alarm01005 NOTIFICATION-TYPE
        OBJECTS        {        neName,
                                neType,
                                eventGroupName,                        -- 01: Platform
                                eventName,                             -- 005: FaultyObjectTooLong
                                correlationId,
                                severity,
                                eventTime,
                                faultyObject,
                                monitoredValue,
                                thresholdValues,
                                info   }
        STATUS                current
        DESCRIPTION        "Spontaneous Alarm from the managed network element:
                            An alarm has been raised with a FaultyObject string that is longer than 255. It has been truncated.
                            Correct code raising the alarm."
        ::= { eventGroup01 5 }

        alarm01006 NOTIFICATION-TYPE
        OBJECTS        {        neName,
                                neType,
                                eventGroupName,                        -- 01: Platform
                                eventName,                             -- 006: AddlInfoTooLong
                                correlationId,
                                severity,
                                eventTime,
                                faultyObject,
                                monitoredValue,
                                thresholdValues,
                                info   }
        STATUS                current
        DESCRIPTION        "Spontaneous Alarm from the managed network element:
                            An alarm has been raised with an Addl Info string that is longer than 255. It has been truncated.
                            Correct code raising the alarm."
        ::= { eventGroup01 6 }

        alarm01007 NOTIFICATION-TYPE
        OBJECTS        {        neName,
                                neType,
                                eventGroupName,                        -- 01: Platform
                                eventName,                             -- 007: TooManyAlarmParameters
                                correlationId,
                                severity,
                                eventTime,
                                faultyObject,
                                monitoredValue,
                                thresholdValues,
                                info   }
        STATUS                current
        DESCRIPTION        "Spontaneous Alarm from the managed network element:
                            There is additional text after AddlInfo in the reported alarm string.
                            Correct code raising the alarm."
        ::= { eventGroup01 7 }


        --********************************************************************
        -- Alarm Trap Definitions for event group 03: FileTransfer
        --********************************************************************

        alarm03001 NOTIFICATION-TYPE
        OBJECTS        {        neName,
                                neType,
                                eventGroupName,                        -- 03: FileTransfer
                                eventName,                             -- 001: ExportFailing
                                correlationId,
                                severity,
                                eventTime,
                                faultyObject,
                                monitoredValue,
                                thresholdValues,
                                info   }
        STATUS                current
        DESCRIPTION        "Spontaneous Alarm from the managed network element:
                            The SFTP connection to remote server has failed for this instance.
                            Probably due to bad File Export configuration data or a network issue where we cannot communicate with the SFTP server. Please check /var/log/platform/logging/LogIssues.log file. Collect the output of the command /opt/platform/bin/plat_fe_ctl --display_working_config."
        ::= { eventGroup03 1 }

        alarm03002 NOTIFICATION-TYPE
        OBJECTS        {        neName,
                                neType,
                                eventGroupName,                        -- 03: FileTransfer
                                eventName,                             -- 002: ExportFailing
                                correlationId,
                                severity,
                                eventTime,
                                faultyObject,
                                monitoredValue,
                                thresholdValues,
                                info   }
        STATUS                current
        DESCRIPTION        "Spontaneous Alarm from the managed network element:
                            The SFTP connection to remote server has failed for this instance.
                            Probably due to bad File Export configuration data or a network issue where we cannot communicate with the SFTP server. Please check /var/log/platform/logging/LogIssues.log file. Collect the output of the command /opt/platform/bin/plat_fe_ctl --display_working_config."
        ::= { eventGroup03 2 }

        alarm03003 NOTIFICATION-TYPE
        OBJECTS        {        neName,
                                neType,
                                eventGroupName,                        -- 03: FileTransfer
                                eventName,                             -- 003: ExportFailing
                                correlationId,
                                severity,
                                eventTime,
                                faultyObject,
                                monitoredValue,
                                thresholdValues,
                                info   }
        STATUS                current
        DESCRIPTION        "Spontaneous Alarm from the managed network element:
                            The SFTP connection to remote server has failed for this instance.
                            Probably due to bad File Export configuration data or a network issue where we cannot communicate with the SFTP server. Please check /var/log/platform/logging/LogIssues.log file. Collect the output of the command /opt/platform/bin/plat_fe_ctl --display_working_config."
        ::= { eventGroup03 3 }


        --********************************************************************
        -- Alarm Trap Definitions for event group 04: Process
        --********************************************************************

        alarm04001 NOTIFICATION-TYPE
        OBJECTS        {        neName,
                                neType,
                                eventGroupName,                        -- 04: Process
                                eventName,                             -- 001: PmAborted
                                correlationId,
                                severity,
                                eventTime,
                                faultyObject,
                                monitoredValue,
                                thresholdValues,
                                info   }
        STATUS                current
        DESCRIPTION        "Spontaneous Alarm from the managed network element:
                            Process Monitoring has aborted.
                            Check configuration files and get logs in debug level 7."
        ::= { eventGroup04 1 }

        alarm04002 NOTIFICATION-TYPE
        OBJECTS        {        neName,
                                neType,
                                eventGroupName,                        -- 04: Process
                                eventName,                             -- 002: NetworkNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 2 }

        alarm04003 NOTIFICATION-TYPE
        OBJECTS        {        neName,
                                neType,
                                eventGroupName,                        -- 04: Process
                                eventName,                             -- 003: RoutesNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 3 }

        alarm04004 NOTIFICATION-TYPE
        OBJECTS        {        neName,
                                neType,
                                eventGroupName,                        -- 04: Process
                                eventName,                             -- 004: GmondNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 4 }

        alarm04005 NOTIFICATION-TYPE
        OBJECTS        {        neName,
                                neType,
                                eventGroupName,                        -- 04: Process
                                eventName,                             -- 005: hsflowdNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 5 }

        alarm04006 NOTIFICATION-TYPE
        OBJECTS        {        neName,
                                neType,
                                eventGroupName,                        -- 04: Process
                                eventName,                             -- 006: jmxtransNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 6 }

        alarm04007 NOTIFICATION-TYPE
        OBJECTS        {        neName,
                                neType,
                                eventGroupName,                        -- 04: Process
                                eventName,                             -- 007: ntpNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 7 }

        alarm04008 NOTIFICATION-TYPE
        OBJECTS        {        neName,
                                neType,
                                eventGroupName,                        -- 04: Process
                                eventName,                             -- 008: syslogNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 8 }

        alarm04009 NOTIFICATION-TYPE
        OBJECTS        {        neName,
                                neType,
                                eventGroupName,                        -- 04: Process
                                eventName,                             -- 009: sshdNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 9 }

        alarm04010 NOTIFICATION-TYPE
        OBJECTS        {        neName,
                                neType,
                                eventGroupName,                        -- 04: Process
                                eventName,                             -- 010: snmpdNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 10 }

        alarm04011 NOTIFICATION-TYPE
        OBJECTS        {        neName,
                                neType,
                                eventGroupName,                        -- 04: Process
                                eventName,                             -- 011: idsNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 11 }

        alarm04012 NOTIFICATION-TYPE
        OBJECTS        {        neName,
                                neType,
                                eventGroupName,                        -- 04: Process
                                eventName,                             -- 012: logstashNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 12 }

        alarm04013 NOTIFICATION-TYPE
        OBJECTS        {        neName,
                                neType,
                                eventGroupName,                        -- 04: Process
                                eventName,                             -- 013: TraceDriverNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 13 }

        alarm04014 NOTIFICATION-TYPE
        OBJECTS        {        neName,
                                neType,
                                eventGroupName,                        -- 04: Process
                                eventName,                             -- 014: LoggingDriverNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 14 }

        alarm04015 NOTIFICATION-TYPE
        OBJECTS        {        neName,
                                neType,
                                eventGroupName,                        -- 04: Process
                                eventName,                             -- 015: LoggingProcessNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 15 }

        alarm04016 NOTIFICATION-TYPE
        OBJECTS        {        neName,
                                neType,
                                eventGroupName,                        -- 04: Process
                                eventName,                             -- 016: PlatAlarmNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 16 }

        alarm04017 NOTIFICATION-TYPE
        OBJECTS        {        neName,
                                neType,
                                eventGroupName,                        -- 04: Process
                                eventName,                             -- 017: PlatZooClientNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 17 }

        alarm04018 NOTIFICATION-TYPE
        OBJECTS        {        neName,
                                neType,
                                eventGroupName,                        -- 04: Process
                                eventName,                             -- 018: PlatPsrNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 18 }

        alarm04019 NOTIFICATION-TYPE
        OBJECTS        {        neName,
                                neType,
                                eventGroupName,                        -- 04: Process
                                eventName,                             -- 019: PlatFileExportNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 19 }

        alarm04020 NOTIFICATION-TYPE
        OBJECTS        {        neName,
                                neType,
                                eventGroupName,                        -- 04: Process
                                eventName,                             -- 020: PlatPstackNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 20 }

        alarm04021 NOTIFICATION-TYPE
        OBJECTS        {        neName,
                                neType,
                                eventGroupName,                        -- 04: Process
                                eventName,                             -- 021: PlatMonitorNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 21 }

        alarm04022 NOTIFICATION-TYPE
        OBJECTS        {        neName,
                                neType,
                                eventGroupName,                        -- 04: Process
                                eventName,                             -- 022: NetReceiverNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 22 }

        alarm04023 NOTIFICATION-TYPE
        OBJECTS        {        neName,
                                neType,
                                eventGroupName,                        -- 04: Process
                                eventName,                             -- 023: TcaNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 23 }

        alarm04024 NOTIFICATION-TYPE
        OBJECTS        {        neName,
                                neType,
                                eventGroupName,                        -- 04: Process
                                eventName,                             -- 024: FileExportScannerNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 24 }

        alarm04025 NOTIFICATION-TYPE
        OBJECTS        {        neName,
                                neType,
                                eventGroupName,                        -- 04: Process
                                eventName,                             -- 025: PlatAuditSumNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 25 }

        alarm04026 NOTIFICATION-TYPE
        OBJECTS        {        neName,
                                neType,
                                eventGroupName,                        -- 04: Process
                                eventName,                             -- 026: PlatLogRotateNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 26 }

        alarm04035 NOTIFICATION-TYPE
        OBJECTS        {        neName,
                                neType,
                                eventGroupName,                        -- 04: Process
                                eventName,                             -- 035: ZooKeeperServerNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 35 }

        alarm04040 NOTIFICATION-TYPE
        OBJECTS        {        neName,
                                neType,
                                eventGroupName,                        -- 04: Process
                                eventName,                             -- 040: AccessRedisNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroup04 40 }

        alarm04041 NOTIFICATION-TYPE
        OBJECTS        {        neName,
                                neType,
                                eventGroupName,                        -- 04: Process
                                eventName,                             -- 041: AccessRedis-clusterNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Redis-cluster configuration."
        ::= { eventGroup04 41 }

        alarm04042 NOTIFICATION-TYPE
        OBJECTS        {        neName,
                                neType,
                                eventGroupName,                        -- 04: Process
                                eventName,                             -- 042: AccessTurnServerNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check TurnServer configuration."
        ::= { eventGroup04 42 }

        alarm04043 NOTIFICATION-TYPE
        OBJECTS        {        neName,
                                neType,
                                eventGroupName,                        -- 04: Process
                                eventName,                             -- 043: AccessNodeAppNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check NodeApp configuration."
        ::= { eventGroup04 43 }

        alarm04044 NOTIFICATION-TYPE
        OBJECTS        {        neName,
                                neType,
                                eventGroupName,                        -- 04: Process
                                eventName,                             -- 044: AccessLvsNodeNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check LvsNode configuration."
        ::= { eventGroup04 44 }

        alarm04045 NOTIFICATION-TYPE
        OBJECTS        {        neName,
                                neType,
                                eventGroupName,                        -- 04: Process
                                eventName,                             -- 045: AccessNginxNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Nginx configuration."
        ::= { eventGroup04 45 }

        alarm04046 NOTIFICATION-TYPE
        OBJECTS        {        neName,
                                neType,
                                eventGroupName,                        -- 04: Process
                                eventName,                             -- 046: AccessMetricsNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Metrics configuration."
        ::= { eventGroup04 46 }

        alarm04047 NOTIFICATION-TYPE
        OBJECTS        {        neName,
                                neType,
                                eventGroupName,                        -- 04: Process
                                eventName,                             -- 047: AccessAuditAppNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Audit configuration."
        ::= { eventGroup04 47 }

        alarm04048 NOTIFICATION-TYPE
        OBJECTS        {        neName,
                                neType,
                                eventGroupName,                        -- 04: Process
                                eventName,                             -- 048: AccessRedis-auditNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Redis configuration."
        ::= { eventGroup04 48 }

        alarm04060 NOTIFICATION-TYPE
        OBJECTS        {        neName,
                                neType,
                                eventGroupName,                        -- 04: Process
                                eventName,                             -- 060: LoadBalancerNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Load Balancer configuration."
        ::= { eventGroup04 60 }

        alarm04070 NOTIFICATION-TYPE
        OBJECTS        {        neName,
                                neType,
                                eventGroupName,                        -- 04: Process
                                eventName,                             -- 070: AnsibleVirgoNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroup04 70 }

        alarm04071 NOTIFICATION-TYPE
        OBJECTS        {        neName,
                                neType,
                                eventGroupName,                        -- 04: Process
                                eventName,                             -- 071: HazelcastNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroup04 71 }

        alarm04072 NOTIFICATION-TYPE
        OBJECTS        {        neName,
                                neType,
                                eventGroupName,                        -- 04: Process
                                eventName,                             -- 072: RabbitMQNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroup04 72 }

        alarm04075 NOTIFICATION-TYPE
        OBJECTS        {        neName,
                                neType,
                                eventGroupName,                        -- 04: Process
                                eventName,                             -- 075: MediaServerNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroup04 75 }

        alarm04080 NOTIFICATION-TYPE
        OBJECTS        {        neName,
                                neType,
                                eventGroupName,                        -- 04: Process
                                eventName,                             -- 080: PostgresqlNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 80 }

        alarm04081 NOTIFICATION-TYPE
        OBJECTS        {        neName,
                                neType,
                                eventGroupName,                        -- 04: Process
                                eventName,                             -- 081: HadoopNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 81 }

        alarm04082 NOTIFICATION-TYPE
        OBJECTS        {        neName,
                                neType,
                                eventGroupName,                        -- 04: Process
                                eventName,                             -- 082: TomcatNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 82 }

        alarm04083 NOTIFICATION-TYPE
        OBJECTS        {        neName,
                                neType,
                                eventGroupName,                        -- 04: Process
                                eventName,                             -- 083: NodeMonitorNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 83 }

        alarm04084 NOTIFICATION-TYPE
        OBJECTS        {        neName,
                                neType,
                                eventGroupName,                        -- 04: Process
                                eventName,                             -- 084: AlarmManagerDNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 84 }

        alarm04085 NOTIFICATION-TYPE
        OBJECTS        {        neName,
                                neType,
                                eventGroupName,                        -- 04: Process
                                eventName,                             -- 085: SolrdNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 85 }

        alarm04086 NOTIFICATION-TYPE
        OBJECTS        {        neName,
                                neType,
                                eventGroupName,                        -- 04: Process
                                eventName,                             -- 086: FilemgrdNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 86 }

        alarm04087 NOTIFICATION-TYPE
        OBJECTS        {        neName,
                                neType,
                                eventGroupName,                        -- 04: Process
                                eventName,                             -- 087: LogmgrdNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 87 }

        alarm04088 NOTIFICATION-TYPE
        OBJECTS        {        neName,
                                neType,
                                eventGroupName,                        -- 04: Process
                                eventName,                             -- 088: Apache2NotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 88 }

        alarm04089 NOTIFICATION-TYPE
        OBJECTS        {        neName,
                                neType,
                                eventGroupName,                        -- 04: Process
                                eventName,                             -- 089: GmetadNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroup04 89 }

        alarm04095 NOTIFICATION-TYPE
        OBJECTS        {        neName,
                                neType,
                                eventGroupName,                        -- 04: Process
                                eventName,                             -- 095: ImpManagementNotRunning
                                correlationId,
                                severity,
                                eventTime,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Management configuration."
        ::= { eventGroup04 95 }


        --********************************************************************
        -- Alarm Trap Definitions for event group 05: ProcessManager
        --********************************************************************

        alarm05001 NOTIFICATION-TYPE
        OBJECTS        {        neName,
                                neType,
                                eventGroupName,                        -- 05: ProcessManager
                                eventName,                             -- 001: InvalidPlatConfiguration
                                correlationId,
                                severity,
                                eventTime,
                                faultyObject,
                                monitoredValue,
                                thresholdValues,
                                info   }
        STATUS                current
        DESCRIPTION        "Spontaneous Alarm from the managed network element:
                            Platform configuration has invalid parameters:
A failure type of 1 means a missing or wrong configuration. PM can run.
2 means missing or wrong process configuration. PM can run but a process has potential problems.
3 means that the configuration file was rejected.
                            Check faulty object to know where the problem is located."
        ::= { eventGroup05 1 }

        alarm05002 NOTIFICATION-TYPE
        OBJECTS        {        neName,
                                neType,
                                eventGroupName,                        -- 05: ProcessManager
                                eventName,                             -- 002: InvalidServerConfiguration
                                correlationId,
                                severity,
                                eventTime,
                                faultyObject,
                                monitoredValue,
                                thresholdValues,
                                info   }
        STATUS                current
        DESCRIPTION        "Spontaneous Alarm from the managed network element:
                            Server configuration has invalid parameters:
A failure type of 1 means a missing or wrong configuration. PM can run.
2 means missing or wrong process configuration. PM can run but a process has potential problems.
3 means that the configuration file was rejected.
                            Check faulty object to know where the problem is located."
        ::= { eventGroup05 2 }

        alarm05003 NOTIFICATION-TYPE
        OBJECTS        {        neName,
                                neType,
                                eventGroupName,                        -- 05: ProcessManager
                                eventName,                             -- 003: CanNotExecuteCommand
                                correlationId,
                                severity,
                                eventTime,
                                faultyObject,
                                monitoredValue,
                                thresholdValues,
                                info   }
        STATUS                current
        DESCRIPTION        "Spontaneous Alarm from the managed network element:
                            One command could not be executed:
Command capabilities = 2 means that the command is important for PM operation and 3 means that it affects node operation.
                            Check faulty object and try to execute it by hand."
        ::= { eventGroup05 3 }

        alarm05004 NOTIFICATION-TYPE
        OBJECTS        {        neName,
                                neType,
                                eventGroupName,                        -- 05: ProcessManager
                                eventName,                             -- 004: UnexpectedBehaviour
                                correlationId,
                                severity,
                                eventTime,
                                faultyObject,
                                monitoredValue,
                                thresholdValues,
                                info   }
        STATUS                current
        DESCRIPTION        "Spontaneous Alarm from the managed network element:
                            PM has found an unexpected behavior during its execution.
1 means that PM is still running and only a feature affected.
2 means that PM is still running, but that process control is affected.
3 means that PM will abort and restart.
                            Check faulty object for function name and line number of the problem."
        ::= { eventGroup05 4 }

        alarm05005 NOTIFICATION-TYPE
        OBJECTS        {        neName,
                                neType,
                                eventGroupName,                        -- 05: ProcessManager
                                eventName,                             -- 005: RecoverEscalation
                                correlationId,
                                severity,
                                eventTime,
                                faultyObject,
                                monitoredValue,
                                thresholdValues,
                                info   }
        STATUS                current
        DESCRIPTION        "Spontaneous Alarm from the managed network element:
                            One or more process cannot be started.
If server Health State is 1 and the process continues to fail, all applicaton processes (Lvl 3) will be restarted.
If the HealthState is 2, the application restart did not work and all platform and all application processes (Lvl 1 and 2 will be restarted.
If the HealthState is 3, the node will be rebooted within 5 minutes.
                            Check which processe(s) are not working. Look for alarms reporting pstacks and coredumps. Collect debug files and send them to the next level of support for analysis."
        ::= { eventGroup05 5 }


        --********************************************************************
        -- Alarm Trap Definitions for event group 06: CoreDump
        --********************************************************************

        alarm06001 NOTIFICATION-TYPE
        OBJECTS        {        neName,
                                neType,
                                eventGroupName,                        -- 06: CoreDump
                                eventName,                             -- 001: PstackFound1
                                correlationId,
                                severity,
                                eventTime,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroup06 1 }

        alarm06002 NOTIFICATION-TYPE
        OBJECTS        {        neName,
                                neType,
                                eventGroupName,                        -- 06: CoreDump
                                eventName,                             -- 002: PstackFound2
                                correlationId,
                                severity,
                                eventTime,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroup06 2 }

        alarm06003 NOTIFICATION-TYPE
        OBJECTS        {        neName,
                                neType,
                                eventGroupName,                        -- 06: CoreDump
                                eventName,                             -- 003: PstackFound3
                                correlationId,
                                severity,
                                eventTime,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroup06 3 }

        alarm06004 NOTIFICATION-TYPE
        OBJECTS        {        neName,
                                neType,
                                eventGroupName,                        -- 06: CoreDump
                                eventName,                             -- 004: PstackFound4
                                correlationId,
                                severity,
                                eventTime,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroup06 4 }

        alarm06005 NOTIFICATION-TYPE
        OBJECTS        {        neName,
                                neType,
                                eventGroupName,                        -- 06: CoreDump
                                eventName,                             -- 005: PstackFound5
                                correlationId,
                                severity,
                                eventTime,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroup06 5 }

        alarm06006 NOTIFICATION-TYPE
        OBJECTS        {        neName,
                                neType,
                                eventGroupName,                        -- 06: CoreDump
                                eventName,                             -- 006: CoreDumpFound1
                                correlationId,
                                severity,
                                eventTime,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 6 }

        alarm06007 NOTIFICATION-TYPE
        OBJECTS        {        neName,
                                neType,
                                eventGroupName,                        -- 06: CoreDump
                                eventName,                             -- 007: CoreDumpFound2
                                correlationId,
                                severity,
                                eventTime,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 7 }

        alarm06008 NOTIFICATION-TYPE
        OBJECTS        {        neName,
                                neType,
                                eventGroupName,                        -- 06: CoreDump
                                eventName,                             -- 008: CoreDumpFound3
                                correlationId,
                                severity,
                                eventTime,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 8 }

        alarm06009 NOTIFICATION-TYPE
        OBJECTS        {        neName,
                                neType,
                                eventGroupName,                        -- 06: CoreDump
                                eventName,                             -- 009: CoreDumpFound4
                                correlationId,
                                severity,
                                eventTime,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 9 }

        alarm06010 NOTIFICATION-TYPE
        OBJECTS        {        neName,
                                neType,
                                eventGroupName,                        -- 06: CoreDump
                                eventName,                             -- 010: CoreDumpFound5
                                correlationId,
                                severity,
                                eventTime,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 10 }

        alarm06011 NOTIFICATION-TYPE
        OBJECTS        {        neName,
                                neType,
                                eventGroupName,                        -- 06: CoreDump
                                eventName,                             -- 011: JavaDumpFound1
                                correlationId,
                                severity,
                                eventTime,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 11 }

        alarm06012 NOTIFICATION-TYPE
        OBJECTS        {        neName,
                                neType,
                                eventGroupName,                        -- 06: CoreDump
                                eventName,                             -- 012: JavaDumpFound2
                                correlationId,
                                severity,
                                eventTime,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 12 }

        alarm06013 NOTIFICATION-TYPE
        OBJECTS        {        neName,
                                neType,
                                eventGroupName,                        -- 06: CoreDump
                                eventName,                             -- 013: JavaDumpFound3
                                correlationId,
                                severity,
                                eventTime,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 13 }

        alarm06014 NOTIFICATION-TYPE
        OBJECTS        {        neName,
                                neType,
                                eventGroupName,                        -- 06: CoreDump
                                eventName,                             -- 014: JavaDumpFound4
                                correlationId,
                                severity,
                                eventTime,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 14 }

        alarm06015 NOTIFICATION-TYPE
        OBJECTS        {        neName,
                                neType,
                                eventGroupName,                        -- 06: CoreDump
                                eventName,                             -- 015: JavaDumpFound5
                                correlationId,
                                severity,
                                eventTime,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroup06 15 }


        --********************************************************************
        -- Alarm Trap Definitions for event group 08: Security
        --********************************************************************

        alarm08001 NOTIFICATION-TYPE
        OBJECTS        {        neName,
                                neType,
                                eventGroupName,                        -- 08: Security
                                eventName,                             -- 001: PFRConfigurationFileMissing
                                correlationId,
                                severity,
                                eventTime,
                                faultyObject,
                                monitoredValue,
                                thresholdValues,
                                info   }
        STATUS                current
        DESCRIPTION        "Spontaneous Alarm from the managed network element:
                            The configuration files listed under faultyObject are missing. The packet filter rules for the firewall may not be defined properly, and/or the node's security may be impacted.
                            Log in directly to the node and check the listed files. Escalate to the next level of support, if necessary to find the root cause for the missing file."
        ::= { eventGroup08 1 }

        alarm08002 NOTIFICATION-TYPE
        OBJECTS        {        neName,
                                neType,
                                eventGroupName,                        -- 08: Security
                                eventName,                             -- 002: PFRConfigurationDataMismatch
                                correlationId,
                                severity,
                                eventTime,
                                faultyObject,
                                monitoredValue,
                                thresholdValues,
                                info   }
        STATUS                current
        DESCRIPTION        "Spontaneous Alarm from the managed network element:
                            The packet filter rules that have the names listed under faultyObject are faulty. The packet filter rules for the firewall may not be defined properly, and/or the node's security may be impacted.
                            Log in directly to the node and check the data listed in the faulty object and additional information. Escalate to the next level of support, if necessary to find the root cause for the wrong rules."
        ::= { eventGroup08 2 }

        alarm08003 NOTIFICATION-TYPE
        OBJECTS        {        neName,
                                neType,
                                eventGroupName,                        -- 08: Security
                                eventName,                             -- 003: OutgoingPacketDropped
                                correlationId,
                                severity,
                                eventTime,
                                faultyObject,
                                monitoredValue,
                                thresholdValues,
                                info   }
        STATUS                current
        DESCRIPTION        "Spontaneous Alarm from the managed network element:
                            The node firewall has dropped outgoing IP packets and the number of dropped packets per minute has crossed a threshold. Dropping a packet may be:

(*) valid
(*) A SW error causing invalid packets to be sent
(*) A misconfigured node packet filter rule
(*) indicate a virus.
                            Use the mgmt node debug file collection function to upload debug files from the node that reported the alarm.

Analyze the dropped packets stored in the firewall log file to determine whether the IMP node sends invalid packets. If the packets are sent by valid IMP software escalate to development to either correct the packet filter rules or to modify the IMP SW not to send these packets.

If not, escalate to the next level of service to investigate whether there is a SW virus."
        ::= { eventGroup08 3 }

        alarm08004 NOTIFICATION-TYPE
        OBJECTS        {        neName,
                                neType,
                                eventGroupName,                        -- 08: Security
                                eventName,                             -- 004: IncomingPacketDropped
                                correlationId,
                                severity,
                                eventTime,
                                faultyObject,
                                monitoredValue,
                                thresholdValues,
                                info   }
        STATUS                current
        DESCRIPTION        "Spontaneous Alarm from the managed network element:
                            The node firewall has dropped incoming IP packets and the number of dropped packets per minute has crossed a threshold. Dropping a packet may be:

(*) valid
(*) indicate a misconfiguration of the datacenter firewall
(*) A SW error in a partner IMP node causing invalid packets to be sent
(*) A misconfigured node packet filter rule
(*) indicate an attack.
                            Use the mgmt node debug file collection function to upload debug files from the node that reported the alarm.

Analyze the dropped packets stored in the firewall log file to determine whether the external firewall is mis-configured or whether IMP nodes send invalid packets. In the first case correct the external firewall and in latter case escalate to development to either correct the packet filter rules or to modify the IMP SW not to send these packets."
        ::= { eventGroup08 4 }

        alarm08011 NOTIFICATION-TYPE
        OBJECTS        {        neName,
                                neType,
                                eventGroupName,                        -- 08: Security
                                eventName,                             -- 011: ConfigurationFileMissing
                                correlationId,
                                severity,
                                eventTime,
                                faultyObject,
                                monitoredValue,
                                thresholdValues,
                                info   }
        STATUS                current
        DESCRIPTION        "Spontaneous Alarm from the managed network element:
                            The security files listed under faultyObject are missing. The node may not start properly, not function properly, and/or its security will be impacted.
                            Log in directly to the node and check the listed files. Escalate to the next level of support, if necessary to find the root cause for the missing file."
        ::= { eventGroup08 11 }

        alarm08012 NOTIFICATION-TYPE
        OBJECTS        {        neName,
                                neType,
                                eventGroupName,                        -- 08: Security
                                eventName,                             -- 012: ConfigurationDataMismatch
                                correlationId,
                                severity,
                                eventTime,
                                faultyObject,
                                monitoredValue,
                                thresholdValues,
                                info   }
        STATUS                current
        DESCRIPTION        "Spontaneous Alarm from the managed network element:
                            Data in the security files listed under faultyObject are wrong, missing or implausible. The node may not start properly, not function properly, and/or its security will be impacted.
                            Log in directly to the node and check the listed files. Escalate to the next level of support, if necessary to find the root cause for the wrong data."
        ::= { eventGroup08 12 }

        alarm08013 NOTIFICATION-TYPE
        OBJECTS        {        neName,
                                neType,
                                eventGroupName,                        -- 08: Security
                                eventName,                             -- 013: FilePermissionsError
                                correlationId,
                                severity,
                                eventTime,
                                faultyObject,
                                monitoredValue,
                                thresholdValues,
                                info   }
        STATUS                current
        DESCRIPTION        "Spontaneous Alarm from the managed network element:
                            The file permission of the listed files are incorrect.
                            Log in directly to the node and change the file permissions to the proper values."
        ::= { eventGroup08 13 }

        alarm08014 NOTIFICATION-TYPE
        OBJECTS        {        neName,
                                neType,
                                eventGroupName,                        -- 08: Security
                                eventName,                             -- 014: IPSECDataFaulty
                                correlationId,
                                severity,
                                eventTime,
                                faultyObject,
                                monitoredValue,
                                thresholdValues,
                                info   }
        STATUS                current
        DESCRIPTION        "Spontaneous Alarm from the managed network element:
                            IPSEC is not configured properly.
                            Escalate to SW development."
        ::= { eventGroup08 14 }

        alarm08015 NOTIFICATION-TYPE
        OBJECTS        {        neName,
                                neType,
                                eventGroupName,                        -- 08: Security
                                eventName,                             -- 015: UserKeyMismatch
                                correlationId,
                                severity,
                                eventTime,
                                faultyObject,
                                monitoredValue,
                                thresholdValues,
                                info   }
        STATUS                current
        DESCRIPTION        "Spontaneous Alarm from the managed network element:
                            User keys do not match.
                            Escalate to SW development."
        ::= { eventGroup08 15 }

        alarm08021 NOTIFICATION-TYPE
        OBJECTS        {        neName,
                                neType,
                                eventGroupName,                        -- 08: Security
                                eventName,                             -- 021: UserAccountDisabled
                                correlationId,
                                severity,
                                eventTime,
                                faultyObject,
                                monitoredValue,
                                thresholdValues,
                                info   }
        STATUS                current
        DESCRIPTION        "Spontaneous Alarm from the managed network element:
                            The specified user accounts are disabled.
                            Review the disabled accounts and either enable or delete them."
        ::= { eventGroup08 21 }

        alarm08022 NOTIFICATION-TYPE
        OBJECTS        {        neName,
                                neType,
                                eventGroupName,                        -- 08: Security
                                eventName,                             -- 022: SystemAccountDisabled
                                correlationId,
                                severity,
                                eventTime,
                                faultyObject,
                                monitoredValue,
                                thresholdValues,
                                info   }
        STATUS                current
        DESCRIPTION        "Spontaneous Alarm from the managed network element:
                            The specified system accounts are disabled.
                            Review the disabled accounts and either enable or delete them.

If all system accounts are disabled and login to the node is not possible, use cloud/hypervisor tools to access the console and use the root account.
A last correction is to terminate the VM and re-launch it."
        ::= { eventGroup08 22 }

        alarm08023 NOTIFICATION-TYPE
        OBJECTS        {        neName,
                                neType,
                                eventGroupName,                        -- 08: Security
                                eventName,                             -- 023: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup08 23 }

        alarm08024 NOTIFICATION-TYPE
        OBJECTS        {        neName,
                                neType,
                                eventGroupName,                        -- 08: Security
                                eventName,                             -- 024: PasswordExpired
                                correlationId,
                                severity,
                                eventTime,
                                faultyObject,
                                monitoredValue,
                                thresholdValues,
                                info   }
        STATUS                current
        DESCRIPTION        "Spontaneous Alarm from the managed network element:
                            The password for the specified accounts has expired.
                            Delete the accounts or change the password."
        ::= { eventGroup08 24 }

        alarm08041 NOTIFICATION-TYPE
        OBJECTS        {        neName,
                                neType,
                                eventGroupName,                        -- 08: Security
                                eventName,                             -- 041: FailedAuthenticationAttempt
                                correlationId,
                                severity,
                                eventTime,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroup08 41 }

        alarm08042 NOTIFICATION-TYPE
        OBJECTS        {        neName,
                                neType,
                                eventGroupName,                        -- 08: Security
                                eventName,                             -- 042: AccessDenied
                                correlationId,
                                severity,
                                eventTime,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroup08 42 }


        --********************************************************************
        -- Alarm Trap Definitions for event group 09: Resources
        --********************************************************************

        alarm09001 NOTIFICATION-TYPE
        OBJECTS        {        neName,
                                neType,
                                eventGroupName,                        -- 09: Resources
                                eventName,                             -- 001: CPU
                                correlationId,
                                severity,
                                eventTime,
                                faultyObject,
                                monitoredValue,
                                thresholdValues,
                                info   }
        STATUS                current
        DESCRIPTION        "Spontaneous Alarm from the managed network element:
                            CPU percentage usage in the last minute.
                            Check CPU usage with "top". It shows the processes that use the most CPU resource. Repair depending on the activities of the offending process(es), e.g. if they are in a loop then restart process might help."
        ::= { eventGroup09 1 }

        alarm09002 NOTIFICATION-TYPE
        OBJECTS        {        neName,
                                neType,
                                eventGroupName,                        -- 09: Resources
                                eventName,                             -- 002: RAM
                                correlationId,
                                severity,
                                eventTime,
                                faultyObject,
                                monitoredValue,
                                thresholdValues,
                                info   }
        STATUS                current
        DESCRIPTION        "Spontaneous Alarm from the managed network element:
                            RAM percentage usage in the last minute. Used Memory is defined as:
used = total - free - buffers - cached.
                            Display processes that uses large amount of RAM with "top" (Enter "top" then Shift+f then n then Enter key). Processes that uses unreasonable large RAM may have a memory leak. If no process shows unreasonable larger RAM usage, additional RAM should be added to the system."
        ::= { eventGroup09 2 }

        alarm09003 NOTIFICATION-TYPE
        OBJECTS        {        neName,
                                neType,
                                eventGroupName,                        -- 09: Resources
                                eventName,                             -- 003: SwapFequency
                                correlationId,
                                severity,
                                eventTime,
                                faultyObject,
                                monitoredValue,
                                thresholdValues,
                                info   }
        STATUS                current
        DESCRIPTION        "Spontaneous Alarm from the managed network element:
                            Total number of pages swapped in the last minute.
                            The system is low of RAM. Do not allow intensive processes running concurrently."
        ::= { eventGroup09 3 }

        alarm09004 NOTIFICATION-TYPE
        OBJECTS        {        neName,
                                neType,
                                eventGroupName,                        -- 09: Resources
                                eventName,                             -- 004: DiskPartitionSwap
                                correlationId,
                                severity,
                                eventTime,
                                faultyObject,
                                monitoredValue,
                                thresholdValues,
                                info   }
        STATUS                current
        DESCRIPTION        "Spontaneous Alarm from the managed network element:
                            Swap partition percentage usage.
If too high the node will reboot.
                            System may be low on memory. Check whether RAM intensive processes are/were running."
        ::= { eventGroup09 4 }

        alarm09005 NOTIFICATION-TYPE
        OBJECTS        {        neName,
                                neType,
                                eventGroupName,                        -- 09: Resources
                                eventName,                             -- 005: DiskPartitionRoot
                                correlationId,
                                severity,
                                eventTime,
                                faultyObject,
                                monitoredValue,
                                thresholdValues,
                                info   }
        STATUS                current
        DESCRIPTION        "Spontaneous Alarm from the managed network element:
                            Root (/) partition percentage usage.
If too high the node will reboot.
                            Delete unused files."
        ::= { eventGroup09 5 }

        alarm09006 NOTIFICATION-TYPE
        OBJECTS        {        neName,
                                neType,
                                eventGroupName,                        -- 09: Resources
                                eventName,                             -- 006: DiskPartitionVar
                                correlationId,
                                severity,
                                eventTime,
                                faultyObject,
                                monitoredValue,
                                thresholdValues,
                                info   }
        STATUS                current
        DESCRIPTION        "Spontaneous Alarm from the managed network element:
                            /var partition percentage usage.
                            Delete unused files."
        ::= { eventGroup09 6 }

        alarm09007 NOTIFICATION-TYPE
        OBJECTS        {        neName,
                                neType,
                                eventGroupName,                        -- 09: Resources
                                eventName,                             -- 007: DiskPartitionDb
                                correlationId,
                                severity,
                                eventTime,
                                faultyObject,
                                monitoredValue,
                                thresholdValues,
                                info   }
        STATUS                current
        DESCRIPTION        "Spontaneous Alarm from the managed network element:
                            /db partition percentage usage.
                            Delete unused files."
        ::= { eventGroup09 7 }

        alarm09008 NOTIFICATION-TYPE
        OBJECTS        {        neName,
                                neType,
                                eventGroupName,                        -- 09: Resources
                                eventName,                             -- 008: DiskPartitionTmp
                                correlationId,
                                severity,
                                eventTime,
                                faultyObject,
                                monitoredValue,
                                thresholdValues,
                                info   }
        STATUS                current
        DESCRIPTION        "Spontaneous Alarm from the managed network element:
                            /tmp partition percentage usage.
If too high the node will reboot.
                            Delete unused files (check if wireshark is using up /tmp)."
        ::= { eventGroup09 8 }

        alarm09009 NOTIFICATION-TYPE
        OBJECTS        {        neName,
                                neType,
                                eventGroupName,                        -- 09: Resources
                                eventName,                             -- 009: DiskPartitionShared
                                correlationId,
                                severity,
                                eventTime,
                                faultyObject,
                                monitoredValue,
                                thresholdValues,
                                info   }
        STATUS                current
        DESCRIPTION        "Spontaneous Alarm from the managed network element:
                            The remote shared storage of the operations node has crossed a fill level threshold. Once full log files cannot be stored anymore and analysis of instrumentation data cannot be performed anymore.
                            Check whether amount and content of stored data is justified. If yes, increase storage space. If not, delete files from storage and escalate the issue to development to check for SW errors."
        ::= { eventGroup09 9 }

        alarm09011 NOTIFICATION-TYPE
        OBJECTS        {        neName,
                                neType,
                                eventGroupName,                        -- 09: Resources
                                eventName,                             -- 011: LogDirectory
                                correlationId,
                                severity,
                                eventTime,
                                faultyObject,
                                monitoredValue,
                                thresholdValues,
                                info   }
        STATUS                current
        DESCRIPTION        "Spontaneous Alarm from the managed network element:
                            Total space usage (GB) of /var/log partition.
                            Delete unused files."
        ::= { eventGroup09 11 }

        alarm09012 NOTIFICATION-TYPE
        OBJECTS        {        neName,
                                neType,
                                eventGroupName,                        -- 09: Resources
                                eventName,                             -- 012: CoreDirectory
                                correlationId,
                                severity,
                                eventTime,
                                faultyObject,
                                monitoredValue,
                                thresholdValues,
                                info   }
        STATUS                current
        DESCRIPTION        "Spontaneous Alarm from the managed network element:
                            Total space usage (GB) of /var/cores partition.
                            Delete unused files."
        ::= { eventGroup09 12 }

        alarm09031 NOTIFICATION-TYPE
        OBJECTS        {        neName,
                                neType,
                                eventGroupName,                        -- 09: Resources
                                eventName,                             -- 031: BandwidthOAMP
                                correlationId,
                                severity,
                                eventTime,
                                faultyObject,
                                monitoredValue,
                                thresholdValues,
                                info   }
        STATUS                current
        DESCRIPTION        "Spontaneous Alarm from the managed network element:
                            Bandwidth OAMP Average transmitted Mbit/s of the last minute.
                            Verify if the number is justified for this interface."
        ::= { eventGroup09 31 }

        alarm09032 NOTIFICATION-TYPE
        OBJECTS        {        neName,
                                neType,
                                eventGroupName,                        -- 09: Resources
                                eventName,                             -- 032: BandwidthApp
                                correlationId,
                                severity,
                                eventTime,
                                faultyObject,
                                monitoredValue,
                                thresholdValues,
                                info   }
        STATUS                current
        DESCRIPTION        "Spontaneous Alarm from the managed network element:
                            Bandwidth App Average transmitted Mbit/s of the last minute.
                            Verify if the number is justified for this interface."
        ::= { eventGroup09 32 }

        alarm09033 NOTIFICATION-TYPE
        OBJECTS        {        neName,
                                neType,
                                eventGroupName,                        -- 09: Resources
                                eventName,                             -- 033: BandwidthExt
                                correlationId,
                                severity,
                                eventTime,
                                faultyObject,
                                monitoredValue,
                                thresholdValues,
                                info   }
        STATUS                current
        DESCRIPTION        "Spontaneous Alarm from the managed network element:
                            Bandwidth Ext Average transmitted Mbit/s of the last minute.
                            Verify if the number is justified for this interface."
        ::= { eventGroup09 33 }


        --********************************************************************
        -- Alarm Trap Definitions for event group 10: Network
        --********************************************************************

        alarm10001 NOTIFICATION-TYPE
        OBJECTS        {        neName,
                                neType,
                                eventGroupName,                        -- 10: Network
                                eventName,                             -- 001: RouterOAMP
                                correlationId,
                                severity,
                                eventTime,
                                faultyObject,
                                monitoredValue,
                                thresholdValues,
                                info   }
        STATUS                current
        DESCRIPTION        "Spontaneous Alarm from the managed network element:
                            The OAMP network router is not available as it is not responding to ARP requests which it had previously.
                            Check OAMP network. Is the router available? Is the IP address correct?"
        ::= { eventGroup10 1 }

        alarm10002 NOTIFICATION-TYPE
        OBJECTS        {        neName,
                                neType,
                                eventGroupName,                        -- 10: Network
                                eventName,                             -- 002: RouterApp
                                correlationId,
                                severity,
                                eventTime,
                                faultyObject,
                                monitoredValue,
                                thresholdValues,
                                info   }
        STATUS                current
        DESCRIPTION        "Spontaneous Alarm from the managed network element:
                            The application network router is not available as it is not responding to ARP requests which it had previously.
                            Check application network. Is the router available? Is the IP address correct?"
        ::= { eventGroup10 2 }

        alarm10003 NOTIFICATION-TYPE
        OBJECTS        {        neName,
                                neType,
                                eventGroupName,                        -- 10: Network
                                eventName,                             -- 003: RouterExt
                                correlationId,
                                severity,
                                eventTime,
                                faultyObject,
                                monitoredValue,
                                thresholdValues,
                                info   }
        STATUS                current
        DESCRIPTION        "Spontaneous Alarm from the managed network element:
                            The external network router is not available as it is not responding to ARP requests which it had previously.
                            Check external network. Is the router available? Is the IP address correct?"
        ::= { eventGroup10 3 }

        alarm10004 NOTIFICATION-TYPE
        OBJECTS        {        neName,
                                neType,
                                eventGroupName,                        -- 10: Network
                                eventName,                             -- 004: DNS
                                correlationId,
                                severity,
                                eventTime,
                                faultyObject,
                                monitoredValue,
                                thresholdValues,
                                info   }
        STATUS                current
        DESCRIPTION        "Spontaneous Alarm from the managed network element:
                            A DNS server is not available as it is not responding to ARP requests which it had previously.
                            Check network. Is the DNS available? Is the IP address correct? Is the DNS reachable via the OAMP network?"
        ::= { eventGroup10 4 }

        alarm10005 NOTIFICATION-TYPE
        OBJECTS        {        neName,
                                neType,
                                eventGroupName,                        -- 10: Network
                                eventName,                             -- 005: NTPLossOfCommunication
                                correlationId,
                                severity,
                                eventTime,
                                faultyObject,
                                monitoredValue,
                                thresholdValues,
                                info   }
        STATUS                current
        DESCRIPTION        "Spontaneous Alarm from the managed network element:
                            The reporting node cannot communicate with the NTP server(s) listed in the faultyObject.
                            The command 'ntpq -pn' can be used to show the status of the NTP server. Most communication alarms will be cleared automatically when communication is restored with the partner. If the problem causing the communication failure cannot be determined and corrected, provide Ethereal/Wireshark trace files obtained from both the reporting node as well as the communication partner in order to help determine the point of failure."
        ::= { eventGroup10 5 }

        alarm10006 NOTIFICATION-TYPE
        OBJECTS        {        neName,
                                neType,
                                eventGroupName,                        -- 10: Network
                                eventName,                             -- 006: NTPSynchronizationFailure
                                correlationId,
                                severity,
                                eventTime,
                                faultyObject,
                                monitoredValue,
                                thresholdValues,
                                info   }
        STATUS                current
        DESCRIPTION        "Spontaneous Alarm from the managed network element:
                            The reporting node cannot synchronize the system clock with any NTP server.
                             The command 'ntpq -pn' can be used to show the status of the NTP server. Verify that the list of NTP servers is correct and analyze the command output to determine why the node could not synchronize with any listed server."
        ::= { eventGroup10 6 }

        alarm10007 NOTIFICATION-TYPE
        OBJECTS        {        neName,
                                neType,
                                eventGroupName,                        -- 10: Network
                                eventName,                             -- 007: NTPDaemonFailure
                                correlationId,
                                severity,
                                eventTime,
                                faultyObject,
                                monitoredValue,
                                thresholdValues,
                                info   }
        STATUS                current
        DESCRIPTION        "Spontaneous Alarm from the managed network element:
                            The reporting node could not execute the ntpq -pn command. This is likely because the NTP daemon is inactive.
                             Review /var/log/messages for ntp messages and determine why the daemon exited. Execute the command 'plat_pmc show .' verify that the ntp process is not blocked. If it is, execute 'plat_pmc start ntp'."
        ::= { eventGroup10 7 }

        alarm10008 NOTIFICATION-TYPE
        OBJECTS        {        neName,
                                neType,
                                eventGroupName,                        -- 10: Network
                                eventName,                             -- 008: eth0LinkDown
                                correlationId,
                                severity,
                                eventTime,
                                faultyObject,
                                monitoredValue,
                                thresholdValues,
                                info   }
        STATUS                current
        DESCRIPTION        "Spontaneous Alarm from the managed network element:
                            The Ethernet interface eth0 is inactive.
                            On a Virtual Machine, configure the Ethernet interface to connect to a valid port/switch. On physical hardware verify physical connectivity between the specified Ethernet port and the adjacent networking device."
        ::= { eventGroup10 8 }

        alarm10009 NOTIFICATION-TYPE
        OBJECTS        {        neName,
                                neType,
                                eventGroupName,                        -- 10: Network
                                eventName,                             -- 009: eth1LinkDown
                                correlationId,
                                severity,
                                eventTime,
                                faultyObject,
                                monitoredValue,
                                thresholdValues,
                                info   }
        STATUS                current
        DESCRIPTION        "Spontaneous Alarm from the managed network element:
                            The Ethernet interface eth1 is inactive.
                            On a Virtual Machine, configure the Ethernet interface to connect to a valid port/switch. On physical hardware verify physical connectivity between the specified Ethernet port and the adjacent networking device."
        ::= { eventGroup10 9 }

        alarm10010 NOTIFICATION-TYPE
        OBJECTS        {        neName,
                                neType,
                                eventGroupName,                        -- 10: Network
                                eventName,                             -- 010: eth2LinkDown
                                correlationId,
                                severity,
                                eventTime,
                                faultyObject,
                                monitoredValue,
                                thresholdValues,
                                info   }
        STATUS                current
        DESCRIPTION        "Spontaneous Alarm from the managed network element:
                            The Ethernet interface eth2 is inactive.
                            On a Virtual Machine, configure the Ethernet interface to connect to a valid port/switch. On physical hardware verify physical connectivity between the specified Ethernet port and the adjacent networking device."
        ::= { eventGroup10 10 }

        alarm10011 NOTIFICATION-TYPE
        OBJECTS        {        neName,
                                neType,
                                eventGroupName,                        -- 10: Network
                                eventName,                             -- 011: HardwareClockOffset
                                correlationId,
                                severity,
                                eventTime,
                                faultyObject,
                                monitoredValue,
                                thresholdValues,
                                info   }
        STATUS                current
        DESCRIPTION        "Spontaneous Alarm from the managed network element:
                            The system time and the time from the hardware clock are different by the specified number of seconds.
                            Follow the documented procedures for changing the time."
        ::= { eventGroup10 11 }

        alarm10012 NOTIFICATION-TYPE
        OBJECTS        {        neName,
                                neType,
                                eventGroupName,                        -- 10: Network
                                eventName,                             -- 012: DNS1Response
                                correlationId,
                                severity,
                                eventTime,
                                faultyObject,
                                monitoredValue,
                                thresholdValues,
                                info   }
        STATUS                current
        DESCRIPTION        "Spontaneous Alarm from the managed network element:
                            Response time from DNS1 is greater than one of the alarm thresolds.
                            Check network."
        ::= { eventGroup10 12 }

        alarm10013 NOTIFICATION-TYPE
        OBJECTS        {        neName,
                                neType,
                                eventGroupName,                        -- 10: Network
                                eventName,                             -- 013: DNS1Resolver
                                correlationId,
                                severity,
                                eventTime,
                                faultyObject,
                                monitoredValue,
                                thresholdValues,
                                info   }
        STATUS                current
        DESCRIPTION        "Spontaneous Alarm from the managed network element:
                            FQDNs could not be resolved.
                            Check FQDNs that failed to be resolved."
        ::= { eventGroup10 13 }

        alarm10014 NOTIFICATION-TYPE
        OBJECTS        {        neName,
                                neType,
                                eventGroupName,                        -- 10: Network
                                eventName,                             -- 014: DNS2Response
                                correlationId,
                                severity,
                                eventTime,
                                faultyObject,
                                monitoredValue,
                                thresholdValues,
                                info   }
        STATUS                current
        DESCRIPTION        "Spontaneous Alarm from the managed network element:
                            Response time from DNS2 is greater than one of the alarm thresolds.
                            Check network."
        ::= { eventGroup10 14 }

        alarm10015 NOTIFICATION-TYPE
        OBJECTS        {        neName,
                                neType,
                                eventGroupName,                        -- 10: Network
                                eventName,                             -- 015: DNS2Resolver
                                correlationId,
                                severity,
                                eventTime,
                                faultyObject,
                                monitoredValue,
                                thresholdValues,
                                info   }
        STATUS                current
        DESCRIPTION        "Spontaneous Alarm from the managed network element:
                            FQDNs could not be resolved.
                            Check FQDNs that failed to be resolved."
        ::= { eventGroup10 15 }


        --********************************************************************
        -- Alarm Trap Definitions for event group 12: RapidStat
        --********************************************************************

        alarm12001 NOTIFICATION-TYPE
        OBJECTS        {        neName,
                                neType,
                                eventGroupName,                        -- 12: RapidStat
                                eventName,                             -- 001: HwClockNotSetToUTC
                                correlationId,
                                severity,
                                eventTime,
                                faultyObject,
                                monitoredValue,
                                thresholdValues,
                                info   }
        STATUS                current
        DESCRIPTION        "Spontaneous Alarm from the managed network element:
                            HW clock is not set to UTC.
                            Verify that the non UTC setting is required. If not, set it back to UTC."
        ::= { eventGroup12 1 }

        alarm12002 NOTIFICATION-TYPE
        OBJECTS        {        neName,
                                neType,
                                eventGroupName,                        -- 12: RapidStat
                                eventName,                             -- 002: DNSrespTime
                                correlationId,
                                severity,
                                eventTime,
                                faultyObject,
                                monitoredValue,
                                thresholdValues,
                                info   }
        STATUS                current
        DESCRIPTION        "Spontaneous Alarm from the managed network element:
                            DNS response time was longer than threshold.
                            Check network."
        ::= { eventGroup12 2 }

        alarm12003 NOTIFICATION-TYPE
        OBJECTS        {        neName,
                                neType,
                                eventGroupName,                        -- 12: RapidStat
                                eventName,                             -- 003: MailSize
                                correlationId,
                                severity,
                                eventTime,
                                faultyObject,
                                monitoredValue,
                                thresholdValues,
                                info   }
        STATUS                current
        DESCRIPTION        "Spontaneous Alarm from the managed network element:
                            There are large files in /var/mail.
                            Delete the files."
        ::= { eventGroup12 3 }

        alarm12004 NOTIFICATION-TYPE
        OBJECTS        {        neName,
                                neType,
                                eventGroupName,                        -- 12: RapidStat
                                eventName,                             -- 004: etcVsNodecfg
                                correlationId,
                                severity,
                                eventTime,
                                faultyObject,
                                monitoredValue,
                                thresholdValues,
                                info   }
        STATUS                current
        DESCRIPTION        "Spontaneous Alarm from the managed network element:
                            There are mismatched values between /etc/hosts and /etc/.xml files.
                            Escalate to next level of support."
        ::= { eventGroup12 4 }

        alarm12005 NOTIFICATION-TYPE
        OBJECTS        {        neName,
                                neType,
                                eventGroupName,                        -- 12: RapidStat
                                eventName,                             -- 005: ntpresolv
                                correlationId,
                                severity,
                                eventTime,
                                faultyObject,
                                monitoredValue,
                                thresholdValues,
                                info   }
        STATUS                current
        DESCRIPTION        "Spontaneous Alarm from the managed network element:
                            System time not synchronized with any NTP server.
                            See repair text for NTP alarms."
        ::= { eventGroup12 5 }

        alarm12006 NOTIFICATION-TYPE
        OBJECTS        {        neName,
                                neType,
                                eventGroupName,                        -- 12: RapidStat
                                eventName,                             -- 006: ActAlrms
                                correlationId,
                                severity,
                                eventTime,
                                faultyObject,
                                monitoredValue,
                                thresholdValues,
                                info   }
        STATUS                current
        DESCRIPTION        "Spontaneous Alarm from the managed network element:
                            There are active alarms on the system.
                            Correct the problems reported in the active alarms. If the alarm does not clear automatically delete it manually."
        ::= { eventGroup12 6 }

        alarm12007 NOTIFICATION-TYPE
        OBJECTS        {        neName,
                                neType,
                                eventGroupName,                        -- 12: RapidStat
                                eventName,                             -- 007: Num_pstacks
                                correlationId,
                                severity,
                                eventTime,
                                faultyObject,
                                monitoredValue,
                                thresholdValues,
                                info   }
        STATUS                current
        DESCRIPTION        "Spontaneous Alarm from the managed network element:
                            Pstacks found.
                            See repair text of pstack alarms."
        ::= { eventGroup12 7 }

        alarm12008 NOTIFICATION-TYPE
        OBJECTS        {        neName,
                                neType,
                                eventGroupName,                        -- 12: RapidStat
                                eventName,                             -- 008: TracingOn
                                correlationId,
                                severity,
                                eventTime,
                                faultyObject,
                                monitoredValue,
                                thresholdValues,
                                info   }
        STATUS                current
        DESCRIPTION        "Spontaneous Alarm from the managed network element:
                            Found active tracing.
                            Verify that tracing is still needed. If not stop tracing."
        ::= { eventGroup12 8 }


        --********************************************************************
        -- Alarm Trap Definitions for event group 13: Logging
        --********************************************************************

        alarm13001 NOTIFICATION-TYPE
        OBJECTS        {        neName,
                                neType,
                                eventGroupName,                        -- 13: Logging
                                eventName,                             -- 001: DeletedOpenFile
                                correlationId,
                                severity,
                                eventTime,
                                faultyObject,
                                monitoredValue,
                                thresholdValues,
                                info   }
        STATUS                current
        DESCRIPTION        "Spontaneous Alarm from the managed network element:
                            A large deleted file has been detected that is still open. The associated process will be restarted. The faultyObject parameter shows file name and associated process.
                            If this happens often, escalate the alarm to development for analysis. The alarm is automatically removed after a couple of hours."
        ::= { eventGroup13 1 }


        --********************************************************************
        -- Alarm Trap Definitions for event group 14: LogTCA
        --********************************************************************

        alarm14001 NOTIFICATION-TYPE
        OBJECTS        {        neName,
                                neType,
                                eventGroupName,                        -- 14: LogTCA
                                eventName,                             -- 001: Platform
                                correlationId,
                                severity,
                                eventTime,
                                faultyObject,
                                monitoredValue,
                                thresholdValues,
                                info   }
        STATUS                current
        DESCRIPTION        "Spontaneous Alarm from the managed network element:
                            The number of events has crossed one of the thresholds within the last 15 minutes for the category PLATFORM. See log file /var/log/platform/logging/LogNonIssues.log.
                            Review log file entries to determine source of problem."
        ::= { eventGroup14 1 }

        alarm14002 NOTIFICATION-TYPE
        OBJECTS        {        neName,
                                neType,
                                eventGroupName,                        -- 14: LogTCA
                                eventName,                             -- 002: Platform_Err
                                correlationId,
                                severity,
                                eventTime,
                                faultyObject,
                                monitoredValue,
                                thresholdValues,
                                info   }
        STATUS                current
        DESCRIPTION        "Spontaneous Alarm from the managed network element:
                            The number of events has crossed one of the thresholds within the last 15 minutes for the category PLATFORM_ERR. See log file /var/log/platform/logging/LogIssues.log.
                            Review log file entries to determine source of problem."
        ::= { eventGroup14 2 }

        alarm14003 NOTIFICATION-TYPE
        OBJECTS        {        neName,
                                neType,
                                eventGroupName,                        -- 14: LogTCA
                                eventName,                             -- 003: Audit
                                correlationId,
                                severity,
                                eventTime,
                                faultyObject,
                                monitoredValue,
                                thresholdValues,
                                info   }
        STATUS                current
        DESCRIPTION        "Spontaneous Alarm from the managed network element:
                            The number of events has crossed one of the thresholds within the last 15 minutes for the category AUDIT. See log file /var/log/platform/logging/LogNonIssues.log.
                            Review log file entries to determine source of problem."
        ::= { eventGroup14 3 }

        alarm14004 NOTIFICATION-TYPE
        OBJECTS        {        neName,
                                neType,
                                eventGroupName,                        -- 14: LogTCA
                                eventName,                             -- 004: Audit_Err
                                correlationId,
                                severity,
                                eventTime,
                                faultyObject,
                                monitoredValue,
                                thresholdValues,
                                info   }
        STATUS                current
        DESCRIPTION        "Spontaneous Alarm from the managed network element:
                            The number of events has crossed one of the thresholds within the last 15 minutes for the category AUDIT_ERR. See log file /var/log/platform/logging/LogIssues.log.
                            Review log file entries to determine source of problem."
        ::= { eventGroup14 4 }

        alarm14005 NOTIFICATION-TYPE
        OBJECTS        {        neName,
                                neType,
                                eventGroupName,                        -- 14: LogTCA
                                eventName,                             -- 005: Com_Err
                                correlationId,
                                severity,
                                eventTime,
                                faultyObject,
                                monitoredValue,
                                thresholdValues,
                                info   }
        STATUS                current
        DESCRIPTION        "Spontaneous Alarm from the managed network element:
                            The number of events has crossed one of the thresholds within the last 15 minutes for the category COM_ERR. See log file /var/log/platform/logging/LogIssues.log.
                            Review log file entries to determine source of problem."
        ::= { eventGroup14 5 }

        alarm14006 NOTIFICATION-TYPE
        OBJECTS        {        neName,
                                neType,
                                eventGroupName,                        -- 14: LogTCA
                                eventName,                             -- 006: SW_Err
                                correlationId,
                                severity,
                                eventTime,
                                faultyObject,
                                monitoredValue,
                                thresholdValues,
                                info   }
        STATUS                current
        DESCRIPTION        "Spontaneous Alarm from the managed network element:
                            The number of events has crossed one of the thresholds within the last 15 minutes for the category SW_ERR. See log file /var/log/platform/logging/LogIssues.log.
                            Review log file entries to determine source of problem."
        ::= { eventGroup14 6 }

        alarm14007 NOTIFICATION-TYPE
        OBJECTS        {        neName,
                                neType,
                                eventGroupName,                        -- 14: LogTCA
                                eventName,                             -- 007: Data_Err
                                correlationId,
                                severity,
                                eventTime,
                                faultyObject,
                                monitoredValue,
                                thresholdValues,
                                info   }
        STATUS                current
        DESCRIPTION        "Spontaneous Alarm from the managed network element:
                            The number of events has crossed one of the thresholds within the last 15 minutes for the category DATA_ERR. See log file /var/log/platform/logging/LogIssues.log.
                            Review log file entries to determine source of problem."
        ::= { eventGroup14 7 }

        alarm14008 NOTIFICATION-TYPE
        OBJECTS        {        neName,
                                neType,
                                eventGroupName,                        -- 14: LogTCA
                                eventName,                             -- 008: Alarm
                                correlationId,
                                severity,
                                eventTime,
                                faultyObject,
                                monitoredValue,
                                thresholdValues,
                                info   }
        STATUS                current
        DESCRIPTION        "Spontaneous Alarm from the managed network element:
                            The number of events has crossed one of the thresholds within the last 15 minutes for the category ALARM. See log file /var/log/platform/logging/LogAlarm.log.
                            Review log file entries to determine source of problem."
        ::= { eventGroup14 8 }

        alarm14009 NOTIFICATION-TYPE
        OBJECTS        {        neName,
                                neType,
                                eventGroupName,                        -- 14: LogTCA
                                eventName,                             -- 009: Alarm_Clear
                                correlationId,
                                severity,
                                eventTime,
                                faultyObject,
                                monitoredValue,
                                thresholdValues,
                                info   }
        STATUS                current
        DESCRIPTION        "Spontaneous Alarm from the managed network element:
                            The number of events has crossed one of the thresholds within the last 15 minutes for the category ALARM_CLEAR. See log file /var/log/platform/logging/LogAlarm.log.
                            Review log file entries to determine source of problem."
        ::= { eventGroup14 9 }

        alarm14010 NOTIFICATION-TYPE
        OBJECTS        {        neName,
                                neType,
                                eventGroupName,                        -- 14: LogTCA
                                eventName,                             -- 010: Alarm_Mgr
                                correlationId,
                                severity,
                                eventTime,
                                faultyObject,
                                monitoredValue,
                                thresholdValues,
                                info   }
        STATUS                current
        DESCRIPTION        "Spontaneous Alarm from the managed network element:
                            The number of events has crossed one of the thresholds within the last 15 minutes for the category ALARM_MGR. See log file /var/log/platform/logging/LogAlarm.log.
                            Review log file entries to determine source of problem."
        ::= { eventGroup14 10 }


        --********************************************************************
        -- Alarm Trap Definitions for event group 17: SNMPTrap
        --********************************************************************

        alarm17001 NOTIFICATION-TYPE
        OBJECTS        {        neName,
                                neType,
                                eventGroupName,                        -- 17: SNMPTrap
                                eventName,                             -- 001: SnmpOpenFailure
                                correlationId,
                                severity,
                                eventTime,
                                faultyObject,
                                monitoredValue,
                                thresholdValues,
                                info   }
        STATUS                current
        DESCRIPTION        "Spontaneous Alarm from the managed network element:
                            Call to snmp_open failed.
                            Look at faulty object and correct accordingly (if possible)."
        ::= { eventGroup17 1 }

        alarm17002 NOTIFICATION-TYPE
        OBJECTS        {        neName,
                                neType,
                                eventGroupName,                        -- 17: SNMPTrap
                                eventName,                             -- 002: SnmpSendFailure
                                correlationId,
                                severity,
                                eventTime,
                                faultyObject,
                                monitoredValue,
                                thresholdValues,
                                info   }
        STATUS                current
        DESCRIPTION        "Spontaneous Alarm from the managed network element:
                            Call to snmp_synch_response failed.
                            Look at faulty object and correct accordingly (if possible)."
        ::= { eventGroup17 2 }


        --********************************************************************
        -- Alarm Trap Definitions for event group 20: Zoo
        --********************************************************************

        alarm20001 NOTIFICATION-TYPE
        OBJECTS        {        neName,
                                neType,
                                eventGroupName,                        -- 20: Zoo
                                eventName,                             -- 001: ZooConnectionFailure
                                correlationId,
                                severity,
                                eventTime,
                                faultyObject,
                                monitoredValue,
                                thresholdValues,
                                info   }
        STATUS                current
        DESCRIPTION        "Spontaneous Alarm from the managed network element:
                            A connection from the platform ZooKeeper Client to a ZooKeeper server could not be established. A quorum of ZooKeeper servers may not be active or may be misconfigured. The ZooKeeper client on the platform may not have a valid configuration. Network failures can also cause this alarm.
                            Ping the ZooKeeper servers from the reporting node to determine if a network problem exists. Verify that a quorum of ZooKeeper servers is active (e.g. at least two servers are active in a three-zookeeper-node ensemble). Verify that the reporting node was deployed correctly and has received the correct configuration in the 'goahead' message. If problem persists, execute 'plat_rapidstat -c' to collect data on the reporting node, all of the ZooKeeper servers."
        ::= { eventGroup20 1 }

        alarm20002 NOTIFICATION-TYPE
        OBJECTS        {        neName,
                                neType,
                                eventGroupName,                        -- 20: Zoo
                                eventName,                             -- 002: ZooConfigCorrupted
                                correlationId,
                                severity,
                                eventTime,
                                faultyObject,
                                monitoredValue,
                                thresholdValues,
                                info   }
        STATUS                current
        DESCRIPTION        "Spontaneous Alarm from the managed network element:
                            Configuration retrieved via ZooKeeper server was corrupt and cannot be parsed.
                            The ZooKeeper znodes that are corrupt are listed with the alarm. Use the Management node application to correct the node configuration. If problem persists, execute 'plat_rapidstat -c' to collect data on the reporting node, Management node, and one of the active ZooKeeper servers."
        ::= { eventGroup20 2 }

        alarm20003 NOTIFICATION-TYPE
        OBJECTS        {        neName,
                                neType,
                                eventGroupName,                        -- 20: Zoo
                                eventName,                             -- 003: ZooConfigUnavailable
                                correlationId,
                                severity,
                                eventTime,
                                faultyObject,
                                monitoredValue,
                                thresholdValues,
                                info   }
        STATUS                current
        DESCRIPTION        "Spontaneous Alarm from the managed network element:
                            Configuration could not be retrieved from a ZooKeeper server.
                            The ZooKeeper znodes that could not be retrieved are listed with the alarm. If data has not been populated on the ZooKeeper servers, use the Management node to configure and populate the data. If problem persists, execute 'plat_rapidstat -c' to collect data on the reporting node as well as one of the active ZooKeeper servers."
        ::= { eventGroup20 3 }

        alarm20004 NOTIFICATION-TYPE
        OBJECTS        {        neName,
                                neType,
                                eventGroupName,                        -- 20: Zoo
                                eventName,                             -- 004: ZookeeperResponseTime
                                correlationId,
                                severity,
                                eventTime,
                                faultyObject,
                                monitoredValue,
                                thresholdValues,
                                info   }
        STATUS                current
        DESCRIPTION        "Spontaneous Alarm from the managed network element:
                            A ZooKeeper server did not respond to a request from the client within the expected response time.
                            The problem could be caused by network problems or by an overloaded ZooKeeper server. If problem persists, execute 'plat_rapidstat -c' to collection data on the reporting node and on each active ZooKeeper server node."
        ::= { eventGroup20 4 }

        alarm20005 NOTIFICATION-TYPE
        OBJECTS        {        neName,
                                neType,
                                eventGroupName,                        -- 20: Zoo
                                eventName,                             -- 005: WrongNodeTypeInGoAhead
                                correlationId,
                                severity,
                                eventTime,
                                faultyObject,
                                monitoredValue,
                                thresholdValues,
                                info   }
        STATUS                current
        DESCRIPTION        "Spontaneous Alarm from the managed network element:
                            The node name received in the GoAhead configuration does not match the node type set by production in the file /etc/platform/type.
                            If the GoAhead was sent to this node in error, send the correct GoAhead to this node. If the node was deployed with the wrong OVF/OVA, redeploy with the correct one and re-send the GoAhead."
        ::= { eventGroup20 5 }


        --********************************************************************
        -- Alarm Trap Definitions for event group 21: IDS
        --********************************************************************

        alarm21001 NOTIFICATION-TYPE
        OBJECTS        {        neName,
                                neType,
                                eventGroupName,                        -- 21: IDS
                                eventName,                             -- 001: DoS
                                correlationId,
                                severity,
                                eventTime,
                                faultyObject,
                                monitoredValue,
                                thresholdValues,
                                info   }
        STATUS                current
        DESCRIPTION        "Spontaneous Alarm from the managed network element:
                            Denial Of Service Attempt Detected.
                            None."
        ::= { eventGroup21 1 }


        --********************************************************************
        -- Alarm Trap Definitions for event group 22: SNMP
        --********************************************************************

        alarm22001 NOTIFICATION-TYPE
        OBJECTS        {        neName,
                                neType,
                                eventGroupName,                        -- 22: SNMP
                                eventName,                             -- 001: SnmpReconfigError
                                correlationId,
                                severity,
                                eventTime,
                                faultyObject,
                                monitoredValue,
                                thresholdValues,
                                info   }
        STATUS                current
        DESCRIPTION        "Spontaneous Alarm from the managed network element:
                            SnmpV3 Users not created successfully
                            Check if all necessary credentials for SnmpV3 Users are defined in Network.xml.If not update file."
        ::= { eventGroup22 1 }


        --********************************************************************
        -- Alarm Trap Definitions for event group 23: Syslog
        --********************************************************************

        alarm23001 NOTIFICATION-TYPE
        OBJECTS        {        neName,
                                neType,
                                eventGroupName,                        -- 23: Syslog
                                eventName,                             -- 001: Emerg
                                correlationId,
                                severity,
                                eventTime,
                                faultyObject,
                                monitoredValue,
                                thresholdValues,
                                info   }
        STATUS                current
        DESCRIPTION        "Spontaneous Alarm from the managed network element:
                            Emgergency syslog failure.
                            Look at syslog entries and correct problem."
        ::= { eventGroup23 1 }

        alarm23002 NOTIFICATION-TYPE
        OBJECTS        {        neName,
                                neType,
                                eventGroupName,                        -- 23: Syslog
                                eventName,                             -- 002: Alert
                                correlationId,
                                severity,
                                eventTime,
                                faultyObject,
                                monitoredValue,
                                thresholdValues,
                                info   }
        STATUS                current
        DESCRIPTION        "Spontaneous Alarm from the managed network element:
                            Alert syslog failure.
                            Look at syslog entries and correct problem."
        ::= { eventGroup23 2 }

        alarm23003 NOTIFICATION-TYPE
        OBJECTS        {        neName,
                                neType,
                                eventGroupName,                        -- 23: Syslog
                                eventName,                             -- 003: Crit
                                correlationId,
                                severity,
                                eventTime,
                                faultyObject,
                                monitoredValue,
                                thresholdValues,
                                info   }
        STATUS                current
        DESCRIPTION        "Spontaneous Alarm from the managed network element:
                            Critical syslog failure.
                            Look at syslog entries and correct problem."
        ::= { eventGroup23 3 }

        alarm23004 NOTIFICATION-TYPE
        OBJECTS        {        neName,
                                neType,
                                eventGroupName,                        -- 23: Syslog
                                eventName,                             -- 004: Error
                                correlationId,
                                severity,
                                eventTime,
                                faultyObject,
                                monitoredValue,
                                thresholdValues,
                                info   }
        STATUS                current
        DESCRIPTION        "Spontaneous Alarm from the managed network element:
                            Error syslog failure.
                            Look at syslog entries and correct problem."
        ::= { eventGroup23 4 }


        --********************************************************************
        -- Alarm Trap Definitions for event group 50: Connectivity
        --********************************************************************

        alarm50001 NOTIFICATION-TYPE
        OBJECTS        {        neName,
                                neType,
                                eventGroupName,                        -- 50: Connectivity
                                eventName,                             -- 001: SmartCloudConnectionFailure
                                correlationId,
                                severity,
                                eventTime,
                                faultyObject,
                                monitoredValue,
                                thresholdValues,
                                info   }
        STATUS                current
        DESCRIPTION        "Spontaneous Alarm from the managed network element:
                            Smart Cloud Connection failure.
                            Check if the Access node has internet connection and can reach the Cloud server."
        ::= { eventGroup50 1 }

        alarm50002 NOTIFICATION-TYPE
        OBJECTS        {        neName,
                                neType,
                                eventGroupName,                        -- 50: Connectivity
                                eventName,                             -- 002: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup50 2 }

        alarm50003 NOTIFICATION-TYPE
        OBJECTS        {        neName,
                                neType,
                                eventGroupName,                        -- 50: Connectivity
                                eventName,                             -- 003: FileApiSocketsUsage
                                correlationId,
                                severity,
                                eventTime,
                                faultyObject,
                                monitoredValue,
                                thresholdValues,
                                info   }
        STATUS                current
        DESCRIPTION        "Spontaneous Alarm from the managed network element:
                            The percentage of used concurrent sockets in fileApi between Access Server and IBM crossed the defined threshold.
                            Check if it is necessary to increase the number of concurrent sockets in fileApi."
        ::= { eventGroup50 3 }

        alarm50005 NOTIFICATION-TYPE
        OBJECTS        {        neName,
                                neType,
                                eventGroupName,                        -- 50: Connectivity
                                eventName,                             -- 005: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup50 5 }

        alarm50006 NOTIFICATION-TYPE
        OBJECTS        {        neName,
                                neType,
                                eventGroupName,                        -- 50: Connectivity
                                eventName,                             -- 006: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup50 6 }

        alarm50007 NOTIFICATION-TYPE
        OBJECTS        {        neName,
                                neType,
                                eventGroupName,                        -- 50: Connectivity
                                eventName,                             -- 007: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup50 7 }

        alarm50011 NOTIFICATION-TYPE
        OBJECTS        {        neName,
                                neType,
                                eventGroupName,                        -- 50: Connectivity
                                eventName,                             -- 011: ConnectionsResponseTime
                                correlationId,
                                severity,
                                eventTime,
                                faultyObject,
                                monitoredValue,
                                thresholdValues,
                                info   }
        STATUS                current
        DESCRIPTION        "Spontaneous Alarm from the managed network element:
                            Smart Cloud Connection response time too high.
                            Check whether the high response time is justified. If not check the network and processed traffic. Are additional nodes needed? Is Smart Cloud overloaded?"
        ::= { eventGroup50 11 }

        alarm50015 NOTIFICATION-TYPE
        OBJECTS        {        neName,
                                neType,
                                eventGroupName,                        -- 50: Connectivity
                                eventName,                             -- 015: ConnectionsActivityServiceFailure
                                correlationId,
                                severity,
                                eventTime,
                                faultyObject,
                                monitoredValue,
                                thresholdValues,
                                info   }
        STATUS                current
        DESCRIPTION        "Spontaneous Alarm from the managed network element:
                            Connectivity could not be established with the IBM Connections Activity Service.
                            Check if the Access node has internet connection and can reach the Cloud server."
        ::= { eventGroup50 15 }

        alarm50016 NOTIFICATION-TYPE
        OBJECTS        {        neName,
                                neType,
                                eventGroupName,                        -- 50: Connectivity
                                eventName,                             -- 016: ConnectionsFileServiceFailure
                                correlationId,
                                severity,
                                eventTime,
                                faultyObject,
                                monitoredValue,
                                thresholdValues,
                                info   }
        STATUS                current
        DESCRIPTION        "Spontaneous Alarm from the managed network element:
                            Connectivity could not be established with the IBM Connections File Service.
                            Check if the Access node has internet connection and can reach the Cloud server."
        ::= { eventGroup50 16 }

        alarm50017 NOTIFICATION-TYPE
        OBJECTS        {        neName,
                                neType,
                                eventGroupName,                        -- 50: Connectivity
                                eventName,                             -- 017: ConnectionsBSSServiceFailure
                                correlationId,
                                severity,
                                eventTime,
                                faultyObject,
                                monitoredValue,
                                thresholdValues,
                                info   }
        STATUS                current
        DESCRIPTION        "Spontaneous Alarm from the managed network element:
                            Connectivity could not be established with the IBM Connections BSS Service.
                            Check if the Access node has internet connection and can reach the Cloud server."
        ::= { eventGroup50 17 }

        alarm50018 NOTIFICATION-TYPE
        OBJECTS        {        neName,
                                neType,
                                eventGroupName,                        -- 50: Connectivity
                                eventName,                             -- 018: ConnectionsSearchServiceFailure
                                correlationId,
                                severity,
                                eventTime,
                                faultyObject,
                                monitoredValue,
                                thresholdValues,
                                info   }
        STATUS                current
        DESCRIPTION        "Spontaneous Alarm from the managed network element:
                            Connectivity could not be established with the IBM Connections Search Service.
                            Check if the Access node has internet connection and can reach the Cloud server."
        ::= { eventGroup50 18 }

        alarm50021 NOTIFICATION-TYPE
        OBJECTS        {        neName,
                                neType,
                                eventGroupName,                        -- 50: Connectivity
                                eventName,                             -- 021: LossOfComSMTP
                                correlationId,
                                severity,
                                eventTime,
                                faultyObject,
                                monitoredValue,
                                thresholdValues,
                                info   }
        STATUS                current
        DESCRIPTION        "Spontaneous Alarm from the managed network element:
                            The IMP application node has lost connectivity with the SMTP server identified in the faultyObject parameter.
                            Check the network (router, firewall, LAN). Check whether the SMTP server is out of service."
        ::= { eventGroup50 21 }

        alarm50051 NOTIFICATION-TYPE
        OBJECTS        {        neName,
                                neType,
                                eventGroupName,                        -- 50: Connectivity
                                eventName,                             -- 051: LossOfComApp
                                correlationId,
                                severity,
                                eventTime,
                                faultyObject,
                                monitoredValue,
                                thresholdValues,
                                info   }
        STATUS                current
        DESCRIPTION        "Spontaneous Alarm from the managed network element:
                            Access server lost communication with Application node.
                            The Application node maybe down, check the network setup. Also check the node configuration files and logs."
        ::= { eventGroup50 51 }

        alarm50061 NOTIFICATION-TYPE
        OBJECTS        {        neName,
                                neType,
                                eventGroupName,                        -- 50: Connectivity
                                eventName,                             -- 061: LossOfComAccClient
                                correlationId,
                                severity,
                                eventTime,
                                faultyObject,
                                monitoredValue,
                                thresholdValues,
                                info   }
        STATUS                current
        DESCRIPTION        "Spontaneous Alarm from the managed network element:
                            Access server lost communication with Accces Client node.
                            Check that all nodes of the solution are active."
        ::= { eventGroup50 61 }

        alarm50062 NOTIFICATION-TYPE
        OBJECTS        {        neName,
                                neType,
                                eventGroupName,                        -- 50: Connectivity
                                eventName,                             -- 062: LossOfComAccServer
                                correlationId,
                                severity,
                                eventTime,
                                faultyObject,
                                monitoredValue,
                                thresholdValues,
                                info   }
        STATUS                current
        DESCRIPTION        "Spontaneous Alarm from the managed network element:
                            Access server lost communication with Accces Server node.
                            Check that all nodes of the solution are active."
        ::= { eventGroup50 62 }

        alarm50071 NOTIFICATION-TYPE
        OBJECTS        {        neName,
                                neType,
                                eventGroupName,                        -- 50: Connectivity
                                eventName,                             -- 071: LossOfComAcc
                                correlationId,
                                severity,
                                eventTime,
                                faultyObject,
                                monitoredValue,
                                thresholdValues,
                                info   }
        STATUS                current
        DESCRIPTION        "Spontaneous Alarm from the managed network element:
                            Server lost communication with Access node.
                            The Access node maybe down, check the network setup. Also check the node configuration files and logs."
        ::= { eventGroup50 71 }


        --********************************************************************
        -- Alarm Trap Definitions for event group 53: Turn
        --********************************************************************

        alarm53001 NOTIFICATION-TYPE
        OBJECTS        {        neName,
                                neType,
                                eventGroupName,                        -- 53: Turn
                                eventName,                             -- 001: LackOfUDPPorts
                                correlationId,
                                severity,
                                eventTime,
                                faultyObject,
                                monitoredValue,
                                thresholdValues,
                                info   }
        STATUS                current
        DESCRIPTION        "Spontaneous Alarm from the managed network element:
                            Turn has used more UDP ports than one of the configured thresholds.
                            Escalate to next level of support to analyze the traffic."
        ::= { eventGroup53 1 }


        --********************************************************************
        -- Alarm Trap Definitions for event group 54: LB
        --********************************************************************

        alarm54001 NOTIFICATION-TYPE
        OBJECTS        {        neName,
                                neType,
                                eventGroupName,                        -- 54: LB
                                eventName,                             -- 001: LossOfRedundancy
                                correlationId,
                                severity,
                                eventTime,
                                faultyObject,
                                monitoredValue,
                                thresholdValues,
                                info   }
        STATUS                current
        DESCRIPTION        "Spontaneous Alarm from the managed network element:
                            LB node lost its partner and now runs as master without backup.
                            Repair the LB partner node."
        ::= { eventGroup54 1 }

        alarm54002 NOTIFICATION-TYPE
        OBJECTS        {        neName,
                                neType,
                                eventGroupName,                        -- 54: LB
                                eventName,                             -- 002: FaultyConfiguration
                                correlationId,
                                severity,
                                eventTime,
                                faultyObject,
                                monitoredValue,
                                thresholdValues,
                                info   }
        STATUS                current
        DESCRIPTION        "Spontaneous Alarm from the managed network element:
                            LB configuration file is faulty. LB functionality is restricted.
                            Review log file entries to determine source of problem."
        ::= { eventGroup54 2 }


        --********************************************************************
        -- Alarm Trap Definitions for event group 55: Analytics
        --********************************************************************

        alarm55001 NOTIFICATION-TYPE
        OBJECTS        {        neName,
                                neType,
                                eventGroupName,                        -- 55: Analytics
                                eventName,                             -- 001: HadoopNoSpace
                                correlationId,
                                severity,
                                eventTime,
                                faultyObject,
                                monitoredValue,
                                thresholdValues,
                                info   }
        STATUS                current
        DESCRIPTION        "Spontaneous Alarm from the managed network element:
                            Hadoop did not start because there is no available disk space in /db/data. As a consequence the features log archiving and analytics are not available.
                            Free up space in /db or add more disk space to /db/data. Then change the operations  node status to locked and back to active to restart the application."
        ::= { eventGroup55 1 }

        alarm55002 NOTIFICATION-TYPE
        OBJECTS        {        neName,
                                neType,
                                eventGroupName,                        -- 55: Analytics
                                eventName,                             -- 002: DataLoaderFailure
                                correlationId,
                                severity,
                                eventTime,
                                faultyObject,
                                monitoredValue,
                                thresholdValues,
                                info   }
        STATUS                current
        DESCRIPTION        "Spontaneous Alarm from the managed network element:
                            Unable to load the instrumentation data. See the analytics log file for details.
                            Resolve any issues found in the analytics log file and then either manually launch the loader or wait until the next maintenance window."
        ::= { eventGroup55 2 }


        --********************************************************************
        -- Alarm Trap Definitions for event group 56: MediaServer
        --********************************************************************

        alarm56001 NOTIFICATION-TYPE
        OBJECTS        {        neName,
                                neType,
                                eventGroupName,                        -- 56: MediaServer
                                eventName,                             -- 001: SIPTrunkMissing
                                correlationId,
                                severity,
                                eventTime,
                                faultyObject,
                                monitoredValue,
                                thresholdValues,
                                info   }
        STATUS                current
        DESCRIPTION        "Spontaneous Alarm from the managed network element:
                            Wrong SIP trunk configuration.
                            Escalate to next level of support."
        ::= { eventGroup56 1 }

        alarm56002 NOTIFICATION-TYPE
        OBJECTS        {        neName,
                                neType,
                                eventGroupName,                        -- 56: MediaServer
                                eventName,                             -- 002: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 2 }

        alarm56003 NOTIFICATION-TYPE
        OBJECTS        {        neName,
                                neType,
                                eventGroupName,                        -- 56: MediaServer
                                eventName,                             -- 003: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 3 }

        alarm56004 NOTIFICATION-TYPE
        OBJECTS        {        neName,
                                neType,
                                eventGroupName,                        -- 56: MediaServer
                                eventName,                             -- 004: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 4 }

        alarm56005 NOTIFICATION-TYPE
        OBJECTS        {        neName,
                                neType,
                                eventGroupName,                        -- 56: MediaServer
                                eventName,                             -- 005: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 5 }

        alarm56010 NOTIFICATION-TYPE
        OBJECTS        {        neName,
                                neType,
                                eventGroupName,                        -- 56: MediaServer
                                eventName,                             -- 010: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 10 }

        alarm56011 NOTIFICATION-TYPE
        OBJECTS        {        neName,
                                neType,
                                eventGroupName,                        -- 56: MediaServer
                                eventName,                             -- 011: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 11 }

        alarm56020 NOTIFICATION-TYPE
        OBJECTS        {        neName,
                                neType,
                                eventGroupName,                        -- 56: MediaServer
                                eventName,                             -- 020: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 20 }

        alarm56021 NOTIFICATION-TYPE
        OBJECTS        {        neName,
                                neType,
                                eventGroupName,                        -- 56: MediaServer
                                eventName,                             -- 021: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 21 }

        alarm56030 NOTIFICATION-TYPE
        OBJECTS        {        neName,
                                neType,
                                eventGroupName,                        -- 56: MediaServer
                                eventName,                             -- 030: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 30 }

        alarm56031 NOTIFICATION-TYPE
        OBJECTS        {        neName,
                                neType,
                                eventGroupName,                        -- 56: MediaServer
                                eventName,                             -- 031: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 31 }

        alarm56033 NOTIFICATION-TYPE
        OBJECTS        {        neName,
                                neType,
                                eventGroupName,                        -- 56: MediaServer
                                eventName,                             -- 033: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 33 }

        alarm56040 NOTIFICATION-TYPE
        OBJECTS        {        neName,
                                neType,
                                eventGroupName,                        -- 56: MediaServer
                                eventName,                             -- 040: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 40 }

        alarm56041 NOTIFICATION-TYPE
        OBJECTS        {        neName,
                                neType,
                                eventGroupName,                        -- 56: MediaServer
                                eventName,                             -- 041: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 41 }

        alarm56042 NOTIFICATION-TYPE
        OBJECTS        {        neName,
                                neType,
                                eventGroupName,                        -- 56: MediaServer
                                eventName,                             -- 042: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 42 }

        alarm56050 NOTIFICATION-TYPE
        OBJECTS        {        neName,
                                neType,
                                eventGroupName,                        -- 56: MediaServer
                                eventName,                             -- 050: N/A
                                correlationId,
                                severity,
                                eventTime,
                                faultyObject,
                                monitoredValue,
                                thresholdValues,
                                info   }
        STATUS                obsolete
        DESCRIPTION        "Spontaneous Alarm from the managed network element:
                            Deprecated alarm
                            None"
        ::= { eventGroup56 50 }

        alarm56100 NOTIFICATION-TYPE
        OBJECTS        {        neName,
                                neType,
                                eventGroupName,                        -- 56: MediaServer
                                eventName,                             -- 100: SipStackStartupProblem
                                correlationId,
                                severity,
                                eventTime,
                                faultyObject,
                                monitoredValue,
                                thresholdValues,
                                info   }
        STATUS                current
        DESCRIPTION        "Spontaneous Alarm from the managed network element:
                            SIP stack startup problem
SIP Connectivity Provider,Failed to create a sip stack instance.
                            Please check the log for further information."
        ::= { eventGroup56 100 }

        alarm56101 NOTIFICATION-TYPE
        OBJECTS        {        neName,
                                neType,
                                eventGroupName,                        -- 56: MediaServer
                                eventName,                             -- 101: SipStackStartupProblemListening
                                correlationId,
                                severity,
                                eventTime,
                                faultyObject,
                                monitoredValue,
                                thresholdValues,
                                info   }
        STATUS                current
        DESCRIPTION        "Spontaneous Alarm from the managed network element:
                            Startup problem with a SIP stack listening point

Failed to create a listening point. Maybe address or port is in use.
                            Please check listeningPoint settings in the management UI or in the sip-connectivity.xml file."
        ::= { eventGroup56 101 }

        alarm56102 NOTIFICATION-TYPE
        OBJECTS        {        neName,
                                neType,
                                eventGroupName,                        -- 56: MediaServer
                                eventName,                             -- 102: SipStackStartupProblemInternal
                                correlationId,
                                severity,
                                eventTime,
                                faultyObject,
                                monitoredValue,
                                thresholdValues,
                                info   }
        STATUS                current
        DESCRIPTION        "Spontaneous Alarm from the managed network element:
                            Startup problem due to internal SIP stack error

Failed to create sip provider instance.
                            Please check the log for further information."
        ::= { eventGroup56 102 }

        alarm56103 NOTIFICATION-TYPE
        OBJECTS        {        neName,
                                neType,
                                eventGroupName,                        -- 56: MediaServer
                                eventName,                             -- 103: SipStackStartupProblemInternal2
                                correlationId,
                                severity,
                                eventTime,
                                faultyObject,
                                monitoredValue,
                                thresholdValues,
                                info   }
        STATUS                current
        DESCRIPTION        "Spontaneous Alarm from the managed network element:
                            Startup problem due to internal SIP stack error

Failed to register SipManager as a SIP listener.
                            Please check the log for further information."
        ::= { eventGroup56 103 }

        alarm56104 NOTIFICATION-TYPE
        OBJECTS        {        neName,
                                neType,
                                eventGroupName,                        -- 56: MediaServer
                                eventName,                             -- 104: SipStackShutdownProblem
                                correlationId,
                                severity,
                                eventTime,
                                faultyObject,
                                monitoredValue,
                                thresholdValues,
                                info   }
        STATUS                current
        DESCRIPTION        "Spontaneous Alarm from the managed network element:
                            SIP stack shutdown problem

Failed to delete a SipProvider instance from sip stack.
                            Please check the log for further information."
        ::= { eventGroup56 104 }

        alarm56105 NOTIFICATION-TYPE
        OBJECTS        {        neName,
                                neType,
                                eventGroupName,                        -- 56: MediaServer
                                eventName,                             -- 105: SipStackShutdownProblem2
                                correlationId,
                                severity,
                                eventTime,
                                faultyObject,
                                monitoredValue,
                                thresholdValues,
                                info   }
        STATUS                current
        DESCRIPTION        "Spontaneous Alarm from the managed network element:
                            SIP stack shutdown problem

Failed to delete a listening point from sip stack.
                            Please check the log for further information."
        ::= { eventGroup56 105 }

        alarm56106 NOTIFICATION-TYPE
        OBJECTS        {        neName,
                                neType,
                                eventGroupName,                        -- 56: MediaServer
                                eventName,                             -- 106: SipProviderConfMissing
                                correlationId,
                                severity,
                                eventTime,
                                faultyObject,
                                monitoredValue,
                                thresholdValues,
                                info   }
        STATUS                current
        DESCRIPTION        "Spontaneous Alarm from the managed network element:
                            SIP provider startup failed: configuration is missing

Failed to start SIP provider due to missing configuration.
                            Please check the log for further information."
        ::= { eventGroup56 106 }

        alarm56107 NOTIFICATION-TYPE
        OBJECTS        {        neName,
                                neType,
                                eventGroupName,                        -- 56: MediaServer
                                eventName,                             -- 107: SipProviderSdpParserMissing
                                correlationId,
                                severity,
                                eventTime,
                                faultyObject,
                                monitoredValue,
                                thresholdValues,
                                info   }
        STATUS                current
        DESCRIPTION        "Spontaneous Alarm from the managed network element:
                            SIP provider startup failed: SDP parser missing

Failed to start SIP provider due to missing SDP parser component.
                            Please check the log for further information."
        ::= { eventGroup56 107 }

        alarm56108 NOTIFICATION-TYPE
        OBJECTS        {        neName,
                                neType,
                                eventGroupName,                        -- 56: MediaServer
                                eventName,                             -- 108: SipProviderAddrTransCompMissing
                                correlationId,
                                severity,
                                eventTime,
                                faultyObject,
                                monitoredValue,
                                thresholdValues,
                                info   }
        STATUS                current
        DESCRIPTION        "Spontaneous Alarm from the managed network element:
                            SIP provider startup failed: Address Translation component missing.

Failed to start SIP provider due to missing Address Translation component.
                            Please check the log for further information."
        ::= { eventGroup56 108 }

        alarm56109 NOTIFICATION-TYPE
        OBJECTS        {        neName,
                                neType,
                                eventGroupName,                        -- 56: MediaServer
                                eventName,                             -- 109: SipProviderLocationDBCompMissing
                                correlationId,
                                severity,
                                eventTime,
                                faultyObject,
                                monitoredValue,
                                thresholdValues,
                                info   }
        STATUS                current
        DESCRIPTION        "Spontaneous Alarm from the managed network element:
                            SIP provider startup failed: Location Database component missing

Failed to start SIP provider due to missing Location Database component.
                            Please check the log for further information."
        ::= { eventGroup56 109 }

        alarm56110 NOTIFICATION-TYPE
        OBJECTS        {        neName,
                                neType,
                                eventGroupName,                        -- 56: MediaServer
                                eventName,                             -- 110: SipProviderStartFailure
                                correlationId,
                                severity,
                                eventTime,
                                faultyObject,
                                monitoredValue,
                                thresholdValues,
                                info   }
        STATUS                current
        DESCRIPTION        "Spontaneous Alarm from the managed network element:
                            Failed to start sip provider

Internal SIP manager startup problem.
                            Please check the log for further information."
        ::= { eventGroup56 110 }

        alarm56200 NOTIFICATION-TYPE
        OBJECTS        {        neName,
                                neType,
                                eventGroupName,                        -- 56: MediaServer
                                eventName,                             -- 200: MFWProviderMissing
                                correlationId,
                                severity,
                                eventTime,
                                faultyObject,
                                monitoredValue,
                                thresholdValues,
                                info   }
        STATUS                current
        DESCRIPTION        "Spontaneous Alarm from the managed network element:
                            Missing MFW provider

Could not get MediaFramework (MFW) provider from Application Host. Processing of streaming data will not work.
                            Check log-output for more details."
        ::= { eventGroup56 200 }

        alarm56202 NOTIFICATION-TYPE
        OBJECTS        {        neName,
                                neType,
                                eventGroupName,                        -- 56: MediaServer
                                eventName,                             -- 202: MPSMediaProcessingProviderInitFailure
                                correlationId,
                                severity,
                                eventTime,
                                faultyObject,
                                monitoredValue,
                                thresholdValues,
                                info   }
        STATUS                current
        DESCRIPTION        "Spontaneous Alarm from the managed network element:
                            Failed to initialize MPS Media Processing Provider

Failed to initialize the Media Processing (MPS) Provider. Processing of streaming data will not work.
                            Check log-output for more details."
        ::= { eventGroup56 202 }

        alarm56203 NOTIFICATION-TYPE
        OBJECTS        {        neName,
                                neType,
                                eventGroupName,                        -- 56: MediaServer
                                eventName,                             -- 203: NoMoreAvailableRTPChannel
                                correlationId,
                                severity,
                                eventTime,
                                faultyObject,
                                monitoredValue,
                                thresholdValues,
                                info   }
        STATUS                current
        DESCRIPTION        "Spontaneous Alarm from the managed network element:
                            No more RTP channel available

Failed to allocate a RTP channel resource to handle call.
                            Please check the ResourceManagement configuration for this application."
        ::= { eventGroup56 203 }

        alarm56204 NOTIFICATION-TYPE
        OBJECTS        {        neName,
                                neType,
                                eventGroupName,                        -- 56: MediaServer
                                eventName,                             -- 204: NoMorAvailableTTSLicens
                                correlationId,
                                severity,
                                eventTime,
                                faultyObject,
                                monitoredValue,
                                thresholdValues,
                                info   }
        STATUS                current
        DESCRIPTION        "Spontaneous Alarm from the managed network element:
                            No (more) TTS license available

Failed to allocate Text-To-Speech port license.
                            Please make sure that there are enough licenses installed and that the 'licensing service' is running."
        ::= { eventGroup56 204 }

        alarm56205 NOTIFICATION-TYPE
        OBJECTS        {        neName,
                                neType,
                                eventGroupName,                        -- 56: MediaServer
                                eventName,                             -- 205: NoMoreAvailableASRLicense
                                correlationId,
                                severity,
                                eventTime,
                                faultyObject,
                                monitoredValue,
                                thresholdValues,
                                info   }
        STATUS                current
        DESCRIPTION        "Spontaneous Alarm from the managed network element:
                            No (more) ASR license available

Failed to allocate Speech-Recognition port license.
                            Please make sure that there are enough licenses installed and that the 'licensing service' is running."
        ::= { eventGroup56 205 }

        alarm56210 NOTIFICATION-TYPE
        OBJECTS        {        neName,
                                neType,
                                eventGroupName,                        -- 56: MediaServer
                                eventName,                             -- 210: NoDiscSpaceLeft
                                correlationId,
                                severity,
                                eventTime,
                                faultyObject,
                                monitoredValue,
                                thresholdValues,
                                info   }
        STATUS                current
        DESCRIPTION        "Spontaneous Alarm from the managed network element:
                            No disc space left

Unable to write further samples for recording, since there is no more disc space available.
                            Run debug file collection and escalate to next level of support."
        ::= { eventGroup56 210 }

        alarm56211 NOTIFICATION-TYPE
        OBJECTS        {        neName,
                                neType,
                                eventGroupName,                        -- 56: MediaServer
                                eventName,                             -- 211: NoAvaiableResource
                                correlationId,
                                severity,
                                eventTime,
                                faultyObject,
                                monitoredValue,
                                thresholdValues,
                                info   }
        STATUS                current
        DESCRIPTION        "Spontaneous Alarm from the managed network element:
                            Resource no longer available

Failed to write samples for recording, because the file path is not available or the file not writeable.
                            Run debug file collection and escalate to next level of support."
        ::= { eventGroup56 211 }

        alarm56300 NOTIFICATION-TYPE
        OBJECTS        {        neName,
                                neType,
                                eventGroupName,                        -- 56: MediaServer
                                eventName,                             -- 300: MediaGatewayProviderInitFailure
                                correlationId,
                                severity,
                                eventTime,
                                faultyObject,
                                monitoredValue,
                                thresholdValues,
                                info   }
        STATUS                current
        DESCRIPTION        "Spontaneous Alarm from the managed network element:
                            Failed to initialize Media Gateway Provider

An error occurred while starting Media Gateway Provider.
                            Please verify Media Gateway Configuration and assure that the PromptDB provider is running."
        ::= { eventGroup56 300 }

        alarm56301 NOTIFICATION-TYPE
        OBJECTS        {        neName,
                                neType,
                                eventGroupName,                        -- 56: MediaServer
                                eventName,                             -- 301: ConfChangesActivationFailure
                                correlationId,
                                severity,
                                eventTime,
                                faultyObject,
                                monitoredValue,
                                thresholdValues,
                                info   }
        STATUS                current
        DESCRIPTION        "Spontaneous Alarm from the managed network element:
                            Failed to activate configuration changes

An error occurred while activating configuration changes.
                            Please fix Media Gateway Configuration and restart provider."
        ::= { eventGroup56 301 }

        alarm56302 NOTIFICATION-TYPE
        OBJECTS        {        neName,
                                neType,
                                eventGroupName,                        -- 56: MediaServer
                                eventName,                             -- 302: MediaGatewayDeactivationFailure
                                correlationId,
                                severity,
                                eventTime,
                                faultyObject,
                                monitoredValue,
                                thresholdValues,
                                info   }
        STATUS                current
        DESCRIPTION        "Spontaneous Alarm from the managed network element:
                            Failed to deactivate Media Gateway Provider

An unexpected error occurred while stopping Media Gateway Provider.
                            Run debug file collection and escalate to next level of support."
        ::= { eventGroup56 302 }

        alarm56303 NOTIFICATION-TYPE
        OBJECTS        {        neName,
                                neType,
                                eventGroupName,                        -- 56: MediaServer
                                eventName,                             -- 303: MediaGatewayActivationFailure
                                correlationId,
                                severity,
                                eventTime,
                                faultyObject,
                                monitoredValue,
                                thresholdValues,
                                info   }
        STATUS                current
        DESCRIPTION        "Spontaneous Alarm from the managed network element:
                            Failed to activate media gateways

No listening point is defined in Media Gateway configuration.
                            Please add at least one listening point."
        ::= { eventGroup56 303 }

        alarm56304 NOTIFICATION-TYPE
        OBJECTS        {        neName,
                                neType,
                                eventGroupName,                        -- 56: MediaServer
                                eventName,                             -- 304: ConnectionCreationFailure
                                correlationId,
                                severity,
                                eventTime,
                                faultyObject,
                                monitoredValue,
                                thresholdValues,
                                info   }
        STATUS                current
        DESCRIPTION        "Spontaneous Alarm from the managed network element:
                            Failed to create connection

Ignoring create connection command, since no incoming connection listener is registered.
                            Please assure that the terminal binder is running."
        ::= { eventGroup56 304 }

        alarm56310 NOTIFICATION-TYPE
        OBJECTS        {        neName,
                                neType,
                                eventGroupName,                        -- 56: MediaServer
                                eventName,                             -- 310: ConnectionCreationFailure2
                                correlationId,
                                severity,
                                eventTime,
                                faultyObject,
                                monitoredValue,
                                thresholdValues,
                                info   }
        STATUS                current
        DESCRIPTION        "Spontaneous Alarm from the managed network element:
                            Failed to create connection

A new connection can not be created due to a non-recoverable problem.
                            Please check the log-output to get more detailed informations (logger: com.cycos.media)."
        ::= { eventGroup56 310 }

        alarm56311 NOTIFICATION-TYPE
        OBJECTS        {        neName,
                                neType,
                                eventGroupName,                        -- 56: MediaServer
                                eventName,                             -- 311: ConnectionModificationFailure
                                correlationId,
                                severity,
                                eventTime,
                                faultyObject,
                                monitoredValue,
                                thresholdValues,
                                info   }
        STATUS                current
        DESCRIPTION        "Spontaneous Alarm from the managed network element:
                            Failed to modify connection

Existing connection can not be modified due to a non-recoverable problem.
                            Please check the log-output to get more detailed informations (logger: com.cycos.media)."
        ::= { eventGroup56 311 }

        alarm56312 NOTIFICATION-TYPE
        OBJECTS        {        neName,
                                neType,
                                eventGroupName,                        -- 56: MediaServer
                                eventName,                             -- 312: ConnectionDeletionFailure
                                correlationId,
                                severity,
                                eventTime,
                                faultyObject,
                                monitoredValue,
                                thresholdValues,
                                info   }
        STATUS                current
        DESCRIPTION        "Spontaneous Alarm from the managed network element:
                            Failed to delete connection

Request to delete a connection can not be handled correctly due to a non-recoverable problem.
                            Please check the log-output to get more detailed informations (logger: com.cycos.media)."
        ::= { eventGroup56 312 }

        alarm56313 NOTIFICATION-TYPE
        OBJECTS        {        neName,
                                neType,
                                eventGroupName,                        -- 56: MediaServer
                                eventName,                             -- 313: NotificationRequestProcessingFailure
                                correlationId,
                                severity,
                                eventTime,
                                faultyObject,
                                monitoredValue,
                                thresholdValues,
                                info   }
        STATUS                current
        DESCRIPTION        "Spontaneous Alarm from the managed network element:
                            Failed to process notification request

An internal problem occurred during the handling of a request for notification.
                            Escalate to next level of support."
        ::= { eventGroup56 313 }

        alarm56330 NOTIFICATION-TYPE
        OBJECTS        {        neName,
                                neType,
                                eventGroupName,                        -- 56: MediaServer
                                eventName,                             -- 330: ResourceAssociatedWithConnectionLost
                                correlationId,
                                severity,
                                eventTime,
                                faultyObject,
                                monitoredValue,
                                thresholdValues,
                                info   }
        STATUS                current
        DESCRIPTION        "Spontaneous Alarm from the managed network element:
                            Lost the resource associated with the connection

An internal problem occurred and the gateway is terminating the connection.
                            Escalate to next level of support."
        ::= { eventGroup56 330 }

        alarm56400 NOTIFICATION-TYPE
        OBJECTS        {        neName,
                                neType,
                                eventGroupName,                        -- 56: MediaServer
                                eventName,                             -- 400: UnknownMFWFault
                                correlationId,
                                severity,
                                eventTime,
                                faultyObject,
                                monitoredValue,
                                thresholdValues,
                                info   }
        STATUS                current
        DESCRIPTION        "Spontaneous Alarm from the managed network element:
                            Unknown MFW fault

Unspecified Media Framework Component fault.
                            Escalate to next level of support."
        ::= { eventGroup56 400 }

        alarm56401 NOTIFICATION-TYPE
        OBJECTS        {        neName,
                                neType,
                                eventGroupName,                        -- 56: MediaServer
                                eventName,                             -- 401: NativeMediaFrameworkStartupFailure
                                correlationId,
                                severity,
                                eventTime,
                                faultyObject,
                                monitoredValue,
                                thresholdValues,
                                info   }
        STATUS                current
        DESCRIPTION        "Spontaneous Alarm from the managed network element:
                            Native Media Framework startup failed

Native part of Media Framework could not be started by Java.
                            Escalate to next level of support."
        ::= { eventGroup56 401 }

        alarm56402 NOTIFICATION-TYPE
        OBJECTS        {        neName,
                                neType,
                                eventGroupName,                        -- 56: MediaServer
                                eventName,                             -- 402: NativeMediaFrameworkNotResponding
                                correlationId,
                                severity,
                                eventTime,
                                faultyObject,
                                monitoredValue,
                                thresholdValues,
                                info   }
        STATUS                current
        DESCRIPTION        "Spontaneous Alarm from the managed network element:
                            Native Media Framework not responding

Native part of Media Framework has crashed or is unable to respond.
                            Escalate to next level of support."
        ::= { eventGroup56 402 }

        alarm56403 NOTIFICATION-TYPE
        OBJECTS        {        neName,
                                neType,
                                eventGroupName,                        -- 56: MediaServer
                                eventName,                             -- 403: JavaMediaFrameworkReceiveSocketOverrun
                                correlationId,
                                severity,
                                eventTime,
                                faultyObject,
                                monitoredValue,
                                thresholdValues,
                                info   }
        STATUS                current
        DESCRIPTION        "Spontaneous Alarm from the managed network element:
                            Java Media Framework receive socket overrun

Receive socket of java part of Media Framework is overloaded.
                            Escalate to next level of support."
        ::= { eventGroup56 403 }

        alarm56404 NOTIFICATION-TYPE
        OBJECTS        {        neName,
                                neType,
                                eventGroupName,                        -- 56: MediaServer
                                eventName,                             -- 404: NativeMediaFrameworkRecieveSocketOverrun
                                correlationId,
                                severity,
                                eventTime,
                                faultyObject,
                                monitoredValue,
                                thresholdValues,
                                info   }
        STATUS                current
        DESCRIPTION        "Spontaneous Alarm from the managed network element:
                            Native Media Framework receive socket overrun

Receive socket of native part of Media Framework is overloaded.
                            Escalate to next level of support."
        ::= { eventGroup56 404 }

        alarm56405 NOTIFICATION-TYPE
        OBJECTS        {        neName,
                                neType,
                                eventGroupName,                        -- 56: MediaServer
                                eventName,                             -- 405: JavaMediaFrameworkReceiveSocketSequencError
                                correlationId,
                                severity,
                                eventTime,
                                faultyObject,
                                monitoredValue,
                                thresholdValues,
                                info   }
        STATUS                current
        DESCRIPTION        "Spontaneous Alarm from the managed network element:
                            Java Media Framework receive socket sequence error

Messages lost on receive socket in java part of Media Framework.
                            Escalate to next level of support."
        ::= { eventGroup56 405 }

        alarm56406 NOTIFICATION-TYPE
        OBJECTS        {        neName,
                                neType,
                                eventGroupName,                        -- 56: MediaServer
                                eventName,                             -- 406: NativeMediaFrameworkReceiveSocketSequencError
                                correlationId,
                                severity,
                                eventTime,
                                faultyObject,
                                monitoredValue,
                                thresholdValues,
                                info   }
        STATUS                current
        DESCRIPTION        "Spontaneous Alarm from the managed network element:
                            Native Media Framework receive socket sequence error

Messages lost on receive socket in native part of Media Framework.
                            Escalate to next level of support."
        ::= { eventGroup56 406 }

        alarm56407 NOTIFICATION-TYPE
        OBJECTS        {        neName,
                                neType,
                                eventGroupName,                        -- 56: MediaServer
                                eventName,                             -- 407: NativeMediaFrameworkSocketError
                                correlationId,
                                severity,
                                eventTime,
                                faultyObject,
                                monitoredValue,
                                thresholdValues,
                                info   }
        STATUS                current
        DESCRIPTION        "Spontaneous Alarm from the managed network element:
                            Native Media Framework socket error

Bind of socket failed in native part of Media Framework.
                            Escalate to next level of support."
        ::= { eventGroup56 407 }

        alarm56408 NOTIFICATION-TYPE
        OBJECTS        {        neName,
                                neType,
                                eventGroupName,                        -- 56: MediaServer
                                eventName,                             -- 408: JavaMediaFrameworkUnrecoverableError
                                correlationId,
                                severity,
                                eventTime,
                                faultyObject,
                                monitoredValue,
                                thresholdValues,
                                info   }
        STATUS                current
        DESCRIPTION        "Spontaneous Alarm from the managed network element:
                            Java Media Framework unrecoverable error

Unrecoverable error in java part of Media Framework leading to permanent service degradation. Any processing of streaming data won't work.
                            Escalate to next level of support."
        ::= { eventGroup56 408 }

        alarm56409 NOTIFICATION-TYPE
        OBJECTS        {        neName,
                                neType,
                                eventGroupName,                        -- 56: MediaServer
                                eventName,                             -- 409: NatvieMediaFrameworkUnrecoverableError
                                correlationId,
                                severity,
                                eventTime,
                                faultyObject,
                                monitoredValue,
                                thresholdValues,
                                info   }
        STATUS                current
        DESCRIPTION        "Spontaneous Alarm from the managed network element:
                            Native Media Framework unrecoverable error

Unrecoverable error in native part of Media Framework leading to permanent service degradation. Any processing of streaming data won't work.
                            Escalate to next level of support."
        ::= { eventGroup56 409 }

        alarm56410 NOTIFICATION-TYPE
        OBJECTS        {        neName,
                                neType,
                                eventGroupName,                        -- 56: MediaServer
                                eventName,                             -- 410: NativeMediaFrameworkOutOfMemory
                                correlationId,
                                severity,
                                eventTime,
                                faultyObject,
                                monitoredValue,
                                thresholdValues,
                                info   }
        STATUS                current
        DESCRIPTION        "Spontaneous Alarm from the managed network element:
                            Native Media Framework out of memory

Memory allocation failed in native part of Media Framework.
                            Escalate to next level of support."
        ::= { eventGroup56 410 }

        alarm56411 NOTIFICATION-TYPE
        OBJECTS        {        neName,
                                neType,
                                eventGroupName,                        -- 56: MediaServer
                                eventName,                             -- 411: NativeMediaFrameworkOutOfUDPPorts
                                correlationId,
                                severity,
                                eventTime,
                                faultyObject,
                                monitoredValue,
                                thresholdValues,
                                info   }
        STATUS                current
        DESCRIPTION        "Spontaneous Alarm from the managed network element:
                            Native Media Framework out of UDP ports

Port allocation failed in native part of Media Framework.
                            Escalate to next level of support."
        ::= { eventGroup56 411 }

        alarm56412 NOTIFICATION-TYPE
        OBJECTS        {        neName,
                                neType,
                                eventGroupName,                        -- 56: MediaServer
                                eventName,                             -- 412: NativeMediaFrameworkCryptoSessionNotFound
                                correlationId,
                                severity,
                                eventTime,
                                faultyObject,
                                monitoredValue,
                                thresholdValues,
                                info   }
        STATUS                current
        DESCRIPTION        "Spontaneous Alarm from the managed network element:
                            Native Media Framework crypto session not found

KeyManagement has no matching crypto session. Processing of encrypted streaming data will be affected.
                            Escalate to next level of support."
        ::= { eventGroup56 412 }

        alarm56413 NOTIFICATION-TYPE
        OBJECTS        {        neName,
                                neType,
                                eventGroupName,                        -- 56: MediaServer
                                eventName,                             -- 413: NativeMediaFrameworkSRTPError
                                correlationId,
                                severity,
                                eventTime,
                                faultyObject,
                                monitoredValue,
                                thresholdValues,
                                info   }
        STATUS                current
        DESCRIPTION        "Spontaneous Alarm from the managed network element:
                            Native Media Framework srtp error

Srtp stack returned error. Processing of encrypted streaming data will be affected.
                            Escalate to next level of support."
        ::= { eventGroup56 413 }

        alarm56414 NOTIFICATION-TYPE
        OBJECTS        {        neName,
                                neType,
                                eventGroupName,                        -- 56: MediaServer
                                eventName,                             -- 414: NativeMediaFrameworkJeyManagementFatalErro
                                correlationId,
                                severity,
                                eventTime,
                                faultyObject,
                                monitoredValue,
                                thresholdValues,
                                info   }
        STATUS                current
        DESCRIPTION        "Spontaneous Alarm from the managed network element:
                            Native Media Framework keyManagement fatal error

KeyManagement in unrecoverable error state. Processing of encrypted streaming data will be affected.
                            Escalate to next level of support."
        ::= { eventGroup56 414 }

        alarm56415 NOTIFICATION-TYPE
        OBJECTS        {        neName,
                                neType,
                                eventGroupName,                        -- 56: MediaServer
                                eventName,                             -- 415: NativeMediaFrameworkControlPortBindError
                                correlationId,
                                severity,
                                eventTime,
                                faultyObject,
                                monitoredValue,
                                thresholdValues,
                                info   }
        STATUS                current
        DESCRIPTION        "Spontaneous Alarm from the managed network element:
                            Media Framework control port bind error

Control port for Java-native communication could not be opened - check port configuration or other processes using conflicting ports.
                            Escalate to next level of support."
        ::= { eventGroup56 415 }

        alarm56416 NOTIFICATION-TYPE
        OBJECTS        {        neName,
                                neType,
                                eventGroupName,                        -- 56: MediaServer
                                eventName,                             -- 416: NativeMediaFrameworkRealtimeError
                                correlationId,
                                severity,
                                eventTime,
                                faultyObject,
                                monitoredValue,
                                thresholdValues,
                                info   }
        STATUS                current
        DESCRIPTION        "Spontaneous Alarm from the managed network element:
                            Native Media Framework realtime error

Native MFW process could not be started in realtime mode: this may lead to bad voice quality.
                            Check access rights for native image."
        ::= { eventGroup56 416 }

        alarm56417 NOTIFICATION-TYPE
        OBJECTS        {        neName,
                                neType,
                                eventGroupName,                        -- 56: MediaServer
                                eventName,                             -- 417: NativeMediaFrameworksRTCError
                                correlationId,
                                severity,
                                eventTime,
                                faultyObject,
                                monitoredValue,
                                thresholdValues,
                                info   }
        STATUS                current
        DESCRIPTION        "Spontaneous Alarm from the managed network element:
                            Native Media Framework RTC error

Realtime clock could not be initialized: this may degrade voice quality.
                            Check for configuration or conflicting usage of RTC by another process."
        ::= { eventGroup56 417 }

        alarm56418 NOTIFICATION-TYPE
        OBJECTS        {        neName,
                                neType,
                                eventGroupName,                        -- 56: MediaServer
                                eventName,                             -- 418: UDPPortBindError
                                correlationId,
                                severity,
                                eventTime,
                                faultyObject,
                                monitoredValue,
                                thresholdValues,
                                info   }
        STATUS                current
        DESCRIPTION        "Spontaneous Alarm from the managed network element:
                            UDP port bind error

Bind of a UDP port failed.
                            If this error persists check port range configuration."
        ::= { eventGroup56 418 }

        alarm56419 NOTIFICATION-TYPE
        OBJECTS        {        neName,
                                neType,
                                eventGroupName,                        -- 56: MediaServer
                                eventName,                             -- 419: IllegalCommandOption
                                correlationId,
                                severity,
                                eventTime,
                                faultyObject,
                                monitoredValue,
                                thresholdValues,
                                info   }
        STATUS                current
        DESCRIPTION        "Spontaneous Alarm from the managed network element:
                            Illegal command option

Media Framework was started with an illegal command option.
                            Check configuration in Media Framework configuration file 'mfw.component.xml'."
        ::= { eventGroup56 419 }

        alarm56420 NOTIFICATION-TYPE
        OBJECTS        {        neName,
                                neType,
                                eventGroupName,                        -- 56: MediaServer
                                eventName,                             -- 420: NoMoreAvailableUDPPorts
                                correlationId,
                                severity,
                                eventTime,
                                faultyObject,
                                monitoredValue,
                                thresholdValues,
                                info   }
        STATUS                current
        DESCRIPTION        "Spontaneous Alarm from the managed network element:
                            No more free UDP ports available

The media framework (MFW) has run out of free UDP ports.
                            Please make sure that the media servers configured port range is sufficient."
        ::= { eventGroup56 420 }

        alarm56500 NOTIFICATION-TYPE
        OBJECTS        {        neName,
                                neType,
                                eventGroupName,                        -- 56: MediaServer
                                eventName,                             -- 500: MRCPServerConnectionSetupError
                                correlationId,
                                severity,
                                eventTime,
                                faultyObject,
                                monitoredValue,
                                thresholdValues,
                                info   }
        STATUS                current
        DESCRIPTION        "Spontaneous Alarm from the managed network element:
                            Unable to setup a connection with MRCP server

Unable to setup a connection with MRCP server. No TTS or ASR services may be used within the media server's applications.
                            Escalate to next level of support."
        ::= { eventGroup56 500 }

        alarm56990 NOTIFICATION-TYPE
        OBJECTS        {        neName,
                                neType,
                                eventGroupName,                        -- 56: MediaServer
                                eventName,                             -- 990: TooManyRTCParticipants
                                correlationId,
                                severity,
                                eventTime,
                                faultyObject,
                                monitoredValue,
                                thresholdValues,
                                info   }
        STATUS                current
        DESCRIPTION        "Spontaneous Alarm from the managed network element:
                            A new RTC participant tried to enter an RTC conference and the limit is reached. The new participant is removed.
                            The alarm is not cleared manually."
        ::= { eventGroup56 990 }

        alarm56991 NOTIFICATION-TYPE
        OBJECTS        {        neName,
                                neType,
                                eventGroupName,                        -- 56: MediaServer
                                eventName,                             -- 991: TooManyPSTNParticipants
                                correlationId,
                                severity,
                                eventTime,
                                faultyObject,
                                monitoredValue,
                                thresholdValues,
                                info   }
        STATUS                current
        DESCRIPTION        "Spontaneous Alarm from the managed network element:
                            A new PSTN participant tried to enter an RTC conference and the limit is reached. The new participant is removed.
                            The alarm is not cleared manually."
        ::= { eventGroup56 991 }

        alarm56992 NOTIFICATION-TYPE
        OBJECTS        {        neName,
                                neType,
                                eventGroupName,                        -- 56: MediaServer
                                eventName,                             -- 992: Overload
                                correlationId,
                                severity,
                                eventTime,
                                faultyObject,
                                monitoredValue,
                                thresholdValues,
                                info   }
        STATUS                current
        DESCRIPTION        "Spontaneous Alarm from the managed network element:
                            The media server has too much load. If possible new conference calls are assigned to other media servers, if not they are rejected.
                            If the alarm condition remains over a longer period of time review installation sizing. If the installation is sized properly escalate to development to check for SW problems."
        ::= { eventGroup56 992 }


        --********************************************************************
        -- Alarm Trap Definitions for event group 57: IMPApplication
        --********************************************************************

        alarm57001 NOTIFICATION-TYPE
        OBJECTS        {        neName,
                                neType,
                                eventGroupName,                        -- 57: IMPApplication
                                eventName,                             -- 001: Service
                                correlationId,
                                severity,
                                eventTime,
                                faultyObject,
                                monitoredValue,
                                thresholdValues,
                                info   }
        STATUS                current
        DESCRIPTION        "Spontaneous Alarm from the managed network element:
                            Service in the application container does not startup.
                            Escalate to next level of support."
        ::= { eventGroup57 1 }

        alarm57003 NOTIFICATION-TYPE
        OBJECTS        {        neName,
                                neType,
                                eventGroupName,                        -- 57: IMPApplication
                                eventName,                             -- 003: ClientAPITimeHigh
                                correlationId,
                                severity,
                                eventTime,
                                faultyObject,
                                monitoredValue,
                                thresholdValues,
                                info   }
        STATUS                current
        DESCRIPTION        "Spontaneous Alarm from the managed network element:
                            Client API average response time.
                            Escalate to next level of support."
        ::= { eventGroup57 3 }

        alarm57004 NOTIFICATION-TYPE
        OBJECTS        {        neName,
                                neType,
                                eventGroupName,                        -- 57: IMPApplication
                                eventName,                             -- 004: ClientAPIFailure
                                correlationId,
                                severity,
                                eventTime,
                                faultyObject,
                                monitoredValue,
                                thresholdValues,
                                info   }
        STATUS                current
        DESCRIPTION        "Spontaneous Alarm from the managed network element:
                            Client API times out, no response.
                            Escalate to next level of support."
        ::= { eventGroup57 4 }

        alarm57005 NOTIFICATION-TYPE
        OBJECTS        {        neName,
                                neType,
                                eventGroupName,                        -- 57: IMPApplication
                                eventName,                             -- 005: ClientAPIZpoolFull
                                correlationId,
                                severity,
                                eventTime,
                                faultyObject,
                                monitoredValue,
                                thresholdValues,
                                info   }
        STATUS                current
        DESCRIPTION        "Spontaneous Alarm from the managed network element:
                            The zpool contains data.

A high fill level may cause issues and failed conversions once 100% reached.
                            If the alarm condition remains over a longer period of time review installation sizing. If the installation is sized properly escalate to development to check for SW problems."
        ::= { eventGroup57 5 }

        alarm57013 NOTIFICATION-TYPE
        OBJECTS        {        neName,
                                neType,
                                eventGroupName,                        -- 57: IMPApplication
                                eventName,                             -- 013: UnknownAlarmId
                                correlationId,
                                severity,
                                eventTime,
                                faultyObject,
                                monitoredValue,
                                thresholdValues,
                                info   }
        STATUS                current
        DESCRIPTION        "Spontaneous Alarm from the managed network element:
                            The platform alarm configuration file could not be found.
                            Check installation. If correct, check permissions on alarm configuration file."
        ::= { eventGroup57 13 }

        alarm57014 NOTIFICATION-TYPE
        OBJECTS        {        neName,
                                neType,
                                eventGroupName,                        -- 57: IMPApplication
                                eventName,                             -- 014: InvalidMonitoredValue
                                correlationId,
                                severity,
                                eventTime,
                                faultyObject,
                                monitoredValue,
                                thresholdValues,
                                info   }
        STATUS                current
        DESCRIPTION        "Spontaneous Alarm from the managed network element:
                            An alarm has been raised or used with an invalid monitored attribute value.
                            Correct code raising the alarm."
        ::= { eventGroup57 14 }

        alarm57015 NOTIFICATION-TYPE
        OBJECTS        {        neName,
                                neType,
                                eventGroupName,                        -- 57: IMPApplication
                                eventName,                             -- 015: FaultyObjectTooLong
                                correlationId,
                                severity,
                                eventTime,
                                faultyObject,
                                monitoredValue,
                                thresholdValues,
                                info   }
        STATUS                current
        DESCRIPTION        "Spontaneous Alarm from the managed network element:
                            An alarm has been raised with a FaultyObject string that is longer than 255. It has been truncated.
                            Correct code raising the alarm."
        ::= { eventGroup57 15 }

        alarm57016 NOTIFICATION-TYPE
        OBJECTS        {        neName,
                                neType,
                                eventGroupName,                        -- 57: IMPApplication
                                eventName,                             -- 016: AddlInfoTooLong
                                correlationId,
                                severity,
                                eventTime,
                                faultyObject,
                                monitoredValue,
                                thresholdValues,
                                info   }
        STATUS                current
        DESCRIPTION        "Spontaneous Alarm from the managed network element:
                            An alarm has been raised with an Addl Info string that is longer than 255. It has been truncated.
                            Correct code raising the alarm."
        ::= { eventGroup57 16 }

        alarm57017 NOTIFICATION-TYPE
        OBJECTS        {        neName,
                                neType,
                                eventGroupName,                        -- 57: IMPApplication
                                eventName,                             -- 017: UnknownAlarmId
                                correlationId,
                                severity,
                                eventTime,
                                faultyObject,
                                monitoredValue,
                                thresholdValues,
                                info   }
        STATUS                current
        DESCRIPTION        "Spontaneous Alarm from the managed network element:
                            An alarm has been raised or used with an unknown group ID and/or event ID.
                            Check if the alarm should be raised/used. If correct, add alarm to alarm configuration."
        ::= { eventGroup57 17 }


        --********************************************************************
        -- Alarm Trap Definitions for event group 58: Redis
        --********************************************************************

        alarm58001 NOTIFICATION-TYPE
        OBJECTS        {        neName,
                                neType,
                                eventGroupName,                        -- 58: Redis
                                eventName,                             -- 001: RedisClusterFail
                                correlationId,
                                severity,
                                eventTime,
                                faultyObject,
                                monitoredValue,
                                thresholdValues,
                                info   }
        STATUS                current
        DESCRIPTION        "Spontaneous Alarm from the managed network element:
                            Redis cluster is in fail state and can not recover by itself. As a result all requests to the data center is not being processed. Human intervention is needed immediately.
                            This alarm can occur during system startup and cluster formation. If this is not the case, check if all nodes are running. Check also if redis-cluster and redis-audit are running. If everything looks good then probably the cluster will not recover by itself. To recover the system lock all nodes (pmc state locked) then run '/etc/init.d/redis-audit clean' in all nodes, afterwards unlock the nodes (pmc state locked) - this way a fresh redis-cluster will start."
        ::= { eventGroup58 1 }

        alarm58002 NOTIFICATION-TYPE
        OBJECTS        {        neName,
                                neType,
                                eventGroupName,                        -- 58: Redis
                                eventName,                             -- 002: RedisClusterFailOver
                                correlationId,
                                severity,
                                eventTime,
                                faultyObject,
                                monitoredValue,
                                thresholdValues,
                                info   }
        STATUS                current
        DESCRIPTION        "Spontaneous Alarm from the managed network element:
                            One of the redis node is down so a failover just happened.
                            This alarm can happen temporarily if some other Access node is restarting. Please check if all nodes are running or if there are network issues. The redis audit will try to rebalance the cluster once the Access node is available again (then the alarm will be automatically cleared). The process of rebalancing can take about 5 to 15 minutes to complete."
        ::= { eventGroup58 2 }

        alarm58003 NOTIFICATION-TYPE
        OBJECTS        {        neName,
                                neType,
                                eventGroupName,                        -- 58: Redis
                                eventName,                             -- 003: RedisClusterRebalancing
                                correlationId,
                                severity,
                                eventTime,
                                faultyObject,
                                monitoredValue,
                                thresholdValues,
                                info   }
        STATUS                current
        DESCRIPTION        "Spontaneous Alarm from the managed network element:
                            A resharding is started, do not stop the nodes participating in the resharding until the alarm is cleared.
                            The redis audit is moving hash slots (resharding). This happens if nodes are added or removed, the alarm will be automatically cleared once the resharding process is complete. The process of resharding can take about 5 to 15 minutes to complete."
        ::= { eventGroup58 3 }

        alarm58004 NOTIFICATION-TYPE
        OBJECTS        {        neName,
                                neType,
                                eventGroupName,                        -- 58: Redis
                                eventName,                             -- 004: RedisClusterInit
                                correlationId,
                                severity,
                                eventTime,
                                faultyObject,
                                monitoredValue,
                                thresholdValues,
                                info   }
        STATUS                current
        DESCRIPTION        "Spontaneous Alarm from the managed network element:
                            Redis Cluster is in the process of reinitializing, all data will be erased and a new cluster will be formed.
                            The redis audit is in process of creating a new cluster, allocating hash slots for each node and defining the Master/Slave roles. This alarm can also happen temporarily after resharding and rebalancing. The alarm will be automatically cleared once the cluster formation process is complete, this process can take about 5 minutes to complete."
        ::= { eventGroup58 4 }


        --********************************************************************
        -- Alarm Trap Definitions for event group 59: LogManager
        --********************************************************************

        alarm59001 NOTIFICATION-TYPE
        OBJECTS        {        neName,
                                neType,
                                eventGroupName,                        -- 59: LogManager
                                eventName,                             -- 001: PostAlarmFailure
                                correlationId,
                                severity,
                                eventTime,
                                faultyObject,
                                monitoredValue,
                                thresholdValues,
                                info   }
        STATUS                current
        DESCRIPTION        "Spontaneous Alarm from the managed network element:
                            The log manger could not store an alarm record in the alarm database. The alarm is not reported as SNMP trap and not displayed in the active alarm database.
                            Run debug file collection of the operations node and escalate to SW development."
        ::= { eventGroup59 1 }

        alarm59002 NOTIFICATION-TYPE
        OBJECTS        {        neName,
                                neType,
                                eventGroupName,                        -- 59: LogManager
                                eventName,                             -- 002: PostSolrFailure
                                correlationId,
                                severity,
                                eventTime,
                                faultyObject,
                                monitoredValue,
                                thresholdValues,
                                info   }
        STATUS                current
        DESCRIPTION        "Spontaneous Alarm from the managed network element:
                            The log manger could not store a log record in Solr. The log is not shown in the log manager GUI and it is not archived in hadoop.
                            Check the partition fill level and accessibility of the /db/logmg directory. Run debug file collection of the operations node and escalate to SW development."
        ::= { eventGroup59 2 }

        alarm59003 NOTIFICATION-TYPE
        OBJECTS        {        neName,
                                neType,
                                eventGroupName,                        -- 59: LogManager
                                eventName,                             -- 003: PostHiveFailure
                                correlationId,
                                severity,
                                eventTime,
                                faultyObject,
                                monitoredValue,
                                thresholdValues,
                                info   }
        STATUS                current
        DESCRIPTION        "Spontaneous Alarm from the managed network element:
                            The log manager could not access Hive.
                            Is the /db partition accessible? Run debug file collection of the operations node and escalate to SW development."
        ::= { eventGroup59 3 }


        --********************************************************************
        -- Alarm Trap Definitions for event group 60: Access
        --********************************************************************

        alarm60001 NOTIFICATION-TYPE
        OBJECTS        {        neName,
                                neType,
                                eventGroupName,                        -- 60: Access
                                eventName,                             -- 001: FaultyConfiguraton
                                correlationId,
                                severity,
                                eventTime,
                                faultyObject,
                                monitoredValue,
                                thresholdValues,
                                info   }
        STATUS                current
        DESCRIPTION        "Spontaneous Alarm from the managed network element:
                            Access node configuration file is faulty. Access node functionality is restricted.
                            Review log file entries, especially /var/log/access.log, to determine source of problem."
        ::= { eventGroup60 1 }


        --********************************************************************
        -- Alarm Trap Definitions for event group 80: NetworkCom
        --********************************************************************

        alarm80001 NOTIFICATION-TYPE
        OBJECTS        {        neName,
                                neType,
                                eventGroupName,                        -- 80: NetworkCom
                                eventName,                             -- 001: NodesUnavailable
                                correlationId,
                                severity,
                                eventTime,
                                faultyObject,
                                monitoredValue,
                                thresholdValues,
                                info   }
        STATUS                current
        DESCRIPTION        "Spontaneous Alarm from the managed network element:
                            The listed nodes are not reported as active in the zookeeper database.
                            Check the administrative and operational status. Try to access the node directly via ssh and run rapidstat."
        ::= { eventGroup80 1 }

        alarm80002 NOTIFICATION-TYPE
        OBJECTS        {        neName,
                                neType,
                                eventGroupName,                        -- 80: NetworkCom
                                eventName,                             -- 002: LocalResponseTime
                                correlationId,
                                severity,
                                eventTime,
                                faultyObject,
                                monitoredValue,
                                thresholdValues,
                                info   }
        STATUS                current
        DESCRIPTION        "Spontaneous Alarm from the managed network element:
                            The node's response time to a test message sent by the operations node was too high.
                            If this alarm persists escalate to next level of support to determine whether is response time is justified. Ether the SW needs to be corrected or the threshold be changed."
        ::= { eventGroup80 2 }

        alarm80003 NOTIFICATION-TYPE
        OBJECTS        {        neName,
                                neType,
                                eventGroupName,                        -- 80: NetworkCom
                                eventName,                             -- 003: RemoteResponseTime
                                correlationId,
                                severity,
                                eventTime,
                                faultyObject,
                                monitoredValue,
                                thresholdValues,
                                info   }
        STATUS                current
        DESCRIPTION        "Spontaneous Alarm from the managed network element:
                            Future.
                            Future."
        ::= { eventGroup80 3 }


        --********************************************************************
        -- Alarm Trap Definitions for event group 81: Eventing
        --********************************************************************

        alarm81001 NOTIFICATION-TYPE
        OBJECTS        {        neName,
                                neType,
                                eventGroupName,                        -- 81: Eventing
                                eventName,                             -- 001: RabbitMQ
                                correlationId,
                                severity,
                                eventTime,
                                faultyObject,
                                monitoredValue,
                                thresholdValues,
                                info   }
        STATUS                current
        DESCRIPTION        "Spontaneous Alarm from the managed network element:
                            RabbitMQ is not running.
                            Check IMP Application configuration."
        ::= { eventGroup81 1 }


        --********************************************************************
        -- Alarm Trap Definitions for event group 82: InMemDatabase
        --********************************************************************

        alarm82001 NOTIFICATION-TYPE
        OBJECTS        {        neName,
                                neType,
                                eventGroupName,                        -- 82: InMemDatabase
                                eventName,                             -- 001: Hazelcast
                                correlationId,
                                severity,
                                eventTime,
                                faultyObject,
                                monitoredValue,
                                thresholdValues,
                                info   }
        STATUS                current
        DESCRIPTION        "Spontaneous Alarm from the managed network element:
                            In memory database is not running, does not startup.
                            Check IMP Application configuration."
        ::= { eventGroup82 1 }



        --********************************************************************
        -- Alarm Trap Definitions for alarms potentially sent for multiple nodes
        -- (using eventGroupC)
        --********************************************************************

        --********************************************************************
        -- Alarm Trap Definitions for alarm eventC 01: Platform
        --********************************************************************

        alarmC01001 NOTIFICATION-TYPE
        OBJECTS        {        neName,
                                neType,
                                eventGroupName,                        -- 01: Platform
                                eventName,                             -- 001: InvalidAlarmConfiguration
                                correlationId,
                                severity,
                                eventTime,
                                nodes,
                                faultyObject,
                                monitoredValue,
                                thresholdValues,
                                info   }
        STATUS                current
        DESCRIPTION        "Spontaneous Alarm from the managed network element:
                            The alarm configuration has problems.
                            Check the problem listed in the faulty object and correct."
        ::= { eventGroupC01 1 }

        alarmC01002 NOTIFICATION-TYPE
        OBJECTS        {        neName,
                                neType,
                                eventGroupName,                        -- 01: Platform
                                eventName,                             -- 002: InvalidTimezoneConfiguration
                                correlationId,
                                severity,
                                eventTime,
                                nodes,
                                faultyObject,
                                monitoredValue,
                                thresholdValues,
                                info   }
        STATUS                current
        DESCRIPTION        "Spontaneous Alarm from the managed network element:
                            The timezone configured in the datacenter configuration in the ZooKeeper database is not one of values supported by the Linux Operating System. An invalid timezone will be ignored so the timezone will remain as the default timezone (UTC) or the last valid timezone that was successfully configured.
                            Manually change the timezone in the datacenter configuration in the ZooKeeper database to a valid timezone. Valid timezones can be found under directory /usr/share/zoneinfo (e.g. US/Eastern)."
        ::= { eventGroupC01 2 }

        alarmC01003 NOTIFICATION-TYPE
        OBJECTS        {        neName,
                                neType,
                                eventGroupName,                        -- 01: Platform
                                eventName,                             -- 003: UnknownAlarmId
                                correlationId,
                                severity,
                                eventTime,
                                nodes,
                                faultyObject,
                                monitoredValue,
                                thresholdValues,
                                info   }
        STATUS                current
        DESCRIPTION        "Spontaneous Alarm from the managed network element:
                            An alarm has been raised or used with an unknown group ID and/or event ID.
                            Check if the alarm should be raised/used. If correct, add alarm to alarm configuration."
        ::= { eventGroupC01 3 }

        alarmC01004 NOTIFICATION-TYPE
        OBJECTS        {        neName,
                                neType,
                                eventGroupName,                        -- 01: Platform
                                eventName,                             -- 004: InvalidMonitoredValue
                                correlationId,
                                severity,
                                eventTime,
                                nodes,
                                faultyObject,
                                monitoredValue,
                                thresholdValues,
                                info   }
        STATUS                current
        DESCRIPTION        "Spontaneous Alarm from the managed network element:
                            An alarm has been raised or used with an invalid monitored attribute value.
                            Correct code raising the alarm."
        ::= { eventGroupC01 4 }

        alarmC01005 NOTIFICATION-TYPE
        OBJECTS        {        neName,
                                neType,
                                eventGroupName,                        -- 01: Platform
                                eventName,                             -- 005: FaultyObjectTooLong
                                correlationId,
                                severity,
                                eventTime,
                                nodes,
                                faultyObject,
                                monitoredValue,
                                thresholdValues,
                                info   }
        STATUS                current
        DESCRIPTION        "Spontaneous Alarm from the managed network element:
                            An alarm has been raised with a FaultyObject string that is longer than 255. It has been truncated.
                            Correct code raising the alarm."
        ::= { eventGroupC01 5 }

        alarmC01006 NOTIFICATION-TYPE
        OBJECTS        {        neName,
                                neType,
                                eventGroupName,                        -- 01: Platform
                                eventName,                             -- 006: AddlInfoTooLong
                                correlationId,
                                severity,
                                eventTime,
                                nodes,
                                faultyObject,
                                monitoredValue,
                                thresholdValues,
                                info   }
        STATUS                current
        DESCRIPTION        "Spontaneous Alarm from the managed network element:
                            An alarm has been raised with an Addl Info string that is longer than 255. It has been truncated.
                            Correct code raising the alarm."
        ::= { eventGroupC01 6 }

        alarmC01007 NOTIFICATION-TYPE
        OBJECTS        {        neName,
                                neType,
                                eventGroupName,                        -- 01: Platform
                                eventName,                             -- 007: TooManyAlarmParameters
                                correlationId,
                                severity,
                                eventTime,
                                nodes,
                                faultyObject,
                                monitoredValue,
                                thresholdValues,
                                info   }
        STATUS                current
        DESCRIPTION        "Spontaneous Alarm from the managed network element:
                            There is additional text after AddlInfo in the reported alarm string.
                            Correct code raising the alarm."
        ::= { eventGroupC01 7 }


        --********************************************************************
        -- Alarm Trap Definitions for alarm eventC 03: FileTransfer
        --********************************************************************

        alarmC03001 NOTIFICATION-TYPE
        OBJECTS        {        neName,
                                neType,
                                eventGroupName,                        -- 03: FileTransfer
                                eventName,                             -- 001: ExportFailing
                                correlationId,
                                severity,
                                eventTime,
                                nodes,
                                faultyObject,
                                monitoredValue,
                                thresholdValues,
                                info   }
        STATUS                current
        DESCRIPTION        "Spontaneous Alarm from the managed network element:
                            The SFTP connection to remote server has failed for this instance.
                            Probably due to bad File Export configuration data or a network issue where we cannot communicate with the SFTP server. Please check /var/log/platform/logging/LogIssues.log file. Collect the output of the command /opt/platform/bin/plat_fe_ctl --display_working_config."
        ::= { eventGroupC03 1 }

        alarmC03002 NOTIFICATION-TYPE
        OBJECTS        {        neName,
                                neType,
                                eventGroupName,                        -- 03: FileTransfer
                                eventName,                             -- 002: ExportFailing
                                correlationId,
                                severity,
                                eventTime,
                                nodes,
                                faultyObject,
                                monitoredValue,
                                thresholdValues,
                                info   }
        STATUS                current
        DESCRIPTION        "Spontaneous Alarm from the managed network element:
                            The SFTP connection to remote server has failed for this instance.
                            Probably due to bad File Export configuration data or a network issue where we cannot communicate with the SFTP server. Please check /var/log/platform/logging/LogIssues.log file. Collect the output of the command /opt/platform/bin/plat_fe_ctl --display_working_config."
        ::= { eventGroupC03 2 }

        alarmC03003 NOTIFICATION-TYPE
        OBJECTS        {        neName,
                                neType,
                                eventGroupName,                        -- 03: FileTransfer
                                eventName,                             -- 003: ExportFailing
                                correlationId,
                                severity,
                                eventTime,
                                nodes,
                                faultyObject,
                                monitoredValue,
                                thresholdValues,
                                info   }
        STATUS                current
        DESCRIPTION        "Spontaneous Alarm from the managed network element:
                            The SFTP connection to remote server has failed for this instance.
                            Probably due to bad File Export configuration data or a network issue where we cannot communicate with the SFTP server. Please check /var/log/platform/logging/LogIssues.log file. Collect the output of the command /opt/platform/bin/plat_fe_ctl --display_working_config."
        ::= { eventGroupC03 3 }


        --********************************************************************
        -- Alarm Trap Definitions for alarm eventC 04: Process
        --********************************************************************

        alarmC04001 NOTIFICATION-TYPE
        OBJECTS        {        neName,
                                neType,
                                eventGroupName,                        -- 04: Process
                                eventName,                             -- 001: PmAborted
                                correlationId,
                                severity,
                                eventTime,
                                nodes,
                                faultyObject,
                                monitoredValue,
                                thresholdValues,
                                info   }
        STATUS                current
        DESCRIPTION        "Spontaneous Alarm from the managed network element:
                            Process Monitoring has aborted.
                            Check configuration files and get logs in debug level 7."
        ::= { eventGroupC04 1 }

        alarmC04002 NOTIFICATION-TYPE
        OBJECTS        {        neName,
                                neType,
                                eventGroupName,                        -- 04: Process
                                eventName,                             -- 002: NetworkNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 2 }

        alarmC04003 NOTIFICATION-TYPE
        OBJECTS        {        neName,
                                neType,
                                eventGroupName,                        -- 04: Process
                                eventName,                             -- 003: RoutesNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 3 }

        alarmC04004 NOTIFICATION-TYPE
        OBJECTS        {        neName,
                                neType,
                                eventGroupName,                        -- 04: Process
                                eventName,                             -- 004: GmondNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 4 }

        alarmC04005 NOTIFICATION-TYPE
        OBJECTS        {        neName,
                                neType,
                                eventGroupName,                        -- 04: Process
                                eventName,                             -- 005: hsflowdNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 5 }

        alarmC04006 NOTIFICATION-TYPE
        OBJECTS        {        neName,
                                neType,
                                eventGroupName,                        -- 04: Process
                                eventName,                             -- 006: jmxtransNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 6 }

        alarmC04007 NOTIFICATION-TYPE
        OBJECTS        {        neName,
                                neType,
                                eventGroupName,                        -- 04: Process
                                eventName,                             -- 007: ntpNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 7 }

        alarmC04008 NOTIFICATION-TYPE
        OBJECTS        {        neName,
                                neType,
                                eventGroupName,                        -- 04: Process
                                eventName,                             -- 008: syslogNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 8 }

        alarmC04009 NOTIFICATION-TYPE
        OBJECTS        {        neName,
                                neType,
                                eventGroupName,                        -- 04: Process
                                eventName,                             -- 009: sshdNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 9 }

        alarmC04010 NOTIFICATION-TYPE
        OBJECTS        {        neName,
                                neType,
                                eventGroupName,                        -- 04: Process
                                eventName,                             -- 010: snmpdNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 10 }

        alarmC04011 NOTIFICATION-TYPE
        OBJECTS        {        neName,
                                neType,
                                eventGroupName,                        -- 04: Process
                                eventName,                             -- 011: idsNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 11 }

        alarmC04012 NOTIFICATION-TYPE
        OBJECTS        {        neName,
                                neType,
                                eventGroupName,                        -- 04: Process
                                eventName,                             -- 012: logstashNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 12 }

        alarmC04013 NOTIFICATION-TYPE
        OBJECTS        {        neName,
                                neType,
                                eventGroupName,                        -- 04: Process
                                eventName,                             -- 013: TraceDriverNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 13 }

        alarmC04014 NOTIFICATION-TYPE
        OBJECTS        {        neName,
                                neType,
                                eventGroupName,                        -- 04: Process
                                eventName,                             -- 014: LoggingDriverNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 14 }

        alarmC04015 NOTIFICATION-TYPE
        OBJECTS        {        neName,
                                neType,
                                eventGroupName,                        -- 04: Process
                                eventName,                             -- 015: LoggingProcessNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 15 }

        alarmC04016 NOTIFICATION-TYPE
        OBJECTS        {        neName,
                                neType,
                                eventGroupName,                        -- 04: Process
                                eventName,                             -- 016: PlatAlarmNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 16 }

        alarmC04017 NOTIFICATION-TYPE
        OBJECTS        {        neName,
                                neType,
                                eventGroupName,                        -- 04: Process
                                eventName,                             -- 017: PlatZooClientNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 17 }

        alarmC04018 NOTIFICATION-TYPE
        OBJECTS        {        neName,
                                neType,
                                eventGroupName,                        -- 04: Process
                                eventName,                             -- 018: PlatPsrNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 18 }

        alarmC04019 NOTIFICATION-TYPE
        OBJECTS        {        neName,
                                neType,
                                eventGroupName,                        -- 04: Process
                                eventName,                             -- 019: PlatFileExportNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 19 }

        alarmC04020 NOTIFICATION-TYPE
        OBJECTS        {        neName,
                                neType,
                                eventGroupName,                        -- 04: Process
                                eventName,                             -- 020: PlatPstackNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 20 }

        alarmC04021 NOTIFICATION-TYPE
        OBJECTS        {        neName,
                                neType,
                                eventGroupName,                        -- 04: Process
                                eventName,                             -- 021: PlatMonitorNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 21 }

        alarmC04022 NOTIFICATION-TYPE
        OBJECTS        {        neName,
                                neType,
                                eventGroupName,                        -- 04: Process
                                eventName,                             -- 022: NetReceiverNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 22 }

        alarmC04023 NOTIFICATION-TYPE
        OBJECTS        {        neName,
                                neType,
                                eventGroupName,                        -- 04: Process
                                eventName,                             -- 023: TcaNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 23 }

        alarmC04024 NOTIFICATION-TYPE
        OBJECTS        {        neName,
                                neType,
                                eventGroupName,                        -- 04: Process
                                eventName,                             -- 024: FileExportScannerNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 24 }

        alarmC04025 NOTIFICATION-TYPE
        OBJECTS        {        neName,
                                neType,
                                eventGroupName,                        -- 04: Process
                                eventName,                             -- 025: PlatAuditSumNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 25 }

        alarmC04026 NOTIFICATION-TYPE
        OBJECTS        {        neName,
                                neType,
                                eventGroupName,                        -- 04: Process
                                eventName,                             -- 026: PlatLogRotateNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 26 }

        alarmC04035 NOTIFICATION-TYPE
        OBJECTS        {        neName,
                                neType,
                                eventGroupName,                        -- 04: Process
                                eventName,                             -- 035: ZooKeeperServerNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 35 }

        alarmC04040 NOTIFICATION-TYPE
        OBJECTS        {        neName,
                                neType,
                                eventGroupName,                        -- 04: Process
                                eventName,                             -- 040: AccessRedisNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            The alarm is cleared if PM was able to start the process.
If the alarm is still active or if the alarm has been reported many times the issue should be escalated to development for SW debugging.
Navigate to the log manager GUI and run debug file collection for the node.
Attach the collected debug file to the fault report."
        ::= { eventGroupC04 40 }

        alarmC04041 NOTIFICATION-TYPE
        OBJECTS        {        neName,
                                neType,
                                eventGroupName,                        -- 04: Process
                                eventName,                             -- 041: AccessRedis-clusterNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Redis-cluster configuration."
        ::= { eventGroupC04 41 }

        alarmC04042 NOTIFICATION-TYPE
        OBJECTS        {        neName,
                                neType,
                                eventGroupName,                        -- 04: Process
                                eventName,                             -- 042: AccessTurnServerNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check TurnServer configuration."
        ::= { eventGroupC04 42 }

        alarmC04043 NOTIFICATION-TYPE
        OBJECTS        {        neName,
                                neType,
                                eventGroupName,                        -- 04: Process
                                eventName,                             -- 043: AccessNodeAppNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check NodeApp configuration."
        ::= { eventGroupC04 43 }

        alarmC04044 NOTIFICATION-TYPE
        OBJECTS        {        neName,
                                neType,
                                eventGroupName,                        -- 04: Process
                                eventName,                             -- 044: AccessLvsNodeNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check LvsNode configuration."
        ::= { eventGroupC04 44 }

        alarmC04045 NOTIFICATION-TYPE
        OBJECTS        {        neName,
                                neType,
                                eventGroupName,                        -- 04: Process
                                eventName,                             -- 045: AccessNginxNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Nginx configuration."
        ::= { eventGroupC04 45 }

        alarmC04046 NOTIFICATION-TYPE
        OBJECTS        {        neName,
                                neType,
                                eventGroupName,                        -- 04: Process
                                eventName,                             -- 046: AccessMetricsNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Metrics configuration."
        ::= { eventGroupC04 46 }

        alarmC04047 NOTIFICATION-TYPE
        OBJECTS        {        neName,
                                neType,
                                eventGroupName,                        -- 04: Process
                                eventName,                             -- 047: AccessAuditAppNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Audit configuration."
        ::= { eventGroupC04 47 }

        alarmC04048 NOTIFICATION-TYPE
        OBJECTS        {        neName,
                                neType,
                                eventGroupName,                        -- 04: Process
                                eventName,                             -- 048: AccessRedis-auditNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Redis configuration."
        ::= { eventGroupC04 48 }

        alarmC04060 NOTIFICATION-TYPE
        OBJECTS        {        neName,
                                neType,
                                eventGroupName,                        -- 04: Process
                                eventName,                             -- 060: LoadBalancerNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Load Balancer configuration."
        ::= { eventGroupC04 60 }

        alarmC04070 NOTIFICATION-TYPE
        OBJECTS        {        neName,
                                neType,
                                eventGroupName,                        -- 04: Process
                                eventName,                             -- 070: AnsibleVirgoNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroupC04 70 }

        alarmC04071 NOTIFICATION-TYPE
        OBJECTS        {        neName,
                                neType,
                                eventGroupName,                        -- 04: Process
                                eventName,                             -- 071: HazelcastNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroupC04 71 }

        alarmC04072 NOTIFICATION-TYPE
        OBJECTS        {        neName,
                                neType,
                                eventGroupName,                        -- 04: Process
                                eventName,                             -- 072: RabbitMQNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroupC04 72 }

        alarmC04075 NOTIFICATION-TYPE
        OBJECTS        {        neName,
                                neType,
                                eventGroupName,                        -- 04: Process
                                eventName,                             -- 075: MediaServerNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check IMP Application configuration."
        ::= { eventGroupC04 75 }

        alarmC04080 NOTIFICATION-TYPE
        OBJECTS        {        neName,
                                neType,
                                eventGroupName,                        -- 04: Process
                                eventName,                             -- 080: PostgresqlNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 80 }

        alarmC04081 NOTIFICATION-TYPE
        OBJECTS        {        neName,
                                neType,
                                eventGroupName,                        -- 04: Process
                                eventName,                             -- 081: HadoopNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 81 }

        alarmC04082 NOTIFICATION-TYPE
        OBJECTS        {        neName,
                                neType,
                                eventGroupName,                        -- 04: Process
                                eventName,                             -- 082: TomcatNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 82 }

        alarmC04083 NOTIFICATION-TYPE
        OBJECTS        {        neName,
                                neType,
                                eventGroupName,                        -- 04: Process
                                eventName,                             -- 083: NodeMonitorNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 83 }

        alarmC04084 NOTIFICATION-TYPE
        OBJECTS        {        neName,
                                neType,
                                eventGroupName,                        -- 04: Process
                                eventName,                             -- 084: AlarmManagerDNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 84 }

        alarmC04085 NOTIFICATION-TYPE
        OBJECTS        {        neName,
                                neType,
                                eventGroupName,                        -- 04: Process
                                eventName,                             -- 085: SolrdNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 85 }

        alarmC04086 NOTIFICATION-TYPE
        OBJECTS        {        neName,
                                neType,
                                eventGroupName,                        -- 04: Process
                                eventName,                             -- 086: FilemgrdNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 86 }

        alarmC04087 NOTIFICATION-TYPE
        OBJECTS        {        neName,
                                neType,
                                eventGroupName,                        -- 04: Process
                                eventName,                             -- 087: LogmgrdNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 87 }

        alarmC04088 NOTIFICATION-TYPE
        OBJECTS        {        neName,
                                neType,
                                eventGroupName,                        -- 04: Process
                                eventName,                             -- 088: Apache2NotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 88 }

        alarmC04089 NOTIFICATION-TYPE
        OBJECTS        {        neName,
                                neType,
                                eventGroupName,                        -- 04: Process
                                eventName,                             -- 089: GmetadNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Operations configuration."
        ::= { eventGroupC04 89 }

        alarmC04095 NOTIFICATION-TYPE
        OBJECTS        {        neName,
                                neType,
                                eventGroupName,                        -- 04: Process
                                eventName,                             -- 095: ImpManagementNotRunning
                                correlationId,
                                severity,
                                eventTime,
                                nodes,
                                faultyObject,
                                monitoredValue,
                                thresholdValues,
                                info   }
        STATUS                current
        DESCRIPTION        "Spontaneous Alarm from the managed network element:
                            The node process manager has found that the process/application is not running. It either could not be started during startup or it failed during normal operation. Usually the process is restarted automatically. In some cases the problem might even escalate to a full node restart.
                            Check Management configuration."
        ::= { eventGroupC04 95 }


        --********************************************************************
        -- Alarm Trap Definitions for alarm eventC 05: ProcessManager
        --********************************************************************

        alarmC05001 NOTIFICATION-TYPE
        OBJECTS        {        neName,
                                neType,
                                eventGroupName,                        -- 05: ProcessManager
                                eventName,                             -- 001: InvalidPlatConfiguration
                                correlationId,
                                severity,
                                eventTime,
                                nodes,
                                faultyObject,
                                monitoredValue,
                                thresholdValues,
                                info   }
        STATUS                current
        DESCRIPTION        "Spontaneous Alarm from the managed network element:
                            Platform configuration has invalid parameters:
A failure type of 1 means a missing or wrong configuration. PM can run.
2 means missing or wrong process configuration. PM can run but a process has potential problems.
3 means that the configuration file was rejected.
                            Check faulty object to know where the problem is located."
        ::= { eventGroupC05 1 }

        alarmC05002 NOTIFICATION-TYPE
        OBJECTS        {        neName,
                                neType,
                                eventGroupName,                        -- 05: ProcessManager
                                eventName,                             -- 002: InvalidServerConfiguration
                                correlationId,
                                severity,
                                eventTime,
                                nodes,
                                faultyObject,
                                monitoredValue,
                                thresholdValues,
                                info   }
        STATUS                current
        DESCRIPTION        "Spontaneous Alarm from the managed network element:
                            Server configuration has invalid parameters:
A failure type of 1 means a missing or wrong configuration. PM can run.
2 means missing or wrong process configuration. PM can run but a process has potential problems.
3 means that the configuration file was rejected.
                            Check faulty object to know where the problem is located."
        ::= { eventGroupC05 2 }

        alarmC05003 NOTIFICATION-TYPE
        OBJECTS        {        neName,
                                neType,
                                eventGroupName,                        -- 05: ProcessManager
                                eventName,                             -- 003: CanNotExecuteCommand
                                correlationId,
                                severity,
                                eventTime,
                                nodes,
                                faultyObject,
                                monitoredValue,
                                thresholdValues,
                                info   }
        STATUS                current
        DESCRIPTION        "Spontaneous Alarm from the managed network element:
                            One command could not be executed:
Command capabilities = 2 means that the command is important for PM operation and 3 means that it affects node operation.
                            Check faulty object and try to execute it by hand."
        ::= { eventGroupC05 3 }

        alarmC05004 NOTIFICATION-TYPE
        OBJECTS        {        neName,
                                neType,
                                eventGroupName,                        -- 05: ProcessManager
                                eventName,                             -- 004: UnexpectedBehaviour
                                correlationId,
                                severity,
                                eventTime,
                                nodes,
                                faultyObject,
                                monitoredValue,
                                thresholdValues,
                                info   }
        STATUS                current
        DESCRIPTION        "Spontaneous Alarm from the managed network element:
                            PM has found an unexpected behavior during its execution.
1 means that PM is still running and only a feature affected.
2 means that PM is still running, but that process control is affected.
3 means that PM will abort and restart.
                            Check faulty object for function name and line number of the problem."
        ::= { eventGroupC05 4 }

        alarmC05005 NOTIFICATION-TYPE
        OBJECTS        {        neName,
                                neType,
                                eventGroupName,                        -- 05: ProcessManager
                                eventName,                             -- 005: RecoverEscalation
                                correlationId,
                                severity,
                                eventTime,
                                nodes,
                                faultyObject,
                                monitoredValue,
                                thresholdValues,
                                info   }
        STATUS                current
        DESCRIPTION        "Spontaneous Alarm from the managed network element:
                            One or more process cannot be started.
If server Health State is 1 and the process continues to fail, all applicaton processes (Lvl 3) will be restarted.
If the HealthState is 2, the application restart did not work and all platform and all application processes (Lvl 1 and 2 will be restarted.
If the HealthState is 3, the node will be rebooted within 5 minutes.
                            Check which processe(s) are not working. Look for alarms reporting pstacks and coredumps. Collect debug files and send them to the next level of support for analysis."
        ::= { eventGroupC05 5 }


        --********************************************************************
        -- Alarm Trap Definitions for alarm eventC 06: CoreDump
        --********************************************************************

        alarmC06001 NOTIFICATION-TYPE
        OBJECTS        {        neName,
                                neType,
                                eventGroupName,                        -- 06: CoreDump
                                eventName,                             -- 001: PstackFound1
                                correlationId,
                                severity,
                                eventTime,
                                nodes,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroupC06 1 }

        alarmC06002 NOTIFICATION-TYPE
        OBJECTS        {        neName,
                                neType,
                                eventGroupName,                        -- 06: CoreDump
                                eventName,                             -- 002: PstackFound2
                                correlationId,
                                severity,
                                eventTime,
                                nodes,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroupC06 2 }

        alarmC06003 NOTIFICATION-TYPE
        OBJECTS        {        neName,
                                neType,
                                eventGroupName,                        -- 06: CoreDump
                                eventName,                             -- 003: PstackFound3
                                correlationId,
                                severity,
                                eventTime,
                                nodes,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroupC06 3 }

        alarmC06004 NOTIFICATION-TYPE
        OBJECTS        {        neName,
                                neType,
                                eventGroupName,                        -- 06: CoreDump
                                eventName,                             -- 004: PstackFound4
                                correlationId,
                                severity,
                                eventTime,
                                nodes,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroupC06 4 }

        alarmC06005 NOTIFICATION-TYPE
        OBJECTS        {        neName,
                                neType,
                                eventGroupName,                        -- 06: CoreDump
                                eventName,                             -- 005: PstackFound5
                                correlationId,
                                severity,
                                eventTime,
                                nodes,
                                faultyObject,
                                monitoredValue,
                                thresholdValues,
                                info   }
        STATUS                current
        DESCRIPTION        "Spontaneous Alarm from the managed network element:
                            A pstack has been found. There was a severe SW error within the process/application specified in the faultyObject. Debugging information has been stored in the pstack file. Usually the faulty process recovers from the error, but it could also be that some features may not work properly. A continuous process failure may also escalate to a node restart.
The alarm is auto-deleted after some hours unless it is overwritten by a more recent core dump.
                            The problem can only be repaired by a SW correction. In order to collect debug information navigate to the log manager GUI and sort through the file collection directory for pstack files based on time stamp and process name. Upload the file.
Also run debug file collection for the impacted node and upload the collected tar file, once available. Attach the files to the fault report."
        ::= { eventGroupC06 5 }

        alarmC06006 NOTIFICATION-TYPE
        OBJECTS        {        neName,
                                neType,
                                eventGroupName,                        -- 06: CoreDump
                                eventName,                             -- 006: CoreDumpFound1
                                correlationId,
                                severity,
                                eventTime,
                                nodes,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 6 }

        alarmC06007 NOTIFICATION-TYPE
        OBJECTS        {        neName,
                                neType,
                                eventGroupName,                        -- 06: CoreDump
                                eventName,                             -- 007: CoreDumpFound2
                                correlationId,
                                severity,
                                eventTime,
                                nodes,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 7 }

        alarmC06008 NOTIFICATION-TYPE
        OBJECTS        {        neName,
                                neType,
                                eventGroupName,                        -- 06: CoreDump
                                eventName,                             -- 008: CoreDumpFound3
                                correlationId,
                                severity,
                                eventTime,
                                nodes,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 8 }

        alarmC06009 NOTIFICATION-TYPE
        OBJECTS        {        neName,
                                neType,
                                eventGroupName,                        -- 06: CoreDump
                                eventName,                             -- 009: CoreDumpFound4
                                correlationId,
                                severity,
                                eventTime,
                                nodes,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 9 }

        alarmC06010 NOTIFICATION-TYPE
        OBJECTS        {        neName,
                                neType,
                                eventGroupName,                        -- 06: CoreDump
                                eventName,                             -- 010: CoreDumpFound5
                                correlationId,
                                severity,
                                eventTime,
                                nodes,
                                faultyObject,
                                monitoredValue,
                                thresholdValues,
                                info   }
        STATUS                current
        DESCRIPTION        "Spontaneous Alarm from the managed network element:
                            A core dump has been found. There was a severe SW error within the process/application specified in the faultyObject. Debugging information has been stored in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 10 }

        alarmC06011 NOTIFICATION-TYPE
        OBJECTS        {        neName,
                                neType,
                                eventGroupName,                        -- 06: CoreDump
                                eventName,                             -- 011: JavaDumpFound1
                                correlationId,
                                severity,
                                eventTime,
                                nodes,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 11 }

        alarmC06012 NOTIFICATION-TYPE
        OBJECTS        {        neName,
                                neType,
                                eventGroupName,                        -- 06: CoreDump
                                eventName,                             -- 012: JavaDumpFound2
                                correlationId,
                                severity,
                                eventTime,
                                nodes,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 12 }

        alarmC06013 NOTIFICATION-TYPE
        OBJECTS        {        neName,
                                neType,
                                eventGroupName,                        -- 06: CoreDump
                                eventName,                             -- 013: JavaDumpFound3
                                correlationId,
                                severity,
                                eventTime,
                                nodes,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 13 }

        alarmC06014 NOTIFICATION-TYPE
        OBJECTS        {        neName,
                                neType,
                                eventGroupName,                        -- 06: CoreDump
                                eventName,                             -- 014: JavaDumpFound4
                                correlationId,
                                severity,
                                eventTime,
                                nodes,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 14 }

        alarmC06015 NOTIFICATION-TYPE
        OBJECTS        {        neName,
                                neType,
                                eventGroupName,                        -- 06: CoreDump
                                eventName,                             -- 015: JavaDumpFound5
                                correlationId,
                                severity,
                                eventTime,
                                nodes,
                                faultyObject,
                                monitoredValue,
                                thresholdValues,
                                info   }
        STATUS                current
        DESCRIPTION        "Spontaneous Alarm from the managed network element:
                            A Java core dump has been found. There was a severe SW error within the process/application specified in the faultyObject. Debugging information are in the core dump file. Usually the faulty process recovers from the error, but it could also be that some features may not work properly. Writing the core file itself may be service impacting. A continuous process failure may also escalate to a node restart.
The alarm is auto-deleted after some hours unless it is overwritten by a more recent core dump.
                            The problem can only be repaired by a SW correction. In order to collect debug information navigate to the log manager GUI and sort through the file collection directory for core dump files based on time stamp and process name. Upload the file.
Also run debug file collection for the impacted node and upload the collected tar file, once available. Attach the files to the fault report."
        ::= { eventGroupC06 15 }


        --********************************************************************
        -- Alarm Trap Definitions for alarm eventC 08: Security
        --********************************************************************

        alarmC08001 NOTIFICATION-TYPE
        OBJECTS        {        neName,
                                neType,
                                eventGroupName,                        -- 08: Security
                                eventName,                             -- 001: PFRConfigurationFileMissing
                                correlationId,
                                severity,
                                eventTime,
                                nodes,
                                faultyObject,
                                monitoredValue,
                                thresholdValues,
                                info   }
        STATUS                current
        DESCRIPTION        "Spontaneous Alarm from the managed network element:
                            The configuration files listed under faultyObject are missing. The packet filter rules for the firewall may not be defined properly, and/or the node's security may be impacted.
                            Log in directly to the node and check the listed files. Escalate to the next level of support, if necessary to find the root cause for the missing file."
        ::= { eventGroupC08 1 }

        alarmC08002 NOTIFICATION-TYPE
        OBJECTS        {        neName,
                                neType,
                                eventGroupName,                        -- 08: Security
                                eventName,                             -- 002: PFRConfigurationDataMismatch
                                correlationId,
                                severity,
                                eventTime,
                                nodes,
                                faultyObject,
                                monitoredValue,
                                thresholdValues,
                                info   }
        STATUS                current
        DESCRIPTION        "Spontaneous Alarm from the managed network element:
                            The packet filter rules that have the names listed under faultyObject are faulty. The packet filter rules for the firewall may not be defined properly, and/or the node's security may be impacted.
                            Log in directly to the node and check the data listed in the faulty object and additional information. Escalate to the next level of support, if necessary to find the root cause for the wrong rules."
        ::= { eventGroupC08 2 }

        alarmC08003 NOTIFICATION-TYPE
        OBJECTS        {        neName,
                                neType,
                                eventGroupName,                        -- 08: Security
                                eventName,                             -- 003: OutgoingPacketDropped
                                correlationId,
                                severity,
                                eventTime,
                                nodes,
                                faultyObject,
                                monitoredValue,
                                thresholdValues,
                                info   }
        STATUS                current
        DESCRIPTION        "Spontaneous Alarm from the managed network element:
                            The node firewall has dropped outgoing IP packets and the number of dropped packets per minute has crossed a threshold. Dropping a packet may be:

(*) valid
(*) A SW error causing invalid packets to be sent
(*) A misconfigured node packet filter rule
(*) indicate a virus.
                            Use the mgmt node debug file collection function to upload debug files from the node that reported the alarm.

Analyze the dropped packets stored in the firewall log file to determine whether the IMP node sends invalid packets. If the packets are sent by valid IMP software escalate to development to either correct the packet filter rules or to modify the IMP SW not to send these packets.

If not, escalate to the next level of service to investigate whether there is a SW virus."
        ::= { eventGroupC08 3 }

        alarmC08004 NOTIFICATION-TYPE
        OBJECTS        {        neName,
                                neType,
                                eventGroupName,                        -- 08: Security
                                eventName,                             -- 004: IncomingPacketDropped
                                correlationId,
                                severity,
                                eventTime,
                                nodes,
                                faultyObject,
                                monitoredValue,
                                thresholdValues,
                                info   }
        STATUS                current
        DESCRIPTION        "Spontaneous Alarm from the managed network element:
                            The node firewall has dropped incoming IP packets and the number of dropped packets per minute has crossed a threshold. Dropping a packet may be:

(*) valid
(*) indicate a misconfiguration of the datacenter firewall
(*) A SW error in a partner IMP node causing invalid packets to be sent
(*) A misconfigured node packet filter rule
(*) indicate an attack.
                            Use the mgmt node debug file collection function to upload debug files from the node that reported the alarm.

Analyze the dropped packets stored in the firewall log file to determine whether the external firewall is mis-configured or whether IMP nodes send invalid packets. In the first case correct the external firewall and in latter case escalate to development to either correct the packet filter rules or to modify the IMP SW not to send these packets."
        ::= { eventGroupC08 4 }

        alarmC08011 NOTIFICATION-TYPE
        OBJECTS        {        neName,
                                neType,
                                eventGroupName,                        -- 08: Security
                                eventName,                             -- 011: ConfigurationFileMissing
                                correlationId,
                                severity,
                                eventTime,
                                nodes,
                                faultyObject,
                                monitoredValue,
                                thresholdValues,
                                info   }
        STATUS                current
        DESCRIPTION        "Spontaneous Alarm from the managed network element:
                            The security files listed under faultyObject are missing. The node may not start properly, not function properly, and/or its security will be impacted.
                            Log in directly to the node and check the listed files. Escalate to the next level of support, if necessary to find the root cause for the missing file."
        ::= { eventGroupC08 11 }

        alarmC08012 NOTIFICATION-TYPE
        OBJECTS        {        neName,
                                neType,
                                eventGroupName,                        -- 08: Security
                                eventName,                             -- 012: ConfigurationDataMismatch
                                correlationId,
                                severity,
                                eventTime,
                                nodes,
                                faultyObject,
                                monitoredValue,
                                thresholdValues,
                                info   }
        STATUS                current
        DESCRIPTION        "Spontaneous Alarm from the managed network element:
                            Data in the security files listed under faultyObject are wrong, missing or implausible. The node may not start properly, not function properly, and/or its security will be impacted.
                            Log in directly to the node and check the listed files. Escalate to the next level of support, if necessary to find the root cause for the wrong data."
        ::= { eventGroupC08 12 }

        alarmC08013 NOTIFICATION-TYPE
        OBJECTS        {        neName,
                                neType,
                                eventGroupName,                        -- 08: Security
                                eventName,                             -- 013: FilePermissionsError
                                correlationId,
                                severity,
                                eventTime,
                                nodes,
                                faultyObject,
                                monitoredValue,
                                thresholdValues,
                                info   }
        STATUS                current
        DESCRIPTION        "Spontaneous Alarm from the managed network element:
                            The file permission of the listed files are incorrect.
                            Log in directly to the node and change the file permissions to the proper values."
        ::= { eventGroupC08 13 }

        alarmC08014 NOTIFICATION-TYPE
        OBJECTS        {        neName,
                                neType,
                                eventGroupName,                        -- 08: Security
                                eventName,                             -- 014: IPSECDataFaulty
                                correlationId,
                                severity,
                                eventTime,
                                nodes,
                                faultyObject,
                                monitoredValue,
                                thresholdValues,
                                info   }
        STATUS                current
        DESCRIPTION        "Spontaneous Alarm from the managed network element:
                            IPSEC is not configured properly.
                            Escalate to SW development."
        ::= { eventGroupC08 14 }

        alarmC08015 NOTIFICATION-TYPE
        OBJECTS        {        neName,
                                neType,
                                eventGroupName,                        -- 08: Security
                                eventName,                             -- 015: UserKeyMismatch
                                correlationId,
                                severity,
                                eventTime,
                                nodes,
                                faultyObject,
                                monitoredValue,
                                thresholdValues,
                                info   }
        STATUS                current
        DESCRIPTION        "Spontaneous Alarm from the managed network element:
                            User keys do not match.
                            Escalate to SW development."
        ::= { eventGroupC08 15 }

        alarmC08021 NOTIFICATION-TYPE
        OBJECTS        {        neName,
                                neType,
                                eventGroupName,                        -- 08: Security
                                eventName,                             -- 021: UserAccountDisabled
                                correlationId,
                                severity,
                                eventTime,
                                nodes,
                                faultyObject,
                                monitoredValue,
                                thresholdValues,
                                info   }
        STATUS                current
        DESCRIPTION        "Spontaneous Alarm from the managed network element:
                            The specified user accounts are disabled.
                            Review the disabled accounts and either enable or delete them."
        ::= { eventGroupC08 21 }

        alarmC08022 NOTIFICATION-TYPE
        OBJECTS        {        neName,
                                neType,
                                eventGroupName,                        -- 08: Security
                                eventName,                             -- 022: SystemAccountDisabled
                                correlationId,
                                severity,
                                eventTime,
                                nodes,
                                faultyObject,
                                monitoredValue,
                                thresholdValues,
                                info   }
        STATUS                current
        DESCRIPTION        "Spontaneous Alarm from the managed network element:
                            The specified system accounts are disabled.
                            Review the disabled accounts and either enable or delete them.

If all system accounts are disabled and login to the node is not possible, use cloud/hypervisor tools to access the console and use the root account.
A last correction is to terminate the VM and re-launch it."
        ::= { eventGroupC08 22 }

        alarmC08023 NOTIFICATION-TYPE
        OBJECTS        {        neName,
                                neType,
                                eventGroupName,                        -- 08: Security
                                eventName,                             -- 023: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC08 23 }

        alarmC08024 NOTIFICATION-TYPE
        OBJECTS        {        neName,
                                neType,
                                eventGroupName,                        -- 08: Security
                                eventName,                             -- 024: PasswordExpired
                                correlationId,
                                severity,
                                eventTime,
                                nodes,
                                faultyObject,
                                monitoredValue,
                                thresholdValues,
                                info   }
        STATUS                current
        DESCRIPTION        "Spontaneous Alarm from the managed network element:
                            The password for the specified accounts has expired.
                            Delete the accounts or change the password."
        ::= { eventGroupC08 24 }

        alarmC08041 NOTIFICATION-TYPE
        OBJECTS        {        neName,
                                neType,
                                eventGroupName,                        -- 08: Security
                                eventName,                             -- 041: FailedAuthenticationAttempt
                                correlationId,
                                severity,
                                eventTime,
                                nodes,
                                faultyObject,
                                monitoredValue,
                                thresholdValues,
                                info   }
        STATUS                current
        DESCRIPTION        "Spontaneous Alarm from the managed network element:
                            A wrong password was entered.
                            This may be an indication for an unauthorized login attempt. If this happens often, check log files to identify the attacker."
        ::= { eventGroupC08 41 }

        alarmC08042 NOTIFICATION-TYPE
        OBJECTS        {        neName,
                                neType,
                                eventGroupName,                        -- 08: Security
                                eventName,                             -- 042: AccessDenied
                                correlationId,
                                severity,
                                eventTime,
                                nodes,
                                faultyObject,
                                monitoredValue,
                                thresholdValues,
                                info   }
        STATUS                current
        DESCRIPTION        "Spontaneous Alarm from the managed network element:
                            Access to system resources was denied (A system call exited with code -1 or -13 (EPERM and EACCESS). E.g. removing a file to becoming the super user with setuid(0) was rejected.
                            Check whether the reported account should have permission to that file and if yes, escalate to development to modify the file permission."
        ::= { eventGroupC08 42 }


        --********************************************************************
        -- Alarm Trap Definitions for alarm eventC 09: Resources
        --********************************************************************

        alarmC09001 NOTIFICATION-TYPE
        OBJECTS        {        neName,
                                neType,
                                eventGroupName,                        -- 09: Resources
                                eventName,                             -- 001: CPU
                                correlationId,
                                severity,
                                eventTime,
                                nodes,
                                faultyObject,
                                monitoredValue,
                                thresholdValues,
                                info   }
        STATUS                current
        DESCRIPTION        "Spontaneous Alarm from the managed network element:
                            CPU percentage usage in the last minute.
                            Check CPU usage with "top". It shows the processes that use the most CPU resource. Repair depending on the activities of the offending process(es), e.g. if they are in a loop then restart process might help."
        ::= { eventGroupC09 1 }

        alarmC09002 NOTIFICATION-TYPE
        OBJECTS        {        neName,
                                neType,
                                eventGroupName,                        -- 09: Resources
                                eventName,                             -- 002: RAM
                                correlationId,
                                severity,
                                eventTime,
                                nodes,
                                faultyObject,
                                monitoredValue,
                                thresholdValues,
                                info   }
        STATUS                current
        DESCRIPTION        "Spontaneous Alarm from the managed network element:
                            RAM percentage usage in the last minute. Used Memory is defined as:
used = total - free - buffers - cached.
                            Display processes that uses large amount of RAM with "top" (Enter "top" then Shift+f then n then Enter key). Processes that uses unreasonable large RAM may have a memory leak. If no process shows unreasonable larger RAM usage, additional RAM should be added to the system."
        ::= { eventGroupC09 2 }

        alarmC09003 NOTIFICATION-TYPE
        OBJECTS        {        neName,
                                neType,
                                eventGroupName,                        -- 09: Resources
                                eventName,                             -- 003: SwapFequency
                                correlationId,
                                severity,
                                eventTime,
                                nodes,
                                faultyObject,
                                monitoredValue,
                                thresholdValues,
                                info   }
        STATUS                current
        DESCRIPTION        "Spontaneous Alarm from the managed network element:
                            Total number of pages swapped in the last minute.
                            The system is low of RAM. Do not allow intensive processes running concurrently."
        ::= { eventGroupC09 3 }

        alarmC09004 NOTIFICATION-TYPE
        OBJECTS        {        neName,
                                neType,
                                eventGroupName,                        -- 09: Resources
                                eventName,                             -- 004: DiskPartitionSwap
                                correlationId,
                                severity,
                                eventTime,
                                nodes,
                                faultyObject,
                                monitoredValue,
                                thresholdValues,
                                info   }
        STATUS                current
        DESCRIPTION        "Spontaneous Alarm from the managed network element:
                            Swap partition percentage usage.
If too high the node will reboot.
                            System may be low on memory. Check whether RAM intensive processes are/were running."
        ::= { eventGroupC09 4 }

        alarmC09005 NOTIFICATION-TYPE
        OBJECTS        {        neName,
                                neType,
                                eventGroupName,                        -- 09: Resources
                                eventName,                             -- 005: DiskPartitionRoot
                                correlationId,
                                severity,
                                eventTime,
                                nodes,
                                faultyObject,
                                monitoredValue,
                                thresholdValues,
                                info   }
        STATUS                current
        DESCRIPTION        "Spontaneous Alarm from the managed network element:
                            Root (/) partition percentage usage.
If too high the node will reboot.
                            Delete unused files."
        ::= { eventGroupC09 5 }

        alarmC09006 NOTIFICATION-TYPE
        OBJECTS        {        neName,
                                neType,
                                eventGroupName,                        -- 09: Resources
                                eventName,                             -- 006: DiskPartitionVar
                                correlationId,
                                severity,
                                eventTime,
                                nodes,
                                faultyObject,
                                monitoredValue,
                                thresholdValues,
                                info   }
        STATUS                current
        DESCRIPTION        "Spontaneous Alarm from the managed network element:
                            /var partition percentage usage.
                            Delete unused files."
        ::= { eventGroupC09 6 }

        alarmC09007 NOTIFICATION-TYPE
        OBJECTS        {        neName,
                                neType,
                                eventGroupName,                        -- 09: Resources
                                eventName,                             -- 007: DiskPartitionDb
                                correlationId,
                                severity,
                                eventTime,
                                nodes,
                                faultyObject,
                                monitoredValue,
                                thresholdValues,
                                info   }
        STATUS                current
        DESCRIPTION        "Spontaneous Alarm from the managed network element:
                            /db partition percentage usage.
                            Delete unused files."
        ::= { eventGroupC09 7 }

        alarmC09008 NOTIFICATION-TYPE
        OBJECTS        {        neName,
                                neType,
                                eventGroupName,                        -- 09: Resources
                                eventName,                             -- 008: DiskPartitionTmp
                                correlationId,
                                severity,
                                eventTime,
                                nodes,
                                faultyObject,
                                monitoredValue,
                                thresholdValues,
                                info   }
        STATUS                current
        DESCRIPTION        "Spontaneous Alarm from the managed network element:
                            /tmp partition percentage usage.
If too high the node will reboot.
                            Delete unused files (check if wireshark is using up /tmp)."
        ::= { eventGroupC09 8 }

        alarmC09009 NOTIFICATION-TYPE
        OBJECTS        {        neName,
                                neType,
                                eventGroupName,                        -- 09: Resources
                                eventName,                             -- 009: DiskPartitionShared
                                correlationId,
                                severity,
                                eventTime,
                                nodes,
                                faultyObject,
                                monitoredValue,
                                thresholdValues,
                                info   }
        STATUS                current
        DESCRIPTION        "Spontaneous Alarm from the managed network element:
                            The remote shared storage of the operations node has crossed a fill level threshold. Once full log files cannot be stored anymore and analysis of instrumentation data cannot be performed anymore.
                            Check whether amount and content of stored data is justified. If yes, increase storage space. If not, delete files from storage and escalate the issue to development to check for SW errors."
        ::= { eventGroupC09 9 }

        alarmC09011 NOTIFICATION-TYPE
        OBJECTS        {        neName,
                                neType,
                                eventGroupName,                        -- 09: Resources
                                eventName,                             -- 011: LogDirectory
                                correlationId,
                                severity,
                                eventTime,
                                nodes,
                                faultyObject,
                                monitoredValue,
                                thresholdValues,
                                info   }
        STATUS                current
        DESCRIPTION        "Spontaneous Alarm from the managed network element:
                            Total space usage (GB) of /var/log partition.
                            Delete unused files."
        ::= { eventGroupC09 11 }

        alarmC09012 NOTIFICATION-TYPE
        OBJECTS        {        neName,
                                neType,
                                eventGroupName,                        -- 09: Resources
                                eventName,                             -- 012: CoreDirectory
                                correlationId,
                                severity,
                                eventTime,
                                nodes,
                                faultyObject,
                                monitoredValue,
                                thresholdValues,
                                info   }
        STATUS                current
        DESCRIPTION        "Spontaneous Alarm from the managed network element:
                            Total space usage (GB) of /var/cores partition.
                            Delete unused files."
        ::= { eventGroupC09 12 }

        alarmC09031 NOTIFICATION-TYPE
        OBJECTS        {        neName,
                                neType,
                                eventGroupName,                        -- 09: Resources
                                eventName,                             -- 031: BandwidthOAMP
                                correlationId,
                                severity,
                                eventTime,
                                nodes,
                                faultyObject,
                                monitoredValue,
                                thresholdValues,
                                info   }
        STATUS                current
        DESCRIPTION        "Spontaneous Alarm from the managed network element:
                            Bandwidth OAMP Average transmitted Mbit/s of the last minute.
                            Verify if the number is justified for this interface."
        ::= { eventGroupC09 31 }

        alarmC09032 NOTIFICATION-TYPE
        OBJECTS        {        neName,
                                neType,
                                eventGroupName,                        -- 09: Resources
                                eventName,                             -- 032: BandwidthApp
                                correlationId,
                                severity,
                                eventTime,
                                nodes,
                                faultyObject,
                                monitoredValue,
                                thresholdValues,
                                info   }
        STATUS                current
        DESCRIPTION        "Spontaneous Alarm from the managed network element:
                            Bandwidth App Average transmitted Mbit/s of the last minute.
                            Verify if the number is justified for this interface."
        ::= { eventGroupC09 32 }

        alarmC09033 NOTIFICATION-TYPE
        OBJECTS        {        neName,
                                neType,
                                eventGroupName,                        -- 09: Resources
                                eventName,                             -- 033: BandwidthExt
                                correlationId,
                                severity,
                                eventTime,
                                nodes,
                                faultyObject,
                                monitoredValue,
                                thresholdValues,
                                info   }
        STATUS                current
        DESCRIPTION        "Spontaneous Alarm from the managed network element:
                            Bandwidth Ext Average transmitted Mbit/s of the last minute.
                            Verify if the number is justified for this interface."
        ::= { eventGroupC09 33 }


        --********************************************************************
        -- Alarm Trap Definitions for alarm eventC 10: Network
        --********************************************************************

        alarmC10001 NOTIFICATION-TYPE
        OBJECTS        {        neName,
                                neType,
                                eventGroupName,                        -- 10: Network
                                eventName,                             -- 001: RouterOAMP
                                correlationId,
                                severity,
                                eventTime,
                                nodes,
                                faultyObject,
                                monitoredValue,
                                thresholdValues,
                                info   }
        STATUS                current
        DESCRIPTION        "Spontaneous Alarm from the managed network element:
                            The OAMP network router is not available as it is not responding to ARP requests which it had previously.
                            Check OAMP network. Is the router available? Is the IP address correct?"
        ::= { eventGroupC10 1 }

        alarmC10002 NOTIFICATION-TYPE
        OBJECTS        {        neName,
                                neType,
                                eventGroupName,                        -- 10: Network
                                eventName,                             -- 002: RouterApp
                                correlationId,
                                severity,
                                eventTime,
                                nodes,
                                faultyObject,
                                monitoredValue,
                                thresholdValues,
                                info   }
        STATUS                current
        DESCRIPTION        "Spontaneous Alarm from the managed network element:
                            The application network router is not available as it is not responding to ARP requests which it had previously.
                            Check application network. Is the router available? Is the IP address correct?"
        ::= { eventGroupC10 2 }

        alarmC10003 NOTIFICATION-TYPE
        OBJECTS        {        neName,
                                neType,
                                eventGroupName,                        -- 10: Network
                                eventName,                             -- 003: RouterExt
                                correlationId,
                                severity,
                                eventTime,
                                nodes,
                                faultyObject,
                                monitoredValue,
                                thresholdValues,
                                info   }
        STATUS                current
        DESCRIPTION        "Spontaneous Alarm from the managed network element:
                            The external network router is not available as it is not responding to ARP requests which it had previously.
                            Check external network. Is the router available? Is the IP address correct?"
        ::= { eventGroupC10 3 }

        alarmC10004 NOTIFICATION-TYPE
        OBJECTS        {        neName,
                                neType,
                                eventGroupName,                        -- 10: Network
                                eventName,                             -- 004: DNS
                                correlationId,
                                severity,
                                eventTime,
                                nodes,
                                faultyObject,
                                monitoredValue,
                                thresholdValues,
                                info   }
        STATUS                current
        DESCRIPTION        "Spontaneous Alarm from the managed network element:
                            A DNS server is not available as it is not responding to ARP requests which it had previously.
                            Check network. Is the DNS available? Is the IP address correct? Is the DNS reachable via the OAMP network?"
        ::= { eventGroupC10 4 }

        alarmC10005 NOTIFICATION-TYPE
        OBJECTS        {        neName,
                                neType,
                                eventGroupName,                        -- 10: Network
                                eventName,                             -- 005: NTPLossOfCommunication
                                correlationId,
                                severity,
                                eventTime,
                                nodes,
                                faultyObject,
                                monitoredValue,
                                thresholdValues,
                                info   }
        STATUS                current
        DESCRIPTION        "Spontaneous Alarm from the managed network element:
                            The reporting node cannot communicate with the NTP server(s) listed in the faultyObject.
                            The command 'ntpq -pn' can be used to show the status of the NTP server. Most communication alarms will be cleared automatically when communication is restored with the partner. If the problem causing the communication failure cannot be determined and corrected, provide Ethereal/Wireshark trace files obtained from both the reporting node as well as the communication partner in order to help determine the point of failure."
        ::= { eventGroupC10 5 }

        alarmC10006 NOTIFICATION-TYPE
        OBJECTS        {        neName,
                                neType,
                                eventGroupName,                        -- 10: Network
                                eventName,                             -- 006: NTPSynchronizationFailure
                                correlationId,
                                severity,
                                eventTime,
                                nodes,
                                faultyObject,
                                monitoredValue,
                                thresholdValues,
                                info   }
        STATUS                current
        DESCRIPTION        "Spontaneous Alarm from the managed network element:
                            The reporting node cannot synchronize the system clock with any NTP server.
                             The command 'ntpq -pn' can be used to show the status of the NTP server. Verify that the list of NTP servers is correct and analyze the command output to determine why the node could not synchronize with any listed server."
        ::= { eventGroupC10 6 }

        alarmC10007 NOTIFICATION-TYPE
        OBJECTS        {        neName,
                                neType,
                                eventGroupName,                        -- 10: Network
                                eventName,                             -- 007: NTPDaemonFailure
                                correlationId,
                                severity,
                                eventTime,
                                nodes,
                                faultyObject,
                                monitoredValue,
                                thresholdValues,
                                info   }
        STATUS                current
        DESCRIPTION        "Spontaneous Alarm from the managed network element:
                            The reporting node could not execute the ntpq -pn command. This is likely because the NTP daemon is inactive.
                             Review /var/log/messages for ntp messages and determine why the daemon exited. Execute the command 'plat_pmc show .' verify that the ntp process is not blocked. If it is, execute 'plat_pmc start ntp'."
        ::= { eventGroupC10 7 }

        alarmC10008 NOTIFICATION-TYPE
        OBJECTS        {        neName,
                                neType,
                                eventGroupName,                        -- 10: Network
                                eventName,                             -- 008: eth0LinkDown
                                correlationId,
                                severity,
                                eventTime,
                                nodes,
                                faultyObject,
                                monitoredValue,
                                thresholdValues,
                                info   }
        STATUS                current
        DESCRIPTION        "Spontaneous Alarm from the managed network element:
                            The Ethernet interface eth0 is inactive.
                            On a Virtual Machine, configure the Ethernet interface to connect to a valid port/switch. On physical hardware verify physical connectivity between the specified Ethernet port and the adjacent networking device."
        ::= { eventGroupC10 8 }

        alarmC10009 NOTIFICATION-TYPE
        OBJECTS        {        neName,
                                neType,
                                eventGroupName,                        -- 10: Network
                                eventName,                             -- 009: eth1LinkDown
                                correlationId,
                                severity,
                                eventTime,
                                nodes,
                                faultyObject,
                                monitoredValue,
                                thresholdValues,
                                info   }
        STATUS                current
        DESCRIPTION        "Spontaneous Alarm from the managed network element:
                            The Ethernet interface eth1 is inactive.
                            On a Virtual Machine, configure the Ethernet interface to connect to a valid port/switch. On physical hardware verify physical connectivity between the specified Ethernet port and the adjacent networking device."
        ::= { eventGroupC10 9 }

        alarmC10010 NOTIFICATION-TYPE
        OBJECTS        {        neName,
                                neType,
                                eventGroupName,                        -- 10: Network
                                eventName,                             -- 010: eth2LinkDown
                                correlationId,
                                severity,
                                eventTime,
                                nodes,
                                faultyObject,
                                monitoredValue,
                                thresholdValues,
                                info   }
        STATUS                current
        DESCRIPTION        "Spontaneous Alarm from the managed network element:
                            The Ethernet interface eth2 is inactive.
                            On a Virtual Machine, configure the Ethernet interface to connect to a valid port/switch. On physical hardware verify physical connectivity between the specified Ethernet port and the adjacent networking device."
        ::= { eventGroupC10 10 }

        alarmC10011 NOTIFICATION-TYPE
        OBJECTS        {        neName,
                                neType,
                                eventGroupName,                        -- 10: Network
                                eventName,                             -- 011: HardwareClockOffset
                                correlationId,
                                severity,
                                eventTime,
                                nodes,
                                faultyObject,
                                monitoredValue,
                                thresholdValues,
                                info   }
        STATUS                current
        DESCRIPTION        "Spontaneous Alarm from the managed network element:
                            The system time and the time from the hardware clock are different by the specified number of seconds.
                            Follow the documented procedures for changing the time."
        ::= { eventGroupC10 11 }

        alarmC10012 NOTIFICATION-TYPE
        OBJECTS        {        neName,
                                neType,
                                eventGroupName,                        -- 10: Network
                                eventName,                             -- 012: DNS1Response
                                correlationId,
                                severity,
                                eventTime,
                                nodes,
                                faultyObject,
                                monitoredValue,
                                thresholdValues,
                                info   }
        STATUS                current
        DESCRIPTION        "Spontaneous Alarm from the managed network element:
                            Response time from DNS1 is greater than one of the alarm thresolds.
                            Check network."
        ::= { eventGroupC10 12 }

        alarmC10013 NOTIFICATION-TYPE
        OBJECTS        {        neName,
                                neType,
                                eventGroupName,                        -- 10: Network
                                eventName,                             -- 013: DNS1Resolver
                                correlationId,
                                severity,
                                eventTime,
                                nodes,
                                faultyObject,
                                monitoredValue,
                                thresholdValues,
                                info   }
        STATUS                current
        DESCRIPTION        "Spontaneous Alarm from the managed network element:
                            FQDNs could not be resolved.
                            Check FQDNs that failed to be resolved."
        ::= { eventGroupC10 13 }

        alarmC10014 NOTIFICATION-TYPE
        OBJECTS        {        neName,
                                neType,
                                eventGroupName,                        -- 10: Network
                                eventName,                             -- 014: DNS2Response
                                correlationId,
                                severity,
                                eventTime,
                                nodes,
                                faultyObject,
                                monitoredValue,
                                thresholdValues,
                                info   }
        STATUS                current
        DESCRIPTION        "Spontaneous Alarm from the managed network element:
                            Response time from DNS2 is greater than one of the alarm thresolds.
                            Check network."
        ::= { eventGroupC10 14 }

        alarmC10015 NOTIFICATION-TYPE
        OBJECTS        {        neName,
                                neType,
                                eventGroupName,                        -- 10: Network
                                eventName,                             -- 015: DNS2Resolver
                                correlationId,
                                severity,
                                eventTime,
                                nodes,
                                faultyObject,
                                monitoredValue,
                                thresholdValues,
                                info   }
        STATUS                current
        DESCRIPTION        "Spontaneous Alarm from the managed network element:
                            FQDNs could not be resolved.
                            Check FQDNs that failed to be resolved."
        ::= { eventGroupC10 15 }


        --********************************************************************
        -- Alarm Trap Definitions for alarm eventC 12: RapidStat
        --********************************************************************

        alarmC12001 NOTIFICATION-TYPE
        OBJECTS        {        neName,
                                neType,
                                eventGroupName,                        -- 12: RapidStat
                                eventName,                             -- 001: HwClockNotSetToUTC
                                correlationId,
                                severity,
                                eventTime,
                                nodes,
                                faultyObject,
                                monitoredValue,
                                thresholdValues,
                                info   }
        STATUS                current
        DESCRIPTION        "Spontaneous Alarm from the managed network element:
                            HW clock is not set to UTC.
                            Verify that the non UTC setting is required. If not, set it back to UTC."
        ::= { eventGroupC12 1 }

        alarmC12002 NOTIFICATION-TYPE
        OBJECTS        {        neName,
                                neType,
                                eventGroupName,                        -- 12: RapidStat
                                eventName,                             -- 002: DNSrespTime
                                correlationId,
                                severity,
                                eventTime,
                                nodes,
                                faultyObject,
                                monitoredValue,
                                thresholdValues,
                                info   }
        STATUS                current
        DESCRIPTION        "Spontaneous Alarm from the managed network element:
                            DNS response time was longer than threshold.
                            Check network."
        ::= { eventGroupC12 2 }

        alarmC12003 NOTIFICATION-TYPE
        OBJECTS        {        neName,
                                neType,
                                eventGroupName,                        -- 12: RapidStat
                                eventName,                             -- 003: MailSize
                                correlationId,
                                severity,
                                eventTime,
                                nodes,
                                faultyObject,
                                monitoredValue,
                                thresholdValues,
                                info   }
        STATUS                current
        DESCRIPTION        "Spontaneous Alarm from the managed network element:
                            There are large files in /var/mail.
                            Delete the files."
        ::= { eventGroupC12 3 }

        alarmC12004 NOTIFICATION-TYPE
        OBJECTS        {        neName,
                                neType,
                                eventGroupName,                        -- 12: RapidStat
                                eventName,                             -- 004: etcVsNodecfg
                                correlationId,
                                severity,
                                eventTime,
                                nodes,
                                faultyObject,
                                monitoredValue,
                                thresholdValues,
                                info   }
        STATUS                current
        DESCRIPTION        "Spontaneous Alarm from the managed network element:
                            There are mismatched values between /etc/hosts and /etc/.xml files.
                            Escalate to next level of support."
        ::= { eventGroupC12 4 }

        alarmC12005 NOTIFICATION-TYPE
        OBJECTS        {        neName,
                                neType,
                                eventGroupName,                        -- 12: RapidStat
                                eventName,                             -- 005: ntpresolv
                                correlationId,
                                severity,
                                eventTime,
                                nodes,
                                faultyObject,
                                monitoredValue,
                                thresholdValues,
                                info   }
        STATUS                current
        DESCRIPTION        "Spontaneous Alarm from the managed network element:
                            System time not synchronized with any NTP server.
                            See repair text for NTP alarms."
        ::= { eventGroupC12 5 }

        alarmC12006 NOTIFICATION-TYPE
        OBJECTS        {        neName,
                                neType,
                                eventGroupName,                        -- 12: RapidStat
                                eventName,                             -- 006: ActAlrms
                                correlationId,
                                severity,
                                eventTime,
                                nodes,
                                faultyObject,
                                monitoredValue,
                                thresholdValues,
                                info   }
        STATUS                current
        DESCRIPTION        "Spontaneous Alarm from the managed network element:
                            There are active alarms on the system.
                            Correct the problems reported in the active alarms. If the alarm does not clear automatically delete it manually."
        ::= { eventGroupC12 6 }

        alarmC12007 NOTIFICATION-TYPE
        OBJECTS        {        neName,
                                neType,
                                eventGroupName,                        -- 12: RapidStat
                                eventName,                             -- 007: Num_pstacks
                                correlationId,
                                severity,
                                eventTime,
                                nodes,
                                faultyObject,
                                monitoredValue,
                                thresholdValues,
                                info   }
        STATUS                current
        DESCRIPTION        "Spontaneous Alarm from the managed network element:
                            Pstacks found.
                            See repair text of pstack alarms."
        ::= { eventGroupC12 7 }

        alarmC12008 NOTIFICATION-TYPE
        OBJECTS        {        neName,
                                neType,
                                eventGroupName,                        -- 12: RapidStat
                                eventName,                             -- 008: TracingOn
                                correlationId,
                                severity,
                                eventTime,
                                nodes,
                                faultyObject,
                                monitoredValue,
                                thresholdValues,
                                info   }
        STATUS                current
        DESCRIPTION        "Spontaneous Alarm from the managed network element:
                            Found active tracing.
                            Verify that tracing is still needed. If not stop tracing."
        ::= { eventGroupC12 8 }


        --********************************************************************
        -- Alarm Trap Definitions for alarm eventC 13: Logging
        --********************************************************************

        alarmC13001 NOTIFICATION-TYPE
        OBJECTS        {        neName,
                                neType,
                                eventGroupName,                        -- 13: Logging
                                eventName,                             -- 001: DeletedOpenFile
                                correlationId,
                                severity,
                                eventTime,
                                nodes,
                                faultyObject,
                                monitoredValue,
                                thresholdValues,
                                info   }
        STATUS                current
        DESCRIPTION        "Spontaneous Alarm from the managed network element:
                            A large deleted file has been detected that is still open. The associated process will be restarted. The faultyObject parameter shows file name and associated process.
                            If this happens often, escalate the alarm to development for analysis. The alarm is automatically removed after a couple of hours."
        ::= { eventGroupC13 1 }


        --********************************************************************
        -- Alarm Trap Definitions for alarm eventC 14: LogTCA
        --********************************************************************

        alarmC14001 NOTIFICATION-TYPE
        OBJECTS        {        neName,
                                neType,
                                eventGroupName,                        -- 14: LogTCA
                                eventName,                             -- 001: Platform
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category PLATFORM. See log file /var/log/platform/logging/LogNonIssues.log.
                            Review log file entries to determine source of problem."
        ::= { eventGroupC14 1 }

        alarmC14002 NOTIFICATION-TYPE
        OBJECTS        {        neName,
                                neType,
                                eventGroupName,                        -- 14: LogTCA
                                eventName,                             -- 002: Platform_Err
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category PLATFORM_ERR. See log file /var/log/platform/logging/LogIssues.log.
                            Review log file entries to determine source of problem."
        ::= { eventGroupC14 2 }

        alarmC14003 NOTIFICATION-TYPE
        OBJECTS        {        neName,
                                neType,
                                eventGroupName,                        -- 14: LogTCA
                                eventName,                             -- 003: Audit
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category AUDIT. See log file /var/log/platform/logging/LogNonIssues.log.
                            Review log file entries to determine source of problem."
        ::= { eventGroupC14 3 }

        alarmC14004 NOTIFICATION-TYPE
        OBJECTS        {        neName,
                                neType,
                                eventGroupName,                        -- 14: LogTCA
                                eventName,                             -- 004: Audit_Err
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category AUDIT_ERR. See log file /var/log/platform/logging/LogIssues.log.
                            Review log file entries to determine source of problem."
        ::= { eventGroupC14 4 }

        alarmC14005 NOTIFICATION-TYPE
        OBJECTS        {        neName,
                                neType,
                                eventGroupName,                        -- 14: LogTCA
                                eventName,                             -- 005: Com_Err
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category COM_ERR. See log file /var/log/platform/logging/LogIssues.log.
                            Review log file entries to determine source of problem."
        ::= { eventGroupC14 5 }

        alarmC14006 NOTIFICATION-TYPE
        OBJECTS        {        neName,
                                neType,
                                eventGroupName,                        -- 14: LogTCA
                                eventName,                             -- 006: SW_Err
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category SW_ERR. See log file /var/log/platform/logging/LogIssues.log.
                            Review log file entries to determine source of problem."
        ::= { eventGroupC14 6 }

        alarmC14007 NOTIFICATION-TYPE
        OBJECTS        {        neName,
                                neType,
                                eventGroupName,                        -- 14: LogTCA
                                eventName,                             -- 007: Data_Err
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category DATA_ERR. See log file /var/log/platform/logging/LogIssues.log.
                            Review log file entries to determine source of problem."
        ::= { eventGroupC14 7 }

        alarmC14008 NOTIFICATION-TYPE
        OBJECTS        {        neName,
                                neType,
                                eventGroupName,                        -- 14: LogTCA
                                eventName,                             -- 008: Alarm
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category ALARM. See log file /var/log/platform/logging/LogAlarm.log.
                            Review log file entries to determine source of problem."
        ::= { eventGroupC14 8 }

        alarmC14009 NOTIFICATION-TYPE
        OBJECTS        {        neName,
                                neType,
                                eventGroupName,                        -- 14: LogTCA
                                eventName,                             -- 009: Alarm_Clear
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category ALARM_CLEAR. See log file /var/log/platform/logging/LogAlarm.log.
                            Review log file entries to determine source of problem."
        ::= { eventGroupC14 9 }

        alarmC14010 NOTIFICATION-TYPE
        OBJECTS        {        neName,
                                neType,
                                eventGroupName,                        -- 14: LogTCA
                                eventName,                             -- 010: Alarm_Mgr
                                correlationId,
                                severity,
                                eventTime,
                                nodes,
                                faultyObject,
                                monitoredValue,
                                thresholdValues,
                                info   }
        STATUS                current
        DESCRIPTION        "Spontaneous Alarm from the managed network element:
                            The number of events has crossed one of the thresholds within the last 15 minutes for the category ALARM_MGR. See log file /var/log/platform/logging/LogAlarm.log.
                            Review log file entries to determine source of problem."
        ::= { eventGroupC14 10 }


        --********************************************************************
        -- Alarm Trap Definitions for alarm eventC 17: SNMPTrap
        --********************************************************************

        alarmC17001 NOTIFICATION-TYPE
        OBJECTS        {        neName,
                                neType,
                                eventGroupName,                        -- 17: SNMPTrap
                                eventName,                             -- 001: SnmpOpenFailure
                                correlationId,
                                severity,
                                eventTime,
                                nodes,
                                faultyObject,
                                monitoredValue,
                                thresholdValues,
                                info   }
        STATUS                current
        DESCRIPTION        "Spontaneous Alarm from the managed network element:
                            Call to snmp_open failed.
                            Look at faulty object and correct accordingly (if possible)."
        ::= { eventGroupC17 1 }

        alarmC17002 NOTIFICATION-TYPE
        OBJECTS        {        neName,
                                neType,
                                eventGroupName,                        -- 17: SNMPTrap
                                eventName,                             -- 002: SnmpSendFailure
                                correlationId,
                                severity,
                                eventTime,
                                nodes,
                                faultyObject,
                                monitoredValue,
                                thresholdValues,
                                info   }
        STATUS                current
        DESCRIPTION        "Spontaneous Alarm from the managed network element:
                            Call to snmp_synch_response failed.
                            Look at faulty object and correct accordingly (if possible)."
        ::= { eventGroupC17 2 }


        --********************************************************************
        -- Alarm Trap Definitions for alarm eventC 20: Zoo
        --********************************************************************

        alarmC20001 NOTIFICATION-TYPE
        OBJECTS        {        neName,
                                neType,
                                eventGroupName,                        -- 20: Zoo
                                eventName,                             -- 001: ZooConnectionFailure
                                correlationId,
                                severity,
                                eventTime,
                                nodes,
                                faultyObject,
                                monitoredValue,
                                thresholdValues,
                                info   }
        STATUS                current
        DESCRIPTION        "Spontaneous Alarm from the managed network element:
                            A connection from the platform ZooKeeper Client to a ZooKeeper server could not be established. A quorum of ZooKeeper servers may not be active or may be misconfigured. The ZooKeeper client on the platform may not have a valid configuration. Network failures can also cause this alarm.
                            Ping the ZooKeeper servers from the reporting node to determine if a network problem exists. Verify that a quorum of ZooKeeper servers is active (e.g. at least two servers are active in a three-zookeeper-node ensemble). Verify that the reporting node was deployed correctly and has received the correct configuration in the 'goahead' message. If problem persists, execute 'plat_rapidstat -c' to collect data on the reporting node, all of the ZooKeeper servers."
        ::= { eventGroupC20 1 }

        alarmC20002 NOTIFICATION-TYPE
        OBJECTS        {        neName,
                                neType,
                                eventGroupName,                        -- 20: Zoo
                                eventName,                             -- 002: ZooConfigCorrupted
                                correlationId,
                                severity,
                                eventTime,
                                nodes,
                                faultyObject,
                                monitoredValue,
                                thresholdValues,
                                info   }
        STATUS                current
        DESCRIPTION        "Spontaneous Alarm from the managed network element:
                            Configuration retrieved via ZooKeeper server was corrupt and cannot be parsed.
                            The ZooKeeper znodes that are corrupt are listed with the alarm. Use the Management node application to correct the node configuration. If problem persists, execute 'plat_rapidstat -c' to collect data on the reporting node, Management node, and one of the active ZooKeeper servers."
        ::= { eventGroupC20 2 }

        alarmC20003 NOTIFICATION-TYPE
        OBJECTS        {        neName,
                                neType,
                                eventGroupName,                        -- 20: Zoo
                                eventName,                             -- 003: ZooConfigUnavailable
                                correlationId,
                                severity,
                                eventTime,
                                nodes,
                                faultyObject,
                                monitoredValue,
                                thresholdValues,
                                info   }
        STATUS                current
        DESCRIPTION        "Spontaneous Alarm from the managed network element:
                            Configuration could not be retrieved from a ZooKeeper server.
                            The ZooKeeper znodes that could not be retrieved are listed with the alarm. If data has not been populated on the ZooKeeper servers, use the Management node to configure and populate the data. If problem persists, execute 'plat_rapidstat -c' to collect data on the reporting node as well as one of the active ZooKeeper servers."
        ::= { eventGroupC20 3 }

        alarmC20004 NOTIFICATION-TYPE
        OBJECTS        {        neName,
                                neType,
                                eventGroupName,                        -- 20: Zoo
                                eventName,                             -- 004: ZookeeperResponseTime
                                correlationId,
                                severity,
                                eventTime,
                                nodes,
                                faultyObject,
                                monitoredValue,
                                thresholdValues,
                                info   }
        STATUS                current
        DESCRIPTION        "Spontaneous Alarm from the managed network element:
                            A ZooKeeper server did not respond to a request from the client within the expected response time.
                            The problem could be caused by network problems or by an overloaded ZooKeeper server. If problem persists, execute 'plat_rapidstat -c' to collection data on the reporting node and on each active ZooKeeper server node."
        ::= { eventGroupC20 4 }

        alarmC20005 NOTIFICATION-TYPE
        OBJECTS        {        neName,
                                neType,
                                eventGroupName,                        -- 20: Zoo
                                eventName,                             -- 005: WrongNodeTypeInGoAhead
                                correlationId,
                                severity,
                                eventTime,
                                nodes,
                                faultyObject,
                                monitoredValue,
                                thresholdValues,
                                info   }
        STATUS                current
        DESCRIPTION        "Spontaneous Alarm from the managed network element:
                            The node name received in the GoAhead configuration does not match the node type set by production in the file /etc/platform/type.
                            If the GoAhead was sent to this node in error, send the correct GoAhead to this node. If the node was deployed with the wrong OVF/OVA, redeploy with the correct one and re-send the GoAhead."
        ::= { eventGroupC20 5 }


        --********************************************************************
        -- Alarm Trap Definitions for alarm eventC 21: IDS
        --********************************************************************

        alarmC21001 NOTIFICATION-TYPE
        OBJECTS        {        neName,
                                neType,
                                eventGroupName,                        -- 21: IDS
                                eventName,                             -- 001: DoS
                                correlationId,
                                severity,
                                eventTime,
                                nodes,
                                faultyObject,
                                monitoredValue,
                                thresholdValues,
                                info   }
        STATUS                current
        DESCRIPTION        "Spontaneous Alarm from the managed network element:
                            Denial Of Service Attempt Detected.
                            None."
        ::= { eventGroupC21 1 }


        --********************************************************************
        -- Alarm Trap Definitions for alarm eventC 22: SNMP
        --********************************************************************

        alarmC22001 NOTIFICATION-TYPE
        OBJECTS        {        neName,
                                neType,
                                eventGroupName,                        -- 22: SNMP
                                eventName,                             -- 001: SnmpReconfigError
                                correlationId,
                                severity,
                                eventTime,
                                nodes,
                                faultyObject,
                                monitoredValue,
                                thresholdValues,
                                info   }
        STATUS                current
        DESCRIPTION        "Spontaneous Alarm from the managed network element:
                            SnmpV3 Users not created successfully
                            Check if all necessary credentials for SnmpV3 Users are defined in Network.xml.If not update file."
        ::= { eventGroupC22 1 }


        --********************************************************************
        -- Alarm Trap Definitions for alarm eventC 23: Syslog
        --********************************************************************

        alarmC23001 NOTIFICATION-TYPE
        OBJECTS        {        neName,
                                neType,
                                eventGroupName,                        -- 23: Syslog
                                eventName,                             -- 001: Emerg
                                correlationId,
                                severity,
                                eventTime,
                                nodes,
                                faultyObject,
                                monitoredValue,
                                thresholdValues,
                                info   }
        STATUS                current
        DESCRIPTION        "Spontaneous Alarm from the managed network element:
                            Emgergency syslog failure.
                            Look at syslog entries and correct problem."
        ::= { eventGroupC23 1 }

        alarmC23002 NOTIFICATION-TYPE
        OBJECTS        {        neName,
                                neType,
                                eventGroupName,                        -- 23: Syslog
                                eventName,                             -- 002: Alert
                                correlationId,
                                severity,
                                eventTime,
                                nodes,
                                faultyObject,
                                monitoredValue,
                                thresholdValues,
                                info   }
        STATUS                current
        DESCRIPTION        "Spontaneous Alarm from the managed network element:
                            Alert syslog failure.
                            Look at syslog entries and correct problem."
        ::= { eventGroupC23 2 }

        alarmC23003 NOTIFICATION-TYPE
        OBJECTS        {        neName,
                                neType,
                                eventGroupName,                        -- 23: Syslog
                                eventName,                             -- 003: Crit
                                correlationId,
                                severity,
                                eventTime,
                                nodes,
                                faultyObject,
                                monitoredValue,
                                thresholdValues,
                                info   }
        STATUS                current
        DESCRIPTION        "Spontaneous Alarm from the managed network element:
                            Critical syslog failure.
                            Look at syslog entries and correct problem."
        ::= { eventGroupC23 3 }

        alarmC23004 NOTIFICATION-TYPE
        OBJECTS        {        neName,
                                neType,
                                eventGroupName,                        -- 23: Syslog
                                eventName,                             -- 004: Error
                                correlationId,
                                severity,
                                eventTime,
                                nodes,
                                faultyObject,
                                monitoredValue,
                                thresholdValues,
                                info   }
        STATUS                current
        DESCRIPTION        "Spontaneous Alarm from the managed network element:
                            Error syslog failure.
                            Look at syslog entries and correct problem."
        ::= { eventGroupC23 4 }


        --********************************************************************
        -- Alarm Trap Definitions for alarm eventC 50: Connectivity
        --********************************************************************

        alarmC50001 NOTIFICATION-TYPE
        OBJECTS        {        neName,
                                neType,
                                eventGroupName,                        -- 50: Connectivity
                                eventName,                             -- 001: SmartCloudConnectionFailure
                                correlationId,
                                severity,
                                eventTime,
                                nodes,
                                faultyObject,
                                monitoredValue,
                                thresholdValues,
                                info   }
        STATUS                current
        DESCRIPTION        "Spontaneous Alarm from the managed network element:
                            Smart Cloud Connection failure.
                            Check if the Access node has internet connection and can reach the Cloud server."
        ::= { eventGroupC50 1 }

        alarmC50002 NOTIFICATION-TYPE
        OBJECTS        {        neName,
                                neType,
                                eventGroupName,                        -- 50: Connectivity
                                eventName,                             -- 002: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC50 2 }

        alarmC50003 NOTIFICATION-TYPE
        OBJECTS        {        neName,
                                neType,
                                eventGroupName,                        -- 50: Connectivity
                                eventName,                             -- 003: FileApiSocketsUsage
                                correlationId,
                                severity,
                                eventTime,
                                nodes,
                                faultyObject,
                                monitoredValue,
                                thresholdValues,
                                info   }
        STATUS                current
        DESCRIPTION        "Spontaneous Alarm from the managed network element:
                            The percentage of used concurrent sockets in fileApi between Access Server and IBM crossed the defined threshold.
                            Check if it is necessary to increase the number of concurrent sockets in fileApi."
        ::= { eventGroupC50 3 }

        alarmC50005 NOTIFICATION-TYPE
        OBJECTS        {        neName,
                                neType,
                                eventGroupName,                        -- 50: Connectivity
                                eventName,                             -- 005: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC50 5 }

        alarmC50006 NOTIFICATION-TYPE
        OBJECTS        {        neName,
                                neType,
                                eventGroupName,                        -- 50: Connectivity
                                eventName,                             -- 006: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC50 6 }

        alarmC50007 NOTIFICATION-TYPE
        OBJECTS        {        neName,
                                neType,
                                eventGroupName,                        -- 50: Connectivity
                                eventName,                             -- 007: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC50 7 }

        alarmC50011 NOTIFICATION-TYPE
        OBJECTS        {        neName,
                                neType,
                                eventGroupName,                        -- 50: Connectivity
                                eventName,                             -- 011: ConnectionsResponseTime
                                correlationId,
                                severity,
                                eventTime,
                                nodes,
                                faultyObject,
                                monitoredValue,
                                thresholdValues,
                                info   }
        STATUS                current
        DESCRIPTION        "Spontaneous Alarm from the managed network element:
                            Smart Cloud Connection response time too high.
                            Check whether the high response time is justified. If not check the network and processed traffic. Are additional nodes needed? Is Smart Cloud overloaded?"
        ::= { eventGroupC50 11 }

        alarmC50015 NOTIFICATION-TYPE
        OBJECTS        {        neName,
                                neType,
                                eventGroupName,                        -- 50: Connectivity
                                eventName,                             -- 015: ConnectionsActivityServiceFailure
                                correlationId,
                                severity,
                                eventTime,
                                nodes,
                                faultyObject,
                                monitoredValue,
                                thresholdValues,
                                info   }
        STATUS                current
        DESCRIPTION        "Spontaneous Alarm from the managed network element:
                            Connectivity could not be established with the IBM Connections Activity Service.
                            Check if the Access node has internet connection and can reach the Cloud server."
        ::= { eventGroupC50 15 }

        alarmC50016 NOTIFICATION-TYPE
        OBJECTS        {        neName,
                                neType,
                                eventGroupName,                        -- 50: Connectivity
                                eventName,                             -- 016: ConnectionsFileServiceFailure
                                correlationId,
                                severity,
                                eventTime,
                                nodes,
                                faultyObject,
                                monitoredValue,
                                thresholdValues,
                                info   }
        STATUS                current
        DESCRIPTION        "Spontaneous Alarm from the managed network element:
                            Connectivity could not be established with the IBM Connections File Service.
                            Check if the Access node has internet connection and can reach the Cloud server."
        ::= { eventGroupC50 16 }

        alarmC50017 NOTIFICATION-TYPE
        OBJECTS        {        neName,
                                neType,
                                eventGroupName,                        -- 50: Connectivity
                                eventName,                             -- 017: ConnectionsBSSServiceFailure
                                correlationId,
                                severity,
                                eventTime,
                                nodes,
                                faultyObject,
                                monitoredValue,
                                thresholdValues,
                                info   }
        STATUS                current
        DESCRIPTION        "Spontaneous Alarm from the managed network element:
                            Connectivity could not be established with the IBM Connections BSS Service.
                            Check if the Access node has internet connection and can reach the Cloud server."
        ::= { eventGroupC50 17 }

        alarmC50018 NOTIFICATION-TYPE
        OBJECTS        {        neName,
                                neType,
                                eventGroupName,                        -- 50: Connectivity
                                eventName,                             -- 018: ConnectionsSearchServiceFailure
                                correlationId,
                                severity,
                                eventTime,
                                nodes,
                                faultyObject,
                                monitoredValue,
                                thresholdValues,
                                info   }
        STATUS                current
        DESCRIPTION        "Spontaneous Alarm from the managed network element:
                            Connectivity could not be established with the IBM Connections Search Service.
                            Check if the Access node has internet connection and can reach the Cloud server."
        ::= { eventGroupC50 18 }

        alarmC50021 NOTIFICATION-TYPE
        OBJECTS        {        neName,
                                neType,
                                eventGroupName,                        -- 50: Connectivity
                                eventName,                             -- 021: LossOfComSMTP
                                correlationId,
                                severity,
                                eventTime,
                                nodes,
                                faultyObject,
                                monitoredValue,
                                thresholdValues,
                                info   }
        STATUS                current
        DESCRIPTION        "Spontaneous Alarm from the managed network element:
                            The IMP application node has lost connectivity with the SMTP server identified in the faultyObject parameter.
                            Check the network (router, firewall, LAN). Check whether the SMTP server is out of service."
        ::= { eventGroupC50 21 }

        alarmC50051 NOTIFICATION-TYPE
        OBJECTS        {        neName,
                                neType,
                                eventGroupName,                        -- 50: Connectivity
                                eventName,                             -- 051: LossOfComApp
                                correlationId,
                                severity,
                                eventTime,
                                nodes,
                                faultyObject,
                                monitoredValue,
                                thresholdValues,
                                info   }
        STATUS                current
        DESCRIPTION        "Spontaneous Alarm from the managed network element:
                            Access server lost communication with Application node.
                            The Application node maybe down, check the network setup. Also check the node configuration files and logs."
        ::= { eventGroupC50 51 }

        alarmC50061 NOTIFICATION-TYPE
        OBJECTS        {        neName,
                                neType,
                                eventGroupName,                        -- 50: Connectivity
                                eventName,                             -- 061: LossOfComAccClient
                                correlationId,
                                severity,
                                eventTime,
                                nodes,
                                faultyObject,
                                monitoredValue,
                                thresholdValues,
                                info   }
        STATUS                current
        DESCRIPTION        "Spontaneous Alarm from the managed network element:
                            Access server lost communication with Accces Client node.
                            Check that all nodes of the solution are active."
        ::= { eventGroupC50 61 }

        alarmC50062 NOTIFICATION-TYPE
        OBJECTS        {        neName,
                                neType,
                                eventGroupName,                        -- 50: Connectivity
                                eventName,                             -- 062: LossOfComAccServer
                                correlationId,
                                severity,
                                eventTime,
                                nodes,
                                faultyObject,
                                monitoredValue,
                                thresholdValues,
                                info   }
        STATUS                current
        DESCRIPTION        "Spontaneous Alarm from the managed network element:
                            Access server lost communication with Accces Server node.
                            Check that all nodes of the solution are active."
        ::= { eventGroupC50 62 }

        alarmC50071 NOTIFICATION-TYPE
        OBJECTS        {        neName,
                                neType,
                                eventGroupName,                        -- 50: Connectivity
                                eventName,                             -- 071: LossOfComAcc
                                correlationId,
                                severity,
                                eventTime,
                                nodes,
                                faultyObject,
                                monitoredValue,
                                thresholdValues,
                                info   }
        STATUS                current
        DESCRIPTION        "Spontaneous Alarm from the managed network element:
                            Server lost communication with Access node.
                            The Access node maybe down, check the network setup. Also check the node configuration files and logs."
        ::= { eventGroupC50 71 }


        --********************************************************************
        -- Alarm Trap Definitions for alarm eventC 53: Turn
        --********************************************************************

        alarmC53001 NOTIFICATION-TYPE
        OBJECTS        {        neName,
                                neType,
                                eventGroupName,                        -- 53: Turn
                                eventName,                             -- 001: LackOfUDPPorts
                                correlationId,
                                severity,
                                eventTime,
                                nodes,
                                faultyObject,
                                monitoredValue,
                                thresholdValues,
                                info   }
        STATUS                current
        DESCRIPTION        "Spontaneous Alarm from the managed network element:
                            Turn has used more UDP ports than one of the configured thresholds.
                            Escalate to next level of support to analyze the traffic."
        ::= { eventGroupC53 1 }


        --********************************************************************
        -- Alarm Trap Definitions for alarm eventC 54: LB
        --********************************************************************

        alarmC54001 NOTIFICATION-TYPE
        OBJECTS        {        neName,
                                neType,
                                eventGroupName,                        -- 54: LB
                                eventName,                             -- 001: LossOfRedundancy
                                correlationId,
                                severity,
                                eventTime,
                                nodes,
                                faultyObject,
                                monitoredValue,
                                thresholdValues,
                                info   }
        STATUS                current
        DESCRIPTION        "Spontaneous Alarm from the managed network element:
                            LB node lost its partner and now runs as master without backup.
                            Repair the LB partner node."
        ::= { eventGroupC54 1 }

        alarmC54002 NOTIFICATION-TYPE
        OBJECTS        {        neName,
                                neType,
                                eventGroupName,                        -- 54: LB
                                eventName,                             -- 002: FaultyConfiguration
                                correlationId,
                                severity,
                                eventTime,
                                nodes,
                                faultyObject,
                                monitoredValue,
                                thresholdValues,
                                info   }
        STATUS                current
        DESCRIPTION        "Spontaneous Alarm from the managed network element:
                            LB configuration file is faulty. LB functionality is restricted.
                            Review log file entries to determine source of problem."
        ::= { eventGroupC54 2 }


        --********************************************************************
        -- Alarm Trap Definitions for alarm eventC 55: Analytics
        --********************************************************************

        alarmC55001 NOTIFICATION-TYPE
        OBJECTS        {        neName,
                                neType,
                                eventGroupName,                        -- 55: Analytics
                                eventName,                             -- 001: HadoopNoSpace
                                correlationId,
                                severity,
                                eventTime,
                                nodes,
                                faultyObject,
                                monitoredValue,
                                thresholdValues,
                                info   }
        STATUS                current
        DESCRIPTION        "Spontaneous Alarm from the managed network element:
                            Hadoop did not start because there is no available disk space in /db/data. As a consequence the features log archiving and analytics are not available.
                            Free up space in /db or add more disk space to /db/data. Then change the operations  node status to locked and back to active to restart the application."
        ::= { eventGroupC55 1 }

        alarmC55002 NOTIFICATION-TYPE
        OBJECTS        {        neName,
                                neType,
                                eventGroupName,                        -- 55: Analytics
                                eventName,                             -- 002: DataLoaderFailure
                                correlationId,
                                severity,
                                eventTime,
                                nodes,
                                faultyObject,
                                monitoredValue,
                                thresholdValues,
                                info   }
        STATUS                current
        DESCRIPTION        "Spontaneous Alarm from the managed network element:
                            Unable to load the instrumentation data. See the analytics log file for details.
                            Resolve any issues found in the analytics log file and then either manually launch the loader or wait until the next maintenance window."
        ::= { eventGroupC55 2 }


        --********************************************************************
        -- Alarm Trap Definitions for alarm eventC 56: MediaServer
        --********************************************************************

        alarmC56001 NOTIFICATION-TYPE
        OBJECTS        {        neName,
                                neType,
                                eventGroupName,                        -- 56: MediaServer
                                eventName,                             -- 001: SIPTrunkMissing
                                correlationId,
                                severity,
                                eventTime,
                                nodes,
                                faultyObject,
                                monitoredValue,
                                thresholdValues,
                                info   }
        STATUS                current
        DESCRIPTION        "Spontaneous Alarm from the managed network element:
                            Wrong SIP trunk configuration.
                            Escalate to next level of support."
        ::= { eventGroupC56 1 }

        alarmC56002 NOTIFICATION-TYPE
        OBJECTS        {        neName,
                                neType,
                                eventGroupName,                        -- 56: MediaServer
                                eventName,                             -- 002: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 2 }

        alarmC56003 NOTIFICATION-TYPE
        OBJECTS        {        neName,
                                neType,
                                eventGroupName,                        -- 56: MediaServer
                                eventName,                             -- 003: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 3 }

        alarmC56004 NOTIFICATION-TYPE
        OBJECTS        {        neName,
                                neType,
                                eventGroupName,                        -- 56: MediaServer
                                eventName,                             -- 004: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 4 }

        alarmC56005 NOTIFICATION-TYPE
        OBJECTS        {        neName,
                                neType,
                                eventGroupName,                        -- 56: MediaServer
                                eventName,                             -- 005: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 5 }

        alarmC56010 NOTIFICATION-TYPE
        OBJECTS        {        neName,
                                neType,
                                eventGroupName,                        -- 56: MediaServer
                                eventName,                             -- 010: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 10 }

        alarmC56011 NOTIFICATION-TYPE
        OBJECTS        {        neName,
                                neType,
                                eventGroupName,                        -- 56: MediaServer
                                eventName,                             -- 011: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 11 }

        alarmC56020 NOTIFICATION-TYPE
        OBJECTS        {        neName,
                                neType,
                                eventGroupName,                        -- 56: MediaServer
                                eventName,                             -- 020: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 20 }

        alarmC56021 NOTIFICATION-TYPE
        OBJECTS        {        neName,
                                neType,
                                eventGroupName,                        -- 56: MediaServer
                                eventName,                             -- 021: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 21 }

        alarmC56030 NOTIFICATION-TYPE
        OBJECTS        {        neName,
                                neType,
                                eventGroupName,                        -- 56: MediaServer
                                eventName,                             -- 030: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 30 }

        alarmC56031 NOTIFICATION-TYPE
        OBJECTS        {        neName,
                                neType,
                                eventGroupName,                        -- 56: MediaServer
                                eventName,                             -- 031: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 31 }

        alarmC56033 NOTIFICATION-TYPE
        OBJECTS        {        neName,
                                neType,
                                eventGroupName,                        -- 56: MediaServer
                                eventName,                             -- 033: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 33 }

        alarmC56040 NOTIFICATION-TYPE
        OBJECTS        {        neName,
                                neType,
                                eventGroupName,                        -- 56: MediaServer
                                eventName,                             -- 040: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 40 }

        alarmC56041 NOTIFICATION-TYPE
        OBJECTS        {        neName,
                                neType,
                                eventGroupName,                        -- 56: MediaServer
                                eventName,                             -- 041: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 41 }

        alarmC56042 NOTIFICATION-TYPE
        OBJECTS        {        neName,
                                neType,
                                eventGroupName,                        -- 56: MediaServer
                                eventName,                             -- 042: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 42 }

        alarmC56050 NOTIFICATION-TYPE
        OBJECTS        {        neName,
                                neType,
                                eventGroupName,                        -- 56: MediaServer
                                eventName,                             -- 050: N/A
                                correlationId,
                                severity,
                                eventTime,
                                nodes,
                                faultyObject,
                                monitoredValue,
                                thresholdValues,
                                info   }
        STATUS                obsolete
        DESCRIPTION        "Spontaneous Alarm from the managed network element:
                            Deprecated alarm
                            None"
        ::= { eventGroupC56 50 }

        alarmC56100 NOTIFICATION-TYPE
        OBJECTS        {        neName,
                                neType,
                                eventGroupName,                        -- 56: MediaServer
                                eventName,                             -- 100: SipStackStartupProblem
                                correlationId,
                                severity,
                                eventTime,
                                nodes,
                                faultyObject,
                                monitoredValue,
                                thresholdValues,
                                info   }
        STATUS                current
        DESCRIPTION        "Spontaneous Alarm from the managed network element:
                            SIP stack startup problem
SIP Connectivity Provider,Failed to create a sip stack instance.
                            Please check the log for further information."
        ::= { eventGroupC56 100 }

        alarmC56101 NOTIFICATION-TYPE
        OBJECTS        {        neName,
                                neType,
                                eventGroupName,                        -- 56: MediaServer
                                eventName,                             -- 101: SipStackStartupProblemListening
                                correlationId,
                                severity,
                                eventTime,
                                nodes,
                                faultyObject,
                                monitoredValue,
                                thresholdValues,
                                info   }
        STATUS                current
        DESCRIPTION        "Spontaneous Alarm from the managed network element:
                            Startup problem with a SIP stack listening point

Failed to create a listening point. Maybe address or port is in use.
                            Please check listeningPoint settings in the management UI or in the sip-connectivity.xml file."
        ::= { eventGroupC56 101 }

        alarmC56102 NOTIFICATION-TYPE
        OBJECTS        {        neName,
                                neType,
                                eventGroupName,                        -- 56: MediaServer
                                eventName,                             -- 102: SipStackStartupProblemInternal
                                correlationId,
                                severity,
                                eventTime,
                                nodes,
                                faultyObject,
                                monitoredValue,
                                thresholdValues,
                                info   }
        STATUS                current
        DESCRIPTION        "Spontaneous Alarm from the managed network element:
                            Startup problem due to internal SIP stack error

Failed to create sip provider instance.
                            Please check the log for further information."
        ::= { eventGroupC56 102 }

        alarmC56103 NOTIFICATION-TYPE
        OBJECTS        {        neName,
                                neType,
                                eventGroupName,                        -- 56: MediaServer
                                eventName,                             -- 103: SipStackStartupProblemInternal2
                                correlationId,
                                severity,
                                eventTime,
                                nodes,
                                faultyObject,
                                monitoredValue,
                                thresholdValues,
                                info   }
        STATUS                current
        DESCRIPTION        "Spontaneous Alarm from the managed network element:
                            Startup problem due to internal SIP stack error

Failed to register SipManager as a SIP listener.
                            Please check the log for further information."
        ::= { eventGroupC56 103 }

        alarmC56104 NOTIFICATION-TYPE
        OBJECTS        {        neName,
                                neType,
                                eventGroupName,                        -- 56: MediaServer
                                eventName,                             -- 104: SipStackShutdownProblem
                                correlationId,
                                severity,
                                eventTime,
                                nodes,
                                faultyObject,
                                monitoredValue,
                                thresholdValues,
                                info   }
        STATUS                current
        DESCRIPTION        "Spontaneous Alarm from the managed network element:
                            SIP stack shutdown problem

Failed to delete a SipProvider instance from sip stack.
                            Please check the log for further information."
        ::= { eventGroupC56 104 }

        alarmC56105 NOTIFICATION-TYPE
        OBJECTS        {        neName,
                                neType,
                                eventGroupName,                        -- 56: MediaServer
                                eventName,                             -- 105: SipStackShutdownProblem2
                                correlationId,
                                severity,
                                eventTime,
                                nodes,
                                faultyObject,
                                monitoredValue,
                                thresholdValues,
                                info   }
        STATUS                current
        DESCRIPTION        "Spontaneous Alarm from the managed network element:
                            SIP stack shutdown problem

Failed to delete a listening point from sip stack.
                            Please check the log for further information."
        ::= { eventGroupC56 105 }

        alarmC56106 NOTIFICATION-TYPE
        OBJECTS        {        neName,
                                neType,
                                eventGroupName,                        -- 56: MediaServer
                                eventName,                             -- 106: SipProviderConfMissing
                                correlationId,
                                severity,
                                eventTime,
                                nodes,
                                faultyObject,
                                monitoredValue,
                                thresholdValues,
                                info   }
        STATUS                current
        DESCRIPTION        "Spontaneous Alarm from the managed network element:
                            SIP provider startup failed: configuration is missing

Failed to start SIP provider due to missing configuration.
                            Please check the log for further information."
        ::= { eventGroupC56 106 }

        alarmC56107 NOTIFICATION-TYPE
        OBJECTS        {        neName,
                                neType,
                                eventGroupName,                        -- 56: MediaServer
                                eventName,                             -- 107: SipProviderSdpParserMissing
                                correlationId,
                                severity,
                                eventTime,
                                nodes,
                                faultyObject,
                                monitoredValue,
                                thresholdValues,
                                info   }
        STATUS                current
        DESCRIPTION        "Spontaneous Alarm from the managed network element:
                            SIP provider startup failed: SDP parser missing

Failed to start SIP provider due to missing SDP parser component.
                            Please check the log for further information."
        ::= { eventGroupC56 107 }

        alarmC56108 NOTIFICATION-TYPE
        OBJECTS        {        neName,
                                neType,
                                eventGroupName,                        -- 56: MediaServer
                                eventName,                             -- 108: SipProviderAddrTransCompMissing
                                correlationId,
                                severity,
                                eventTime,
                                nodes,
                                faultyObject,
                                monitoredValue,
                                thresholdValues,
                                info   }
        STATUS                current
        DESCRIPTION        "Spontaneous Alarm from the managed network element:
                            SIP provider startup failed: Address Translation component missing.

Failed to start SIP provider due to missing Address Translation component.
                            Please check the log for further information."
        ::= { eventGroupC56 108 }

        alarmC56109 NOTIFICATION-TYPE
        OBJECTS        {        neName,
                                neType,
                                eventGroupName,                        -- 56: MediaServer
                                eventName,                             -- 109: SipProviderLocationDBCompMissing
                                correlationId,
                                severity,
                                eventTime,
                                nodes,
                                faultyObject,
                                monitoredValue,
                                thresholdValues,
                                info   }
        STATUS                current
        DESCRIPTION        "Spontaneous Alarm from the managed network element:
                            SIP provider startup failed: Location Database component missing

Failed to start SIP provider due to missing Location Database component.
                            Please check the log for further information."
        ::= { eventGroupC56 109 }

        alarmC56110 NOTIFICATION-TYPE
        OBJECTS        {        neName,
                                neType,
                                eventGroupName,                        -- 56: MediaServer
                                eventName,                             -- 110: SipProviderStartFailure
                                correlationId,
                                severity,
                                eventTime,
                                nodes,
                                faultyObject,
                                monitoredValue,
                                thresholdValues,
                                info   }
        STATUS                current
        DESCRIPTION        "Spontaneous Alarm from the managed network element:
                            Failed to start sip provider

Internal SIP manager startup problem.
                            Please check the log for further information."
        ::= { eventGroupC56 110 }

        alarmC56200 NOTIFICATION-TYPE
        OBJECTS        {        neName,
                                neType,
                                eventGroupName,                        -- 56: MediaServer
                                eventName,                             -- 200: MFWProviderMissing
                                correlationId,
                                severity,
                                eventTime,
                                nodes,
                                faultyObject,
                                monitoredValue,
                                thresholdValues,
                                info   }
        STATUS                current
        DESCRIPTION        "Spontaneous Alarm from the managed network element:
                            Missing MFW provider

Could not get MediaFramework (MFW) provider from Application Host. Processing of streaming data will not work.
                            Check log-output for more details."
        ::= { eventGroupC56 200 }

        alarmC56202 NOTIFICATION-TYPE
        OBJECTS        {        neName,
                                neType,
                                eventGroupName,                        -- 56: MediaServer
                                eventName,                             -- 202: MPSMediaProcessingProviderInitFailure
                                correlationId,
                                severity,
                                eventTime,
                                nodes,
                                faultyObject,
                                monitoredValue,
                                thresholdValues,
                                info   }
        STATUS                current
        DESCRIPTION        "Spontaneous Alarm from the managed network element:
                            Failed to initialize MPS Media Processing Provider

Failed to initialize the Media Processing (MPS) Provider. Processing of streaming data will not work.
                            Check log-output for more details."
        ::= { eventGroupC56 202 }

        alarmC56203 NOTIFICATION-TYPE
        OBJECTS        {        neName,
                                neType,
                                eventGroupName,                        -- 56: MediaServer
                                eventName,                             -- 203: NoMoreAvailableRTPChannel
                                correlationId,
                                severity,
                                eventTime,
                                nodes,
                                faultyObject,
                                monitoredValue,
                                thresholdValues,
                                info   }
        STATUS                current
        DESCRIPTION        "Spontaneous Alarm from the managed network element:
                            No more RTP channel available

Failed to allocate a RTP channel resource to handle call.
                            Please check the ResourceManagement configuration for this application."
        ::= { eventGroupC56 203 }

        alarmC56204 NOTIFICATION-TYPE
        OBJECTS        {        neName,
                                neType,
                                eventGroupName,                        -- 56: MediaServer
                                eventName,                             -- 204: NoMorAvailableTTSLicens
                                correlationId,
                                severity,
                                eventTime,
                                nodes,
                                faultyObject,
                                monitoredValue,
                                thresholdValues,
                                info   }
        STATUS                current
        DESCRIPTION        "Spontaneous Alarm from the managed network element:
                            No (more) TTS license available

Failed to allocate Text-To-Speech port license.
                            Please make sure that there are enough licenses installed and that the 'licensing service' is running."
        ::= { eventGroupC56 204 }

        alarmC56205 NOTIFICATION-TYPE
        OBJECTS        {        neName,
                                neType,
                                eventGroupName,                        -- 56: MediaServer
                                eventName,                             -- 205: NoMoreAvailableASRLicense
                                correlationId,
                                severity,
                                eventTime,
                                nodes,
                                faultyObject,
                                monitoredValue,
                                thresholdValues,
                                info   }
        STATUS                current
        DESCRIPTION        "Spontaneous Alarm from the managed network element:
                            No (more) ASR license available

Failed to allocate Speech-Recognition port license.
                            Please make sure that there are enough licenses installed and that the 'licensing service' is running."
        ::= { eventGroupC56 205 }

        alarmC56210 NOTIFICATION-TYPE
        OBJECTS        {        neName,
                                neType,
                                eventGroupName,                        -- 56: MediaServer
                                eventName,                             -- 210: NoDiscSpaceLeft
                                correlationId,
                                severity,
                                eventTime,
                                nodes,
                                faultyObject,
                                monitoredValue,
                                thresholdValues,
                                info   }
        STATUS                current
        DESCRIPTION        "Spontaneous Alarm from the managed network element:
                            No disc space left

Unable to write further samples for recording, since there is no more disc space available.
                            Run debug file collection and escalate to next level of support."
        ::= { eventGroupC56 210 }

        alarmC56211 NOTIFICATION-TYPE
        OBJECTS        {        neName,
                                neType,
                                eventGroupName,                        -- 56: MediaServer
                                eventName,                             -- 211: NoAvaiableResource
                                correlationId,
                                severity,
                                eventTime,
                                nodes,
                                faultyObject,
                                monitoredValue,
                                thresholdValues,
                                info   }
        STATUS                current
        DESCRIPTION        "Spontaneous Alarm from the managed network element:
                            Resource no longer available

Failed to write samples for recording, because the file path is not available or the file not writeable.
                            Run debug file collection and escalate to next level of support."
        ::= { eventGroupC56 211 }

        alarmC56300 NOTIFICATION-TYPE
        OBJECTS        {        neName,
                                neType,
                                eventGroupName,                        -- 56: MediaServer
                                eventName,                             -- 300: MediaGatewayProviderInitFailure
                                correlationId,
                                severity,
                                eventTime,
                                nodes,
                                faultyObject,
                                monitoredValue,
                                thresholdValues,
                                info   }
        STATUS                current
        DESCRIPTION        "Spontaneous Alarm from the managed network element:
                            Failed to initialize Media Gateway Provider

An error occurred while starting Media Gateway Provider.
                            Please verify Media Gateway Configuration and assure that the PromptDB provider is running."
        ::= { eventGroupC56 300 }

        alarmC56301 NOTIFICATION-TYPE
        OBJECTS        {        neName,
                                neType,
                                eventGroupName,                        -- 56: MediaServer
                                eventName,                             -- 301: ConfChangesActivationFailure
                                correlationId,
                                severity,
                                eventTime,
                                nodes,
                                faultyObject,
                                monitoredValue,
                                thresholdValues,
                                info   }
        STATUS                current
        DESCRIPTION        "Spontaneous Alarm from the managed network element:
                            Failed to activate configuration changes

An error occurred while activating configuration changes.
                            Please fix Media Gateway Configuration and restart provider."
        ::= { eventGroupC56 301 }

        alarmC56302 NOTIFICATION-TYPE
        OBJECTS        {        neName,
                                neType,
                                eventGroupName,                        -- 56: MediaServer
                                eventName,                             -- 302: MediaGatewayDeactivationFailure
                                correlationId,
                                severity,
                                eventTime,
                                nodes,
                                faultyObject,
                                monitoredValue,
                                thresholdValues,
                                info   }
        STATUS                current
        DESCRIPTION        "Spontaneous Alarm from the managed network element:
                            Failed to deactivate Media Gateway Provider

An unexpected error occurred while stopping Media Gateway Provider.
                            Run debug file collection and escalate to next level of support."
        ::= { eventGroupC56 302 }

        alarmC56303 NOTIFICATION-TYPE
        OBJECTS        {        neName,
                                neType,
                                eventGroupName,                        -- 56: MediaServer
                                eventName,                             -- 303: MediaGatewayActivationFailure
                                correlationId,
                                severity,
                                eventTime,
                                nodes,
                                faultyObject,
                                monitoredValue,
                                thresholdValues,
                                info   }
        STATUS                current
        DESCRIPTION        "Spontaneous Alarm from the managed network element:
                            Failed to activate media gateways

No listening point is defined in Media Gateway configuration.
                            Please add at least one listening point."
        ::= { eventGroupC56 303 }

        alarmC56304 NOTIFICATION-TYPE
        OBJECTS        {        neName,
                                neType,
                                eventGroupName,                        -- 56: MediaServer
                                eventName,                             -- 304: ConnectionCreationFailure
                                correlationId,
                                severity,
                                eventTime,
                                nodes,
                                faultyObject,
                                monitoredValue,
                                thresholdValues,
                                info   }
        STATUS                current
        DESCRIPTION        "Spontaneous Alarm from the managed network element:
                            Failed to create connection

Ignoring create connection command, since no incoming connection listener is registered.
                            Please assure that the terminal binder is running."
        ::= { eventGroupC56 304 }

        alarmC56310 NOTIFICATION-TYPE
        OBJECTS        {        neName,
                                neType,
                                eventGroupName,                        -- 56: MediaServer
                                eventName,                             -- 310: ConnectionCreationFailure2
                                correlationId,
                                severity,
                                eventTime,
                                nodes,
                                faultyObject,
                                monitoredValue,
                                thresholdValues,
                                info   }
        STATUS                current
        DESCRIPTION        "Spontaneous Alarm from the managed network element:
                            Failed to create connection

A new connection can not be created due to a non-recoverable problem.
                            Please check the log-output to get more detailed informations (logger: com.cycos.media)."
        ::= { eventGroupC56 310 }

        alarmC56311 NOTIFICATION-TYPE
        OBJECTS        {        neName,
                                neType,
                                eventGroupName,                        -- 56: MediaServer
                                eventName,                             -- 311: ConnectionModificationFailure
                                correlationId,
                                severity,
                                eventTime,
                                nodes,
                                faultyObject,
                                monitoredValue,
                                thresholdValues,
                                info   }
        STATUS                current
        DESCRIPTION        "Spontaneous Alarm from the managed network element:
                            Failed to modify connection

Existing connection can not be modified due to a non-recoverable problem.
                            Please check the log-output to get more detailed informations (logger: com.cycos.media)."
        ::= { eventGroupC56 311 }

        alarmC56312 NOTIFICATION-TYPE
        OBJECTS        {        neName,
                                neType,
                                eventGroupName,                        -- 56: MediaServer
                                eventName,                             -- 312: ConnectionDeletionFailure
                                correlationId,
                                severity,
                                eventTime,
                                nodes,
                                faultyObject,
                                monitoredValue,
                                thresholdValues,
                                info   }
        STATUS                current
        DESCRIPTION        "Spontaneous Alarm from the managed network element:
                            Failed to delete connection

Request to delete a connection can not be handled correctly due to a non-recoverable problem.
                            Please check the log-output to get more detailed informations (logger: com.cycos.media)."
        ::= { eventGroupC56 312 }

        alarmC56313 NOTIFICATION-TYPE
        OBJECTS        {        neName,
                                neType,
                                eventGroupName,                        -- 56: MediaServer
                                eventName,                             -- 313: NotificationRequestProcessingFailure
                                correlationId,
                                severity,
                                eventTime,
                                nodes,
                                faultyObject,
                                monitoredValue,
                                thresholdValues,
                                info   }
        STATUS                current
        DESCRIPTION        "Spontaneous Alarm from the managed network element:
                            Failed to process notification request

An internal problem occurred during the handling of a request for notification.
                            Escalate to next level of support."
        ::= { eventGroupC56 313 }

        alarmC56330 NOTIFICATION-TYPE
        OBJECTS        {        neName,
                                neType,
                                eventGroupName,                        -- 56: MediaServer
                                eventName,                             -- 330: ResourceAssociatedWithConnectionLost
                                correlationId,
                                severity,
                                eventTime,
                                nodes,
                                faultyObject,
                                monitoredValue,
                                thresholdValues,
                                info   }
        STATUS                current
        DESCRIPTION        "Spontaneous Alarm from the managed network element:
                            Lost the resource associated with the connection

An internal problem occurred and the gateway is terminating the connection.
                            Escalate to next level of support."
        ::= { eventGroupC56 330 }

        alarmC56400 NOTIFICATION-TYPE
        OBJECTS        {        neName,
                                neType,
                                eventGroupName,                        -- 56: MediaServer
                                eventName,                             -- 400: UnknownMFWFault
                                correlationId,
                                severity,
                                eventTime,
                                nodes,
                                faultyObject,
                                monitoredValue,
                                thresholdValues,
                                info   }
        STATUS                current
        DESCRIPTION        "Spontaneous Alarm from the managed network element:
                            Unknown MFW fault

Unspecified Media Framework Component fault.
                            Escalate to next level of support."
        ::= { eventGroupC56 400 }

        alarmC56401 NOTIFICATION-TYPE
        OBJECTS        {        neName,
                                neType,
                                eventGroupName,                        -- 56: MediaServer
                                eventName,                             -- 401: NativeMediaFrameworkStartupFailure
                                correlationId,
                                severity,
                                eventTime,
                                nodes,
                                faultyObject,
                                monitoredValue,
                                thresholdValues,
                                info   }
        STATUS                current
        DESCRIPTION        "Spontaneous Alarm from the managed network element:
                            Native Media Framework startup failed

Native part of Media Framework could not be started by Java.
                            Escalate to next level of support."
        ::= { eventGroupC56 401 }

        alarmC56402 NOTIFICATION-TYPE
        OBJECTS        {        neName,
                                neType,
                                eventGroupName,                        -- 56: MediaServer
                                eventName,                             -- 402: NativeMediaFrameworkNotResponding
                                correlationId,
                                severity,
                                eventTime,
                                nodes,
                                faultyObject,
                                monitoredValue,
                                thresholdValues,
                                info   }
        STATUS                current
        DESCRIPTION        "Spontaneous Alarm from the managed network element:
                            Native Media Framework not responding

Native part of Media Framework has crashed or is unable to respond.
                            Escalate to next level of support."
        ::= { eventGroupC56 402 }

        alarmC56403 NOTIFICATION-TYPE
        OBJECTS        {        neName,
                                neType,
                                eventGroupName,                        -- 56: MediaServer
                                eventName,                             -- 403: JavaMediaFrameworkReceiveSocketOverrun
                                correlationId,
                                severity,
                                eventTime,
                                nodes,
                                faultyObject,
                                monitoredValue,
                                thresholdValues,
                                info   }
        STATUS                current
        DESCRIPTION        "Spontaneous Alarm from the managed network element:
                            Java Media Framework receive socket overrun

Receive socket of java part of Media Framework is overloaded.
                            Escalate to next level of support."
        ::= { eventGroupC56 403 }

        alarmC56404 NOTIFICATION-TYPE
        OBJECTS        {        neName,
                                neType,
                                eventGroupName,                        -- 56: MediaServer
                                eventName,                             -- 404: NativeMediaFrameworkRecieveSocketOverrun
                                correlationId,
                                severity,
                                eventTime,
                                nodes,
                                faultyObject,
                                monitoredValue,
                                thresholdValues,
                                info   }
        STATUS                current
        DESCRIPTION        "Spontaneous Alarm from the managed network element:
                            Native Media Framework receive socket overrun

Receive socket of native part of Media Framework is overloaded.
                            Escalate to next level of support."
        ::= { eventGroupC56 404 }

        alarmC56405 NOTIFICATION-TYPE
        OBJECTS        {        neName,
                                neType,
                                eventGroupName,                        -- 56: MediaServer
                                eventName,                             -- 405: JavaMediaFrameworkReceiveSocketSequencError
                                correlationId,
                                severity,
                                eventTime,
                                nodes,
                                faultyObject,
                                monitoredValue,
                                thresholdValues,
                                info   }
        STATUS                current
        DESCRIPTION        "Spontaneous Alarm from the managed network element:
                            Java Media Framework receive socket sequence error

Messages lost on receive socket in java part of Media Framework.
                            Escalate to next level of support."
        ::= { eventGroupC56 405 }

        alarmC56406 NOTIFICATION-TYPE
        OBJECTS        {        neName,
                                neType,
                                eventGroupName,                        -- 56: MediaServer
                                eventName,                             -- 406: NativeMediaFrameworkReceiveSocketSequencError
                                correlationId,
                                severity,
                                eventTime,
                                nodes,
                                faultyObject,
                                monitoredValue,
                                thresholdValues,
                                info   }
        STATUS                current
        DESCRIPTION        "Spontaneous Alarm from the managed network element:
                            Native Media Framework receive socket sequence error

Messages lost on receive socket in native part of Media Framework.
                            Escalate to next level of support."
        ::= { eventGroupC56 406 }

        alarmC56407 NOTIFICATION-TYPE
        OBJECTS        {        neName,
                                neType,
                                eventGroupName,                        -- 56: MediaServer
                                eventName,                             -- 407: NativeMediaFrameworkSocketError
                                correlationId,
                                severity,
                                eventTime,
                                nodes,
                                faultyObject,
                                monitoredValue,
                                thresholdValues,
                                info   }
        STATUS                current
        DESCRIPTION        "Spontaneous Alarm from the managed network element:
                            Native Media Framework socket error

Bind of socket failed in native part of Media Framework.
                            Escalate to next level of support."
        ::= { eventGroupC56 407 }

        alarmC56408 NOTIFICATION-TYPE
        OBJECTS        {        neName,
                                neType,
                                eventGroupName,                        -- 56: MediaServer
                                eventName,                             -- 408: JavaMediaFrameworkUnrecoverableError
                                correlationId,
                                severity,
                                eventTime,
                                nodes,
                                faultyObject,
                                monitoredValue,
                                thresholdValues,
                                info   }
        STATUS                current
        DESCRIPTION        "Spontaneous Alarm from the managed network element:
                            Java Media Framework unrecoverable error

Unrecoverable error in java part of Media Framework leading to permanent service degradation. Any processing of streaming data won't work.
                            Escalate to next level of support."
        ::= { eventGroupC56 408 }

        alarmC56409 NOTIFICATION-TYPE
        OBJECTS        {        neName,
                                neType,
                                eventGroupName,                        -- 56: MediaServer
                                eventName,                             -- 409: NatvieMediaFrameworkUnrecoverableError
                                correlationId,
                                severity,
                                eventTime,
                                nodes,
                                faultyObject,
                                monitoredValue,
                                thresholdValues,
                                info   }
        STATUS                current
        DESCRIPTION        "Spontaneous Alarm from the managed network element:
                            Native Media Framework unrecoverable error

Unrecoverable error in native part of Media Framework leading to permanent service degradation. Any processing of streaming data won't work.
                            Escalate to next level of support."
        ::= { eventGroupC56 409 }

        alarmC56410 NOTIFICATION-TYPE
        OBJECTS        {        neName,
                                neType,
                                eventGroupName,                        -- 56: MediaServer
                                eventName,                             -- 410: NativeMediaFrameworkOutOfMemory
                                correlationId,
                                severity,
                                eventTime,
                                nodes,
                                faultyObject,
                                monitoredValue,
                                thresholdValues,
                                info   }
        STATUS                current
        DESCRIPTION        "Spontaneous Alarm from the managed network element:
                            Native Media Framework out of memory

Memory allocation failed in native part of Media Framework.
                            Escalate to next level of support."
        ::= { eventGroupC56 410 }

        alarmC56411 NOTIFICATION-TYPE
        OBJECTS        {        neName,
                                neType,
                                eventGroupName,                        -- 56: MediaServer
                                eventName,                             -- 411: NativeMediaFrameworkOutOfUDPPorts
                                correlationId,
                                severity,
                                eventTime,
                                nodes,
                                faultyObject,
                                monitoredValue,
                                thresholdValues,
                                info   }
        STATUS                current
        DESCRIPTION        "Spontaneous Alarm from the managed network element:
                            Native Media Framework out of UDP ports

Port allocation failed in native part of Media Framework.
                            Escalate to next level of support."
        ::= { eventGroupC56 411 }

        alarmC56412 NOTIFICATION-TYPE
        OBJECTS        {        neName,
                                neType,
                                eventGroupName,                        -- 56: MediaServer
                                eventName,                             -- 412: NativeMediaFrameworkCryptoSessionNotFound
                                correlationId,
                                severity,
                                eventTime,
                                nodes,
                                faultyObject,
                                monitoredValue,
                                thresholdValues,
                                info   }
        STATUS                current
        DESCRIPTION        "Spontaneous Alarm from the managed network element:
                            Native Media Framework crypto session not found

KeyManagement has no matching crypto session. Processing of encrypted streaming data will be affected.
                            Escalate to next level of support."
        ::= { eventGroupC56 412 }

        alarmC56413 NOTIFICATION-TYPE
        OBJECTS        {        neName,
                                neType,
                                eventGroupName,                        -- 56: MediaServer
                                eventName,                             -- 413: NativeMediaFrameworkSRTPError
                                correlationId,
                                severity,
                                eventTime,
                                nodes,
                                faultyObject,
                                monitoredValue,
                                thresholdValues,
                                info   }
        STATUS                current
        DESCRIPTION        "Spontaneous Alarm from the managed network element:
                            Native Media Framework srtp error

Srtp stack returned error. Processing of encrypted streaming data will be affected.
                            Escalate to next level of support."
        ::= { eventGroupC56 413 }

        alarmC56414 NOTIFICATION-TYPE
        OBJECTS        {        neName,
                                neType,
                                eventGroupName,                        -- 56: MediaServer
                                eventName,                             -- 414: NativeMediaFrameworkJeyManagementFatalErro
                                correlationId,
                                severity,
                                eventTime,
                                nodes,
                                faultyObject,
                                monitoredValue,
                                thresholdValues,
                                info   }
        STATUS                current
        DESCRIPTION        "Spontaneous Alarm from the managed network element:
                            Native Media Framework keyManagement fatal error

KeyManagement in unrecoverable error state. Processing of encrypted streaming data will be affected.
                            Escalate to next level of support."
        ::= { eventGroupC56 414 }

        alarmC56415 NOTIFICATION-TYPE
        OBJECTS        {        neName,
                                neType,
                                eventGroupName,                        -- 56: MediaServer
                                eventName,                             -- 415: NativeMediaFrameworkControlPortBindError
                                correlationId,
                                severity,
                                eventTime,
                                nodes,
                                faultyObject,
                                monitoredValue,
                                thresholdValues,
                                info   }
        STATUS                current
        DESCRIPTION        "Spontaneous Alarm from the managed network element:
                            Media Framework control port bind error

Control port for Java-native communication could not be opened - check port configuration or other processes using conflicting ports.
                            Escalate to next level of support."
        ::= { eventGroupC56 415 }

        alarmC56416 NOTIFICATION-TYPE
        OBJECTS        {        neName,
                                neType,
                                eventGroupName,                        -- 56: MediaServer
                                eventName,                             -- 416: NativeMediaFrameworkRealtimeError
                                correlationId,
                                severity,
                                eventTime,
                                nodes,
                                faultyObject,
                                monitoredValue,
                                thresholdValues,
                                info   }
        STATUS                current
        DESCRIPTION        "Spontaneous Alarm from the managed network element:
                            Native Media Framework realtime error

Native MFW process could not be started in realtime mode: this may lead to bad voice quality.
                            Check access rights for native image."
        ::= { eventGroupC56 416 }

        alarmC56417 NOTIFICATION-TYPE
        OBJECTS        {        neName,
                                neType,
                                eventGroupName,                        -- 56: MediaServer
                                eventName,                             -- 417: NativeMediaFrameworksRTCError
                                correlationId,
                                severity,
                                eventTime,
                                nodes,
                                faultyObject,
                                monitoredValue,
                                thresholdValues,
                                info   }
        STATUS                current
        DESCRIPTION        "Spontaneous Alarm from the managed network element:
                            Native Media Framework RTC error

Realtime clock could not be initialized: this may degrade voice quality.
                            Check for configuration or conflicting usage of RTC by another process."
        ::= { eventGroupC56 417 }

        alarmC56418 NOTIFICATION-TYPE
        OBJECTS        {        neName,
                                neType,
                                eventGroupName,                        -- 56: MediaServer
                                eventName,                             -- 418: UDPPortBindError
                                correlationId,
                                severity,
                                eventTime,
                                nodes,
                                faultyObject,
                                monitoredValue,
                                thresholdValues,
                                info   }
        STATUS                current
        DESCRIPTION        "Spontaneous Alarm from the managed network element:
                            UDP port bind error

Bind of a UDP port failed.
                            If this error persists check port range configuration."
        ::= { eventGroupC56 418 }

        alarmC56419 NOTIFICATION-TYPE
        OBJECTS        {        neName,
                                neType,
                                eventGroupName,                        -- 56: MediaServer
                                eventName,                             -- 419: IllegalCommandOption
                                correlationId,
                                severity,
                                eventTime,
                                nodes,
                                faultyObject,
                                monitoredValue,
                                thresholdValues,
                                info   }
        STATUS                current
        DESCRIPTION        "Spontaneous Alarm from the managed network element:
                            Illegal command option

Media Framework was started with an illegal command option.
                            Check configuration in Media Framework configuration file 'mfw.component.xml'."
        ::= { eventGroupC56 419 }

        alarmC56420 NOTIFICATION-TYPE
        OBJECTS        {        neName,
                                neType,
                                eventGroupName,                        -- 56: MediaServer
                                eventName,                             -- 420: NoMoreAvailableUDPPorts
                                correlationId,
                                severity,
                                eventTime,
                                nodes,
                                faultyObject,
                                monitoredValue,
                                thresholdValues,
                                info   }
        STATUS                current
        DESCRIPTION        "Spontaneous Alarm from the managed network element:
                            No more free UDP ports available

The media framework (MFW) has run out of free UDP ports.
                            Please make sure that the media servers configured port range is sufficient."
        ::= { eventGroupC56 420 }

        alarmC56500 NOTIFICATION-TYPE
        OBJECTS        {        neName,
                                neType,
                                eventGroupName,                        -- 56: MediaServer
                                eventName,                             -- 500: MRCPServerConnectionSetupError
                                correlationId,
                                severity,
                                eventTime,
                                nodes,
                                faultyObject,
                                monitoredValue,
                                thresholdValues,
                                info   }
        STATUS                current
        DESCRIPTION        "Spontaneous Alarm from the managed network element:
                            Unable to setup a connection with MRCP server

Unable to setup a connection with MRCP server. No TTS or ASR services may be used within the media server's applications.
                            Escalate to next level of support."
        ::= { eventGroupC56 500 }

        alarmC56990 NOTIFICATION-TYPE
        OBJECTS        {        neName,
                                neType,
                                eventGroupName,                        -- 56: MediaServer
                                eventName,                             -- 990: TooManyRTCParticipants
                                correlationId,
                                severity,
                                eventTime,
                                nodes,
                                faultyObject,
                                monitoredValue,
                                thresholdValues,
                                info   }
        STATUS                current
        DESCRIPTION        "Spontaneous Alarm from the managed network element:
                            A new RTC participant tried to enter an RTC conference and the limit is reached. The new participant is removed.
                            The alarm is not cleared manually."
        ::= { eventGroupC56 990 }

        alarmC56991 NOTIFICATION-TYPE
        OBJECTS        {        neName,
                                neType,
                                eventGroupName,                        -- 56: MediaServer
                                eventName,                             -- 991: TooManyPSTNParticipants
                                correlationId,
                                severity,
                                eventTime,
                                nodes,
                                faultyObject,
                                monitoredValue,
                                thresholdValues,
                                info   }
        STATUS                current
        DESCRIPTION        "Spontaneous Alarm from the managed network element:
                            A new PSTN participant tried to enter an RTC conference and the limit is reached. The new participant is removed.
                            The alarm is not cleared manually."
        ::= { eventGroupC56 991 }

        alarmC56992 NOTIFICATION-TYPE
        OBJECTS        {        neName,
                                neType,
                                eventGroupName,                        -- 56: MediaServer
                                eventName,                             -- 992: Overload
                                correlationId,
                                severity,
                                eventTime,
                                nodes,
                                faultyObject,
                                monitoredValue,
                                thresholdValues,
                                info   }
        STATUS                current
        DESCRIPTION        "Spontaneous Alarm from the managed network element:
                            The media server has too much load. If possible new conference calls are assigned to other media servers, if not they are rejected.
                            If the alarm condition remains over a longer period of time review installation sizing. If the installation is sized properly escalate to development to check for SW problems."
        ::= { eventGroupC56 992 }


        --********************************************************************
        -- Alarm Trap Definitions for alarm eventC 57: IMPApplication
        --********************************************************************

        alarmC57001 NOTIFICATION-TYPE
        OBJECTS        {        neName,
                                neType,
                                eventGroupName,                        -- 57: IMPApplication
                                eventName,                             -- 001: Service
                                correlationId,
                                severity,
                                eventTime,
                                nodes,
                                faultyObject,
                                monitoredValue,
                                thresholdValues,
                                info   }
        STATUS                current
        DESCRIPTION        "Spontaneous Alarm from the managed network element:
                            Service in the application container does not startup.
                            Escalate to next level of support."
        ::= { eventGroupC57 1 }

        alarmC57003 NOTIFICATION-TYPE
        OBJECTS        {        neName,
                                neType,
                                eventGroupName,                        -- 57: IMPApplication
                                eventName,                             -- 003: ClientAPITimeHigh
                                correlationId,
                                severity,
                                eventTime,
                                nodes,
                                faultyObject,
                                monitoredValue,
                                thresholdValues,
                                info   }
        STATUS                current
        DESCRIPTION        "Spontaneous Alarm from the managed network element:
                            Client API average response time.
                            Escalate to next level of support."
        ::= { eventGroupC57 3 }

        alarmC57004 NOTIFICATION-TYPE
        OBJECTS        {        neName,
                                neType,
                                eventGroupName,                        -- 57: IMPApplication
                                eventName,                             -- 004: ClientAPIFailure
                                correlationId,
                                severity,
                                eventTime,
                                nodes,
                                faultyObject,
                                monitoredValue,
                                thresholdValues,
                                info   }
        STATUS                current
        DESCRIPTION        "Spontaneous Alarm from the managed network element:
                            Client API times out, no response.
                            Escalate to next level of support."
        ::= { eventGroupC57 4 }

        alarmC57005 NOTIFICATION-TYPE
        OBJECTS        {        neName,
                                neType,
                                eventGroupName,                        -- 57: IMPApplication
                                eventName,                             -- 005: ClientAPIZpoolFull
                                correlationId,
                                severity,
                                eventTime,
                                nodes,
                                faultyObject,
                                monitoredValue,
                                thresholdValues,
                                info   }
        STATUS                current
        DESCRIPTION        "Spontaneous Alarm from the managed network element:
                            The zpool contains data.

A high fill level may cause issues and failed conversions once 100% reached.
                            If the alarm condition remains over a longer period of time review installation sizing. If the installation is sized properly escalate to development to check for SW problems."
        ::= { eventGroupC57 5 }

        alarmC57013 NOTIFICATION-TYPE
        OBJECTS        {        neName,
                                neType,
                                eventGroupName,                        -- 57: IMPApplication
                                eventName,                             -- 013: UnknownAlarmId
                                correlationId,
                                severity,
                                eventTime,
                                nodes,
                                faultyObject,
                                monitoredValue,
                                thresholdValues,
                                info   }
        STATUS                current
        DESCRIPTION        "Spontaneous Alarm from the managed network element:
                            The platform alarm configuration file could not be found.
                            Check installation. If correct, check permissions on alarm configuration file."
        ::= { eventGroupC57 13 }

        alarmC57014 NOTIFICATION-TYPE
        OBJECTS        {        neName,
                                neType,
                                eventGroupName,                        -- 57: IMPApplication
                                eventName,                             -- 014: InvalidMonitoredValue
                                correlationId,
                                severity,
                                eventTime,
                                nodes,
                                faultyObject,
                                monitoredValue,
                                thresholdValues,
                                info   }
        STATUS                current
        DESCRIPTION        "Spontaneous Alarm from the managed network element:
                            An alarm has been raised or used with an invalid monitored attribute value.
                            Correct code raising the alarm."
        ::= { eventGroupC57 14 }

        alarmC57015 NOTIFICATION-TYPE
        OBJECTS        {        neName,
                                neType,
                                eventGroupName,                        -- 57: IMPApplication
                                eventName,                             -- 015: FaultyObjectTooLong
                                correlationId,
                                severity,
                                eventTime,
                                nodes,
                                faultyObject,
                                monitoredValue,
                                thresholdValues,
                                info   }
        STATUS                current
        DESCRIPTION        "Spontaneous Alarm from the managed network element:
                            An alarm has been raised with a FaultyObject string that is longer than 255. It has been truncated.
                            Correct code raising the alarm."
        ::= { eventGroupC57 15 }

        alarmC57016 NOTIFICATION-TYPE
        OBJECTS        {        neName,
                                neType,
                                eventGroupName,                        -- 57: IMPApplication
                                eventName,                             -- 016: AddlInfoTooLong
                                correlationId,
                                severity,
                                eventTime,
                                nodes,
                                faultyObject,
                                monitoredValue,
                                thresholdValues,
                                info   }
        STATUS                current
        DESCRIPTION        "Spontaneous Alarm from the managed network element:
                            An alarm has been raised with an Addl Info string that is longer than 255. It has been truncated.
                            Correct code raising the alarm."
        ::= { eventGroupC57 16 }

        alarmC57017 NOTIFICATION-TYPE
        OBJECTS        {        neName,
                                neType,
                                eventGroupName,                        -- 57: IMPApplication
                                eventName,                             -- 017: UnknownAlarmId
                                correlationId,
                                severity,
                                eventTime,
                                nodes,
                                faultyObject,
                                monitoredValue,
                                thresholdValues,
                                info   }
        STATUS                current
        DESCRIPTION        "Spontaneous Alarm from the managed network element:
                            An alarm has been raised or used with an unknown group ID and/or event ID.
                            Check if the alarm should be raised/used. If correct, add alarm to alarm configuration."
        ::= { eventGroupC57 17 }


        --********************************************************************
        -- Alarm Trap Definitions for alarm eventC 58: Redis
        --********************************************************************

        alarmC58001 NOTIFICATION-TYPE
        OBJECTS        {        neName,
                                neType,
                                eventGroupName,                        -- 58: Redis
                                eventName,                             -- 001: RedisClusterFail
                                correlationId,
                                severity,
                                eventTime,
                                nodes,
                                faultyObject,
                                monitoredValue,
                                thresholdValues,
                                info   }
        STATUS                current
        DESCRIPTION        "Spontaneous Alarm from the managed network element:
                            Redis cluster is in fail state and can not recover by itself. As a result all requests to the data center is not being processed. Human intervention is needed immediately.
                            This alarm can occur during system startup and cluster formation. If this is not the case, check if all nodes are running. Check also if redis-cluster and redis-audit are running. If everything looks good then probably the cluster will not recover by itself. To recover the system lock all nodes (pmc state locked) then run '/etc/init.d/redis-audit clean' in all nodes, afterwards unlock the nodes (pmc state locked) - this way a fresh redis-cluster will start."
        ::= { eventGroupC58 1 }

        alarmC58002 NOTIFICATION-TYPE
        OBJECTS        {        neName,
                                neType,
                                eventGroupName,                        -- 58: Redis
                                eventName,                             -- 002: RedisClusterFailOver
                                correlationId,
                                severity,
                                eventTime,
                                nodes,
                                faultyObject,
                                monitoredValue,
                                thresholdValues,
                                info   }
        STATUS                current
        DESCRIPTION        "Spontaneous Alarm from the managed network element:
                            One of the redis node is down so a failover just happened.
                            This alarm can happen temporarily if some other Access node is restarting. Please check if all nodes are running or if there are network issues. The redis audit will try to rebalance the cluster once the Access node is available again (then the alarm will be automatically cleared). The process of rebalancing can take about 5 to 15 minutes to complete."
        ::= { eventGroupC58 2 }

        alarmC58003 NOTIFICATION-TYPE
        OBJECTS        {        neName,
                                neType,
                                eventGroupName,                        -- 58: Redis
                                eventName,                             -- 003: RedisClusterRebalancing
                                correlationId,
                                severity,
                                eventTime,
                                nodes,
                                faultyObject,
                                monitoredValue,
                                thresholdValues,
                                info   }
        STATUS                current
        DESCRIPTION        "Spontaneous Alarm from the managed network element:
                            A resharding is started, do not stop the nodes participating in the resharding until the alarm is cleared.
                            The redis audit is moving hash slots (resharding). This happens if nodes are added or removed, the alarm will be automatically cleared once the resharding process is complete. The process of resharding can take about 5 to 15 minutes to complete."
        ::= { eventGroupC58 3 }

        alarmC58004 NOTIFICATION-TYPE
        OBJECTS        {        neName,
                                neType,
                                eventGroupName,                        -- 58: Redis
                                eventName,                             -- 004: RedisClusterInit
                                correlationId,
                                severity,
                                eventTime,
                                nodes,
                                faultyObject,
                                monitoredValue,
                                thresholdValues,
                                info   }
        STATUS                current
        DESCRIPTION        "Spontaneous Alarm from the managed network element:
                            Redis Cluster is in the process of reinitializing, all data will be erased and a new cluster will be formed.
                            The redis audit is in process of creating a new cluster, allocating hash slots for each node and defining the Master/Slave roles. This alarm can also happen temporarily after resharding and rebalancing. The alarm will be automatically cleared once the cluster formation process is complete, this process can take about 5 minutes to complete."
        ::= { eventGroupC58 4 }


        --********************************************************************
        -- Alarm Trap Definitions for alarm eventC 59: LogManager
        --********************************************************************

        alarmC59001 NOTIFICATION-TYPE
        OBJECTS        {        neName,
                                neType,
                                eventGroupName,                        -- 59: LogManager
                                eventName,                             -- 001: PostAlarmFailure
                                correlationId,
                                severity,
                                eventTime,
                                nodes,
                                faultyObject,
                                monitoredValue,
                                thresholdValues,
                                info   }
        STATUS                current
        DESCRIPTION        "Spontaneous Alarm from the managed network element:
                            The log manger could not store an alarm record in the alarm database. The alarm is not reported as SNMP trap and not displayed in the active alarm database.
                            Run debug file collection of the operations node and escalate to SW development."
        ::= { eventGroupC59 1 }

        alarmC59002 NOTIFICATION-TYPE
        OBJECTS        {        neName,
                                neType,
                                eventGroupName,                        -- 59: LogManager
                                eventName,                             -- 002: PostSolrFailure
                                correlationId,
                                severity,
                                eventTime,
                                nodes,
                                faultyObject,
                                monitoredValue,
                                thresholdValues,
                                info   }
        STATUS                current
        DESCRIPTION        "Spontaneous Alarm from the managed network element:
                            The log manger could not store a log record in Solr. The log is not shown in the log manager GUI and it is not archived in hadoop.
                            Check the partition fill level and accessibility of the /db/logmg directory. Run debug file collection of the operations node and escalate to SW development."
        ::= { eventGroupC59 2 }

        alarmC59003 NOTIFICATION-TYPE
        OBJECTS        {        neName,
                                neType,
                                eventGroupName,                        -- 59: LogManager
                                eventName,                             -- 003: PostHiveFailure
                                correlationId,
                                severity,
                                eventTime,
                                nodes,
                                faultyObject,
                                monitoredValue,
                                thresholdValues,
                                info   }
        STATUS                current
        DESCRIPTION        "Spontaneous Alarm from the managed network element:
                            The log manager could not access Hive.
                            Is the /db partition accessible? Run debug file collection of the operations node and escalate to SW development."
        ::= { eventGroupC59 3 }


        --********************************************************************
        -- Alarm Trap Definitions for alarm eventC 60: Access
        --********************************************************************

        alarmC60001 NOTIFICATION-TYPE
        OBJECTS        {        neName,
                                neType,
                                eventGroupName,                        -- 60: Access
                                eventName,                             -- 001: FaultyConfiguraton
                                correlationId,
                                severity,
                                eventTime,
                                nodes,
                                faultyObject,
                                monitoredValue,
                                thresholdValues,
                                info   }
        STATUS                current
        DESCRIPTION        "Spontaneous Alarm from the managed network element:
                            Access node configuration file is faulty. Access node functionality is restricted.
                            Review log file entries, especially /var/log/access.log, to determine source of problem."
        ::= { eventGroupC60 1 }


        --********************************************************************
        -- Alarm Trap Definitions for alarm eventC 80: NetworkCom
        --********************************************************************

        alarmC80001 NOTIFICATION-TYPE
        OBJECTS        {        neName,
                                neType,
                                eventGroupName,                        -- 80: NetworkCom
                                eventName,                             -- 001: NodesUnavailable
                                correlationId,
                                severity,
                                eventTime,
                                nodes,
                                faultyObject,
                                monitoredValue,
                                thresholdValues,
                                info   }
        STATUS                current
        DESCRIPTION        "Spontaneous Alarm from the managed network element:
                            The listed nodes are not reported as active in the zookeeper database.
                            Check the administrative and operational status. Try to access the node directly via ssh and run rapidstat."
        ::= { eventGroupC80 1 }

        alarmC80002 NOTIFICATION-TYPE
        OBJECTS        {        neName,
                                neType,
                                eventGroupName,                        -- 80: NetworkCom
                                eventName,                             -- 002: LocalResponseTime
                                correlationId,
                                severity,
                                eventTime,
                                nodes,
                                faultyObject,
                                monitoredValue,
                                thresholdValues,
                                info   }
        STATUS                current
        DESCRIPTION        "Spontaneous Alarm from the managed network element:
                            The node's response time to a test message sent by the operations node was too high.
                            If this alarm persists escalate to next level of support to determine whether is response time is justified. Ether the SW needs to be corrected or the threshold be changed."
        ::= { eventGroupC80 2 }

        alarmC80003 NOTIFICATION-TYPE
        OBJECTS        {        neName,
                                neType,
                                eventGroupName,                        -- 80: NetworkCom
                                eventName,                             -- 003: RemoteResponseTime
                                correlationId,
                                severity,
                                eventTime,
                                nodes,
                                faultyObject,
                                monitoredValue,
                                thresholdValues,
                                info   }
        STATUS                current
        DESCRIPTION        "Spontaneous Alarm from the managed network element:
                            Future.
                            Future."
        ::= { eventGroupC80 3 }


        --********************************************************************
        -- Alarm Trap Definitions for alarm eventC 81: Eventing
        --********************************************************************

        alarmC81001 NOTIFICATION-TYPE
        OBJECTS        {        neName,
                                neType,
                                eventGroupName,                        -- 81: Eventing
                                eventName,                             -- 001: RabbitMQ
                                correlationId,
                                severity,
                                eventTime,
                                nodes,
                                faultyObject,
                                monitoredValue,
                                thresholdValues,
                                info   }
        STATUS                current
        DESCRIPTION        "Spontaneous Alarm from the managed network element:
                            RabbitMQ is not running.
                            Check IMP Application configuration."
        ::= { eventGroupC81 1 }


        --********************************************************************
        -- Alarm Trap Definitions for alarm eventC 82: InMemDatabase
        --********************************************************************

        alarmC82001 NOTIFICATION-TYPE
        OBJECTS        {        neName,
                                neType,
                                eventGroupName,                        -- 82: InMemDatabase
                                eventName,                             -- 001: Hazelcast
                                correlationId,
                                severity,
                                eventTime,
                                nodes,
                                faultyObject,
                                monitoredValue,
                                thresholdValues,
                                info   }
        STATUS                current
        DESCRIPTION        "Spontaneous Alarm from the managed network element:
                            In memory database is not running, does not startup.
                            Check IMP Application configuration."
        ::= { eventGroupC82 1 }

END
