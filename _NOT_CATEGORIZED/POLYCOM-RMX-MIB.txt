POLYCOM-RMX-MIB DEFINITIONS ::= BEGIN

IMPORTS  
	TEXTUAL-CONVENTION FROM SNMPv2-TC
TRAP-TYPE          FROM RFC-1215
DateAndTime        FROM SNMPv2-TC
  MODULE-IDENTITY, OBJECT-TYPE, NOTIFICATION-TYPE,
    enterprises   , Unsigned32
    FROM SNMPv2-SMI ; 

polycom MODULE-IDENTITY
  LAST-UPDATED  "200703140000Z"
  ORGANIZATION  "Polycom Ltd."
  CONTACT-INFO  "Sagi Amiel"

  DESCRIPTION
"This is RMX MCU MIB"
  ::= { enterprises 13885 }  
    
nsdProducts	         OBJECT IDENTIFIER ::= { polycom    9}
rmx                      OBJECT IDENTIFIER ::= { nsdProducts 1}

rmxMib1	                 OBJECT IDENTIFIER ::= { rmx 1}
rmxMib1General	 	 OBJECT IDENTIFIER ::= { rmxMib1 1}
rmxMib1Events	 	 OBJECT IDENTIFIER ::= { rmxMib1 2}
rmxMib1EventsParams	 OBJECT IDENTIFIER ::= { rmxMib1Events 1}
rmxNotify	  	 OBJECT IDENTIFIER ::= { rmxMib1Events 2}
rmxTraps	         OBJECT IDENTIFIER ::= { rmxNotify 0 }


rmxProducts	         OBJECT IDENTIFIER ::= { rmx 10 }
rmx2000	                 OBJECT IDENTIFIER ::= { rmxProducts 1 }
rmx4000					 OBJECT IDENTIFIER ::= { rmxProducts 2 }
-- PUT HERE MORE PRODUCTS...  
-- sample : rmx8000	                 OBJECT IDENTIFIER ::= { rmxProducts 8 }


RmxStatus ::= TEXTUAL-CONVENTION
    STATUS          current
    DESCRIPTION
            "A possible status of RMX"
	SYNTAX  	INTEGER {
					normal  (0),
					startup (1),
					minor   (2),
					major   (3)
    }



rmxCurrentStatus OBJECT-TYPE
	SYNTAX  	RmxStatus
	MAX-ACCESS	read-only
	STATUS		current
	DESCRIPTION	"MCU current status"
::= { rmxMib1General 1 }


 
----------------------------------------------------------
--   Trap Group
--   All RMX traps have severity major (3).
-------------------------------------------------------

rmxAlarmDescription OBJECT-TYPE
	SYNTAX  OCTET STRING (SIZE (0..255))
	MAX-ACCESS  accessible-for-notify
	STATUS  current
   	DESCRIPTION	"Active alarm description"
::= {rmxMib1EventsParams 1 }  

rmxActiveAlarmDateAndTime OBJECT-TYPE
	SYNTAX  DateAndTime
	MAX-ACCESS  accessible-for-notify
	STATUS  current
   	DESCRIPTION	"Active alarm date and time"
::= {rmxMib1EventsParams 2 } 

rmxActiveAlarmIndex OBJECT-TYPE
	SYNTAX  Unsigned32
	MAX-ACCESS  accessible-for-notify
	STATUS  current
   	DESCRIPTION	"Active alarm table unique index number"
::= {rmxMib1EventsParams 3 } 

rmxActiveAlarmListName OBJECT-TYPE
	SYNTAX  OCTET STRING (SIZE (0..255))
	MAX-ACCESS  accessible-for-notify
	STATUS  current
   	DESCRIPTION	"The alarmListName value of this entery."
::= {rmxMib1EventsParams 4 } 

rmxActiveAlarmRmxStatus OBJECT-TYPE
	SYNTAX  RmxStatus
	MAX-ACCESS  accessible-for-notify
	STATUS  current
   	DESCRIPTION	"The current status of the RMX"
::= {rmxMib1EventsParams 5 } 


------------------------------------------------------------------------------
--  TRAP V2
------------------------------------------------------------------------------


   


rmxNoLicensingAlarmFault  NOTIFICATION-TYPE
             OBJECTS   { rmxAlarmDescription , rmxActiveAlarmDateAndTime, rmxActiveAlarmIndex , rmxActiveAlarmListName , rmxActiveAlarmRmxStatus }
             STATUS  current
             DESCRIPTION
             "License not found"
             ::= { rmxTraps 5001 } 



rmxNoLicensingAlarmClear  NOTIFICATION-TYPE
             OBJECTS   { rmxAlarmDescription , rmxActiveAlarmDateAndTime, rmxActiveAlarmIndex , rmxActiveAlarmListName , rmxActiveAlarmRmxStatus }
             STATUS  current
             DESCRIPTION
             "License not found"
             ::= { rmxTraps 15001 } 



rmxNoMeetingRoomAlarmFault  NOTIFICATION-TYPE
             OBJECTS   { rmxAlarmDescription , rmxActiveAlarmDateAndTime, rmxActiveAlarmIndex , rmxActiveAlarmListName , rmxActiveAlarmRmxStatus }
             STATUS  current
             DESCRIPTION
             "Resource process did not receive the Meeting Room list during startup."
             ::= { rmxTraps 5002 } 



rmxNoMeetingRoomAlarmClear  NOTIFICATION-TYPE
             OBJECTS   { rmxAlarmDescription , rmxActiveAlarmDateAndTime, rmxActiveAlarmIndex , rmxActiveAlarmListName , rmxActiveAlarmRmxStatus }
             STATUS  current
             DESCRIPTION
             "Resource process did not receive the Meeting Room list during startup."
             ::= { rmxTraps 15002 } 



rmxNoIpServiceParamsAlarmFault  NOTIFICATION-TYPE
             OBJECTS   { rmxAlarmDescription , rmxActiveAlarmDateAndTime, rmxActiveAlarmIndex , rmxActiveAlarmListName , rmxActiveAlarmRmxStatus }
             STATUS  current
             DESCRIPTION
             "No IP Network Services defined"
             ::= { rmxTraps 5003 } 



rmxNoIpServiceParamsAlarmClear  NOTIFICATION-TYPE
             OBJECTS   { rmxAlarmDescription , rmxActiveAlarmDateAndTime, rmxActiveAlarmIndex , rmxActiveAlarmListName , rmxActiveAlarmRmxStatus }
             STATUS  current
             DESCRIPTION
             "No IP Network Services defined"
             ::= { rmxTraps 15003 } 



rmxTaskTerminatedAlarmFault  NOTIFICATION-TYPE
             OBJECTS   { rmxAlarmDescription , rmxActiveAlarmDateAndTime, rmxActiveAlarmIndex , rmxActiveAlarmListName , rmxActiveAlarmRmxStatus }
             STATUS  current
             DESCRIPTION
             "Task terminated"
             ::= { rmxTraps 5004 } 



rmxTaskTerminatedAlarmClear  NOTIFICATION-TYPE
             OBJECTS   { rmxAlarmDescription , rmxActiveAlarmDateAndTime, rmxActiveAlarmIndex , rmxActiveAlarmListName , rmxActiveAlarmRmxStatus }
             STATUS  current
             DESCRIPTION
             "Task terminated"
             ::= { rmxTraps 15004 } 



rmxCfgChangedAlarmFault  NOTIFICATION-TYPE
             OBJECTS   { rmxAlarmDescription , rmxActiveAlarmDateAndTime, rmxActiveAlarmIndex , rmxActiveAlarmListName , rmxActiveAlarmRmxStatus }
             STATUS  current
             DESCRIPTION
             "System Configuration modified"
             ::= { rmxTraps 5005 } 



rmxCfgChangedAlarmClear  NOTIFICATION-TYPE
             OBJECTS   { rmxAlarmDescription , rmxActiveAlarmDateAndTime, rmxActiveAlarmIndex , rmxActiveAlarmListName , rmxActiveAlarmRmxStatus }
             STATUS  current
             DESCRIPTION
             "System Configuration modified"
             ::= { rmxTraps 15005 } 



rmxCfgInvalidAlarmFault  NOTIFICATION-TYPE
             OBJECTS   { rmxAlarmDescription , rmxActiveAlarmDateAndTime, rmxActiveAlarmIndex , rmxActiveAlarmListName , rmxActiveAlarmRmxStatus }
             STATUS  current
             DESCRIPTION
             "Invalid System Configuration"
             ::= { rmxTraps 5006 } 



rmxCfgInvalidAlarmClear  NOTIFICATION-TYPE
             OBJECTS   { rmxAlarmDescription , rmxActiveAlarmDateAndTime, rmxActiveAlarmIndex , rmxActiveAlarmListName , rmxActiveAlarmRmxStatus }
             STATUS  current
             DESCRIPTION
             "Invalid System Configuration"
             ::= { rmxTraps 15006 } 



rmxDebugModeAlarmFault  NOTIFICATION-TYPE
             OBJECTS   { rmxAlarmDescription , rmxActiveAlarmDateAndTime, rmxActiveAlarmIndex , rmxActiveAlarmListName , rmxActiveAlarmRmxStatus }
             STATUS  current
             DESCRIPTION
             "DEBUG mode enabled"
             ::= { rmxTraps 5007 } 



rmxDebugModeAlarmClear  NOTIFICATION-TYPE
             OBJECTS   { rmxAlarmDescription , rmxActiveAlarmDateAndTime, rmxActiveAlarmIndex , rmxActiveAlarmListName , rmxActiveAlarmRmxStatus }
             STATUS  current
             DESCRIPTION
             "DEBUG mode enabled"
             ::= { rmxTraps 15007 } 



rmxLowProcessMemoryAlertAlarmFault  NOTIFICATION-TYPE
             OBJECTS   { rmxAlarmDescription , rmxActiveAlarmDateAndTime, rmxActiveAlarmIndex , rmxActiveAlarmListName , rmxActiveAlarmRmxStatus }
             STATUS  current
             DESCRIPTION
             "Low Processing Memory"
             ::= { rmxTraps 5008 } 



rmxLowProcessMemoryAlertAlarmClear  NOTIFICATION-TYPE
             OBJECTS   { rmxAlarmDescription , rmxActiveAlarmDateAndTime, rmxActiveAlarmIndex , rmxActiveAlarmListName , rmxActiveAlarmRmxStatus }
             STATUS  current
             DESCRIPTION
             "Low Processing Memory"
             ::= { rmxTraps 15008 } 



rmxLowSystemMemoryAlertAlarmFault  NOTIFICATION-TYPE
             OBJECTS   { rmxAlarmDescription , rmxActiveAlarmDateAndTime, rmxActiveAlarmIndex , rmxActiveAlarmListName , rmxActiveAlarmRmxStatus }
             STATUS  current
             DESCRIPTION
             "Low system Memory"
             ::= { rmxTraps 5009 } 



rmxLowSystemMemoryAlertAlarmClear  NOTIFICATION-TYPE
             OBJECTS   { rmxAlarmDescription , rmxActiveAlarmDateAndTime, rmxActiveAlarmIndex , rmxActiveAlarmListName , rmxActiveAlarmRmxStatus }
             STATUS  current
             DESCRIPTION
             "Low system Memory"
             ::= { rmxTraps 15009 } 



rmxSystemCpuUsageAlertAlarmFault  NOTIFICATION-TYPE
             OBJECTS   { rmxAlarmDescription , rmxActiveAlarmDateAndTime, rmxActiveAlarmIndex , rmxActiveAlarmListName , rmxActiveAlarmRmxStatus }
             STATUS  current
             DESCRIPTION
             "High system CPU usage"
             ::= { rmxTraps 5010 } 



rmxSystemCpuUsageAlertAlarmClear  NOTIFICATION-TYPE
             OBJECTS   { rmxAlarmDescription , rmxActiveAlarmDateAndTime, rmxActiveAlarmIndex , rmxActiveAlarmListName , rmxActiveAlarmRmxStatus }
             STATUS  current
             DESCRIPTION
             "High system CPU usage"
             ::= { rmxTraps 15010 } 



rmxTestErrorAlarmFault  NOTIFICATION-TYPE
             OBJECTS   { rmxAlarmDescription , rmxActiveAlarmDateAndTime, rmxActiveAlarmIndex , rmxActiveAlarmListName , rmxActiveAlarmRmxStatus }
             STATUS  current
             DESCRIPTION
             "Used for testing the Active Alarms mechanism"
             ::= { rmxTraps 5011 } 



rmxTestErrorAlarmClear  NOTIFICATION-TYPE
             OBJECTS   { rmxAlarmDescription , rmxActiveAlarmDateAndTime, rmxActiveAlarmIndex , rmxActiveAlarmListName , rmxActiveAlarmRmxStatus }
             STATUS  current
             DESCRIPTION
             "Used for testing the Active Alarms mechanism"
             ::= { rmxTraps 15011 } 



rmxSipSecuredCommunicationFailedAlarmFault  NOTIFICATION-TYPE
             OBJECTS   { rmxAlarmDescription , rmxActiveAlarmDateAndTime, rmxActiveAlarmIndex , rmxActiveAlarmListName , rmxActiveAlarmRmxStatus }
             STATUS  current
             DESCRIPTION
             "Secured SIP communication failed"
             ::= { rmxTraps 5012 } 



rmxSipSecuredCommunicationFailedAlarmClear  NOTIFICATION-TYPE
             OBJECTS   { rmxAlarmDescription , rmxActiveAlarmDateAndTime, rmxActiveAlarmIndex , rmxActiveAlarmListName , rmxActiveAlarmRmxStatus }
             STATUS  current
             DESCRIPTION
             "Secured SIP communication failed"
             ::= { rmxTraps 15012 } 



rmxBadFileAlarmFault  NOTIFICATION-TYPE
             OBJECTS   { rmxAlarmDescription , rmxActiveAlarmDateAndTime, rmxActiveAlarmIndex , rmxActiveAlarmListName , rmxActiveAlarmRmxStatus }
             STATUS  current
             DESCRIPTION
             "File error"
             ::= { rmxTraps 5013 } 



rmxBadFileAlarmClear  NOTIFICATION-TYPE
             OBJECTS   { rmxAlarmDescription , rmxActiveAlarmDateAndTime, rmxActiveAlarmIndex , rmxActiveAlarmListName , rmxActiveAlarmRmxStatus }
             STATUS  current
             DESCRIPTION
             "File error"
             ::= { rmxTraps 15013 } 



rmxHighCpuUsageProcessAlertAlarmFault  NOTIFICATION-TYPE
             OBJECTS   { rmxAlarmDescription , rmxActiveAlarmDateAndTime, rmxActiveAlarmIndex , rmxActiveAlarmListName , rmxActiveAlarmRmxStatus }
             STATUS  current
             DESCRIPTION
             "High CPU utilization"
             ::= { rmxTraps 5014 } 



rmxHighCpuUsageProcessAlertAlarmClear  NOTIFICATION-TYPE
             OBJECTS   { rmxAlarmDescription , rmxActiveAlarmDateAndTime, rmxActiveAlarmIndex , rmxActiveAlarmListName , rmxActiveAlarmRmxStatus }
             STATUS  current
             DESCRIPTION
             "High CPU utilization"
             ::= { rmxTraps 15014 } 



rmxIdleDeadlineReachedAlarmFault  NOTIFICATION-TYPE
             OBJECTS   { rmxAlarmDescription , rmxActiveAlarmDateAndTime, rmxActiveAlarmIndex , rmxActiveAlarmListName , rmxActiveAlarmRmxStatus }
             STATUS  current
             DESCRIPTION
             "Process idle"
             ::= { rmxTraps 5016 } 



rmxIdleDeadlineReachedAlarmClear  NOTIFICATION-TYPE
             OBJECTS   { rmxAlarmDescription , rmxActiveAlarmDateAndTime, rmxActiveAlarmIndex , rmxActiveAlarmListName , rmxActiveAlarmRmxStatus }
             STATUS  current
             DESCRIPTION
             "Process idle"
             ::= { rmxTraps 15016 } 



rmxStartupConditionConfigurationAlarmFault  NOTIFICATION-TYPE
             OBJECTS   { rmxAlarmDescription , rmxActiveAlarmDateAndTime, rmxActiveAlarmIndex , rmxActiveAlarmListName , rmxActiveAlarmRmxStatus }
             STATUS  current
             DESCRIPTION
             "Internal System configuration during startup"
             ::= { rmxTraps 5017 } 



rmxStartupConditionConfigurationAlarmClear  NOTIFICATION-TYPE
             OBJECTS   { rmxAlarmDescription , rmxActiveAlarmDateAndTime, rmxActiveAlarmIndex , rmxActiveAlarmListName , rmxActiveAlarmRmxStatus }
             STATUS  current
             DESCRIPTION
             "Internal System configuration during startup"
             ::= { rmxTraps 15017 } 



rmxRestoringDefaultFactoryAlarmFault  NOTIFICATION-TYPE
             OBJECTS   { rmxAlarmDescription , rmxActiveAlarmDateAndTime, rmxActiveAlarmIndex , rmxActiveAlarmListName , rmxActiveAlarmRmxStatus }
             STATUS  current
             DESCRIPTION
             "Restoring Factory Defaults. Default system settings will be restored once Reset is completed"
             ::= { rmxTraps 5018 } 



rmxRestoringDefaultFactoryAlarmClear  NOTIFICATION-TYPE
             OBJECTS   { rmxAlarmDescription , rmxActiveAlarmDateAndTime, rmxActiveAlarmIndex , rmxActiveAlarmListName , rmxActiveAlarmRmxStatus }
             STATUS  current
             DESCRIPTION
             "Restoring Factory Defaults. Default system settings will be restored once Reset is completed"
             ::= { rmxTraps 15018 } 



rmxIpVersionChangedAlarmFault  NOTIFICATION-TYPE
             OBJECTS   { rmxAlarmDescription , rmxActiveAlarmDateAndTime, rmxActiveAlarmIndex , rmxActiveAlarmListName , rmxActiveAlarmRmxStatus }
             STATUS  current
             DESCRIPTION
             "IP Version has been changed"
             ::= { rmxTraps 5019 } 



rmxIpVersionChangedAlarmClear  NOTIFICATION-TYPE
             OBJECTS   { rmxAlarmDescription , rmxActiveAlarmDateAndTime, rmxActiveAlarmIndex , rmxActiveAlarmListName , rmxActiveAlarmRmxStatus }
             STATUS  current
             DESCRIPTION
             "IP Version has been changed"
             ::= { rmxTraps 15019 } 



rmxNoServiceFoundInDbAlarmFault  NOTIFICATION-TYPE
             OBJECTS   { rmxAlarmDescription , rmxActiveAlarmDateAndTime, rmxActiveAlarmIndex , rmxActiveAlarmListName , rmxActiveAlarmRmxStatus }
             STATUS  current
             DESCRIPTION
             "IP Network Service not found"
             ::= { rmxTraps 5050 } 



rmxNoServiceFoundInDbAlarmClear  NOTIFICATION-TYPE
             OBJECTS   { rmxAlarmDescription , rmxActiveAlarmDateAndTime, rmxActiveAlarmIndex , rmxActiveAlarmListName , rmxActiveAlarmRmxStatus }
             STATUS  current
             DESCRIPTION
             "IP Network Service not found"
             ::= { rmxTraps 15050 } 



rmxNoConnectionWithCsAlarmFault  NOTIFICATION-TYPE
             OBJECTS   { rmxAlarmDescription , rmxActiveAlarmDateAndTime, rmxActiveAlarmIndex , rmxActiveAlarmListName , rmxActiveAlarmRmxStatus }
             STATUS  current
             DESCRIPTION
             "No response from Central Signaling"
             ::= { rmxTraps 5052 } 



rmxNoConnectionWithCsAlarmClear  NOTIFICATION-TYPE
             OBJECTS   { rmxAlarmDescription , rmxActiveAlarmDateAndTime, rmxActiveAlarmIndex , rmxActiveAlarmListName , rmxActiveAlarmRmxStatus }
             STATUS  current
             DESCRIPTION
             "No response from Central Signaling"
             ::= { rmxTraps 15052 } 



rmxCsComponentFatalAlarmFault  NOTIFICATION-TYPE
             OBJECTS   { rmxAlarmDescription , rmxActiveAlarmDateAndTime, rmxActiveAlarmIndex , rmxActiveAlarmListName , rmxActiveAlarmRmxStatus }
             STATUS  current
             DESCRIPTION
             "Central signaling component failure"
             ::= { rmxTraps 5053 } 



rmxCsComponentFatalAlarmClear  NOTIFICATION-TYPE
             OBJECTS   { rmxAlarmDescription , rmxActiveAlarmDateAndTime, rmxActiveAlarmIndex , rmxActiveAlarmListName , rmxActiveAlarmRmxStatus }
             STATUS  current
             DESCRIPTION
             "Central signaling component failure"
             ::= { rmxTraps 15053 } 



rmxCsNotConfiguredAlarmFault  NOTIFICATION-TYPE
             OBJECTS   { rmxAlarmDescription , rmxActiveAlarmDateAndTime, rmxActiveAlarmIndex , rmxActiveAlarmListName , rmxActiveAlarmRmxStatus }
             STATUS  current
             DESCRIPTION
             "Missing Central Signaling configuration"
             ::= { rmxTraps 5054 } 



rmxCsNotConfiguredAlarmClear  NOTIFICATION-TYPE
             OBJECTS   { rmxAlarmDescription , rmxActiveAlarmDateAndTime, rmxActiveAlarmIndex , rmxActiveAlarmListName , rmxActiveAlarmRmxStatus }
             STATUS  current
             DESCRIPTION
             "Missing Central Signaling configuration"
             ::= { rmxTraps 15054 } 



rmxCsServiceStateFailAlarmFault  NOTIFICATION-TYPE
             OBJECTS   { rmxAlarmDescription , rmxActiveAlarmDateAndTime, rmxActiveAlarmIndex , rmxActiveAlarmListName , rmxActiveAlarmRmxStatus }
             STATUS  current
             DESCRIPTION
             "Central Signaling indicating Faulty status"
             ::= { rmxTraps 5055 } 



rmxCsServiceStateFailAlarmClear  NOTIFICATION-TYPE
             OBJECTS   { rmxAlarmDescription , rmxActiveAlarmDateAndTime, rmxActiveAlarmIndex , rmxActiveAlarmListName , rmxActiveAlarmRmxStatus }
             STATUS  current
             DESCRIPTION
             "Central Signaling indicating Faulty status"
             ::= { rmxTraps 15055 } 



rmxCsStartupFailedAlarmFault  NOTIFICATION-TYPE
             OBJECTS   { rmxAlarmDescription , rmxActiveAlarmDateAndTime, rmxActiveAlarmIndex , rmxActiveAlarmListName , rmxActiveAlarmRmxStatus }
             STATUS  current
             DESCRIPTION
             "Central Signaling startup failure"
             ::= { rmxTraps 5056 } 



rmxCsStartupFailedAlarmClear  NOTIFICATION-TYPE
             OBJECTS   { rmxAlarmDescription , rmxActiveAlarmDateAndTime, rmxActiveAlarmIndex , rmxActiveAlarmListName , rmxActiveAlarmRmxStatus }
             STATUS  current
             DESCRIPTION
             "Central Signaling startup failure"
             ::= { rmxTraps 15056 } 



rmxDuplicateIpCsMngmntAlarmFault  NOTIFICATION-TYPE
             OBJECTS   { rmxAlarmDescription , rmxActiveAlarmDateAndTime, rmxActiveAlarmIndex , rmxActiveAlarmListName , rmxActiveAlarmRmxStatus }
             STATUS  current
             DESCRIPTION
             "IP addresses of Signaling Host and Control Unit are the same"
             ::= { rmxTraps 5058 } 



rmxDuplicateIpCsMngmntAlarmClear  NOTIFICATION-TYPE
             OBJECTS   { rmxAlarmDescription , rmxActiveAlarmDateAndTime, rmxActiveAlarmIndex , rmxActiveAlarmListName , rmxActiveAlarmRmxStatus }
             STATUS  current
             DESCRIPTION
             "IP addresses of Signaling Host and Control Unit are the same"
             ::= { rmxTraps 15058 } 



rmxIpServiceDeletedAlarmFault  NOTIFICATION-TYPE
             OBJECTS   { rmxAlarmDescription , rmxActiveAlarmDateAndTime, rmxActiveAlarmIndex , rmxActiveAlarmListName , rmxActiveAlarmRmxStatus }
             STATUS  current
             DESCRIPTION
             "IP Network Service deleted"
             ::= { rmxTraps 5059 } 



rmxIpServiceDeletedAlarmClear  NOTIFICATION-TYPE
             OBJECTS   { rmxAlarmDescription , rmxActiveAlarmDateAndTime, rmxActiveAlarmIndex , rmxActiveAlarmListName , rmxActiveAlarmRmxStatus }
             STATUS  current
             DESCRIPTION
             "IP Network Service deleted"
             ::= { rmxTraps 15059 } 



rmxIpServiceChangedAlarmFault  NOTIFICATION-TYPE
             OBJECTS   { rmxAlarmDescription , rmxActiveAlarmDateAndTime, rmxActiveAlarmIndex , rmxActiveAlarmListName , rmxActiveAlarmRmxStatus }
             STATUS  current
             DESCRIPTION
             "IP Network Service configuration modified"
             ::= { rmxTraps 5060 } 



rmxIpServiceChangedAlarmClear  NOTIFICATION-TYPE
             OBJECTS   { rmxAlarmDescription , rmxActiveAlarmDateAndTime, rmxActiveAlarmIndex , rmxActiveAlarmListName , rmxActiveAlarmRmxStatus }
             STATUS  current
             DESCRIPTION
             "IP Network Service configuration modified"
             ::= { rmxTraps 15060 } 



rmxCsRecoveryStatusAlarmFault  NOTIFICATION-TYPE
             OBJECTS   { rmxAlarmDescription , rmxActiveAlarmDateAndTime, rmxActiveAlarmIndex , rmxActiveAlarmListName , rmxActiveAlarmRmxStatus }
             STATUS  current
             DESCRIPTION
             "Central Signaling indicating Recovery status"
             ::= { rmxTraps 5061 } 



rmxCsRecoveryStatusAlarmClear  NOTIFICATION-TYPE
             OBJECTS   { rmxAlarmDescription , rmxActiveAlarmDateAndTime, rmxActiveAlarmIndex , rmxActiveAlarmListName , rmxActiveAlarmRmxStatus }
             STATUS  current
             DESCRIPTION
             "Central Signaling indicating Recovery status"
             ::= { rmxTraps 15061 } 



rmxExternalAlertCsAlarmFault  NOTIFICATION-TYPE
             OBJECTS   { rmxAlarmDescription , rmxActiveAlarmDateAndTime, rmxActiveAlarmIndex , rmxActiveAlarmListName , rmxActiveAlarmRmxStatus }
             STATUS  current
             DESCRIPTION
             "Alarm generated by a Central Signaling component"
             ::= { rmxTraps 5062 } 



rmxExternalAlertCsAlarmClear  NOTIFICATION-TYPE
             OBJECTS   { rmxAlarmDescription , rmxActiveAlarmDateAndTime, rmxActiveAlarmIndex , rmxActiveAlarmListName , rmxActiveAlarmRmxStatus }
             STATUS  current
             DESCRIPTION
             "Alarm generated by a Central Signaling component"
             ::= { rmxTraps 15062 } 



rmxProductActivationFailureAlarmFault  NOTIFICATION-TYPE
             OBJECTS   { rmxAlarmDescription , rmxActiveAlarmDateAndTime, rmxActiveAlarmIndex , rmxActiveAlarmListName , rmxActiveAlarmRmxStatus }
             STATUS  current
             DESCRIPTION
             "Product activation failure"
             ::= { rmxTraps 5100 } 



rmxProductActivationFailureAlarmClear  NOTIFICATION-TYPE
             OBJECTS   { rmxAlarmDescription , rmxActiveAlarmDateAndTime, rmxActiveAlarmIndex , rmxActiveAlarmListName , rmxActiveAlarmRmxStatus }
             STATUS  current
             DESCRIPTION
             "Product activation failure"
             ::= { rmxTraps 15100 } 



rmxNoManagementIpInterfaceAlarmFault  NOTIFICATION-TYPE
             OBJECTS   { rmxAlarmDescription , rmxActiveAlarmDateAndTime, rmxActiveAlarmIndex , rmxActiveAlarmListName , rmxActiveAlarmRmxStatus }
             STATUS  current
             DESCRIPTION
             "Management Network not configured"
             ::= { rmxTraps 5101 } 



rmxNoManagementIpInterfaceAlarmClear  NOTIFICATION-TYPE
             OBJECTS   { rmxAlarmDescription , rmxActiveAlarmDateAndTime, rmxActiveAlarmIndex , rmxActiveAlarmListName , rmxActiveAlarmRmxStatus }
             STATUS  current
             DESCRIPTION
             "Management Network not configured"
             ::= { rmxTraps 15101 } 



rmxNoTimeConfigurationAlarmFault  NOTIFICATION-TYPE
             OBJECTS   { rmxAlarmDescription , rmxActiveAlarmDateAndTime, rmxActiveAlarmIndex , rmxActiveAlarmListName , rmxActiveAlarmRmxStatus }
             STATUS  current
             DESCRIPTION
             "Error reading MCU time"
             ::= { rmxTraps 5102 } 



rmxNoTimeConfigurationAlarmClear  NOTIFICATION-TYPE
             OBJECTS   { rmxAlarmDescription , rmxActiveAlarmDateAndTime, rmxActiveAlarmIndex , rmxActiveAlarmListName , rmxActiveAlarmRmxStatus }
             STATUS  current
             DESCRIPTION
             "Error reading MCU time"
             ::= { rmxTraps 15102 } 



rmxMplStartupFailureAuthenticationNotReceivedAlarmFault  NOTIFICATION-TYPE
             OBJECTS   { rmxAlarmDescription , rmxActiveAlarmDateAndTime, rmxActiveAlarmIndex , rmxActiveAlarmListName , rmxActiveAlarmRmxStatus }
             STATUS  current
             DESCRIPTION
             "MPL startup failure. Authentication not received."
             ::= { rmxTraps 5103 } 



rmxMplStartupFailureAuthenticationNotReceivedAlarmClear  NOTIFICATION-TYPE
             OBJECTS   { rmxAlarmDescription , rmxActiveAlarmDateAndTime, rmxActiveAlarmIndex , rmxActiveAlarmListName , rmxActiveAlarmRmxStatus }
             STATUS  current
             DESCRIPTION
             "MPL startup failure. Authentication not received."
             ::= { rmxTraps 15103 } 



rmxMplStartupFailureMngmntIpCnfgNotReceivedAlarmFault  NOTIFICATION-TYPE
             OBJECTS   { rmxAlarmDescription , rmxActiveAlarmDateAndTime, rmxActiveAlarmIndex , rmxActiveAlarmListName , rmxActiveAlarmRmxStatus }
             STATUS  current
             DESCRIPTION
             "MPL startup failure. Management Network configuration not received."
             ::= { rmxTraps 5104 } 



rmxMplStartupFailureMngmntIpCnfgNotReceivedAlarmClear  NOTIFICATION-TYPE
             OBJECTS   { rmxAlarmDescription , rmxActiveAlarmDateAndTime, rmxActiveAlarmIndex , rmxActiveAlarmListName , rmxActiveAlarmRmxStatus }
             STATUS  current
             DESCRIPTION
             "MPL startup failure. Management Network configuration not received."
             ::= { rmxTraps 15104 } 



rmxNoDnsConfigurationAlarmFault  NOTIFICATION-TYPE
             OBJECTS   { rmxAlarmDescription , rmxActiveAlarmDateAndTime, rmxActiveAlarmIndex , rmxActiveAlarmListName , rmxActiveAlarmRmxStatus }
             STATUS  current
             DESCRIPTION
             "DNS not configured in IP Network Service"
             ::= { rmxTraps 5105 } 



rmxNoDnsConfigurationAlarmClear  NOTIFICATION-TYPE
             OBJECTS   { rmxAlarmDescription , rmxActiveAlarmDateAndTime, rmxActiveAlarmIndex , rmxActiveAlarmListName , rmxActiveAlarmRmxStatus }
             STATUS  current
             DESCRIPTION
             "DNS not configured in IP Network Service"
             ::= { rmxTraps 15105 } 



rmxDnsRegistraionFailedAlarmFault  NOTIFICATION-TYPE
             OBJECTS   { rmxAlarmDescription , rmxActiveAlarmDateAndTime, rmxActiveAlarmIndex , rmxActiveAlarmListName , rmxActiveAlarmRmxStatus }
             STATUS  current
             DESCRIPTION
             "Failed to register with DNS server"
             ::= { rmxTraps 5106 } 



rmxDnsRegistraionFailedAlarmClear  NOTIFICATION-TYPE
             OBJECTS   { rmxAlarmDescription , rmxActiveAlarmDateAndTime, rmxActiveAlarmIndex , rmxActiveAlarmListName , rmxActiveAlarmRmxStatus }
             STATUS  current
             DESCRIPTION
             "Failed to register with DNS server"
             ::= { rmxTraps 15106 } 



rmxFailedToOpenApacheConfigurationFileAlarmFault  NOTIFICATION-TYPE
             OBJECTS   { rmxAlarmDescription , rmxActiveAlarmDateAndTime, rmxActiveAlarmIndex , rmxActiveAlarmListName , rmxActiveAlarmRmxStatus }
             STATUS  current
             DESCRIPTION
             "Failed to open Apache server configuration file"
             ::= { rmxTraps 5107 } 



rmxFailedToOpenApacheConfigurationFileAlarmClear  NOTIFICATION-TYPE
             OBJECTS   { rmxAlarmDescription , rmxActiveAlarmDateAndTime, rmxActiveAlarmIndex , rmxActiveAlarmListName , rmxActiveAlarmRmxStatus }
             STATUS  current
             DESCRIPTION
             "Failed to open Apache server configuration file"
             ::= { rmxTraps 15107 } 



rmxFailedToSaveApacheConfigurationFileAlarmFault  NOTIFICATION-TYPE
             OBJECTS   { rmxAlarmDescription , rmxActiveAlarmDateAndTime, rmxActiveAlarmIndex , rmxActiveAlarmListName , rmxActiveAlarmRmxStatus }
             STATUS  current
             DESCRIPTION
             "Failed to save Apache server configuration file"
             ::= { rmxTraps 5108 } 



rmxFailedToSaveApacheConfigurationFileAlarmClear  NOTIFICATION-TYPE
             OBJECTS   { rmxAlarmDescription , rmxActiveAlarmDateAndTime, rmxActiveAlarmIndex , rmxActiveAlarmListName , rmxActiveAlarmRmxStatus }
             STATUS  current
             DESCRIPTION
             "Failed to save Apache server configuration file"
             ::= { rmxTraps 15108 } 



rmxPatchedVersionAlarmFault  NOTIFICATION-TYPE
             OBJECTS   { rmxAlarmDescription , rmxActiveAlarmDateAndTime, rmxActiveAlarmIndex , rmxActiveAlarmListName , rmxActiveAlarmRmxStatus }
             STATUS  current
             DESCRIPTION
             "The software contains patch(es)"
             ::= { rmxTraps 5109 } 



rmxPatchedVersionAlarmClear  NOTIFICATION-TYPE
             OBJECTS   { rmxAlarmDescription , rmxActiveAlarmDateAndTime, rmxActiveAlarmIndex , rmxActiveAlarmListName , rmxActiveAlarmRmxStatus }
             STATUS  current
             DESCRIPTION
             "The software contains patch(es)"
             ::= { rmxTraps 15109 } 



rmxPrivateVersionAlarmFault  NOTIFICATION-TYPE
             OBJECTS   { rmxAlarmDescription , rmxActiveAlarmDateAndTime, rmxActiveAlarmIndex , rmxActiveAlarmListName , rmxActiveAlarmRmxStatus }
             STATUS  current
             DESCRIPTION
             "A private version is loaded"
             ::= { rmxTraps 5110 } 



rmxPrivateVersionAlarmClear  NOTIFICATION-TYPE
             OBJECTS   { rmxAlarmDescription , rmxActiveAlarmDateAndTime, rmxActiveAlarmIndex , rmxActiveAlarmListName , rmxActiveAlarmRmxStatus }
             STATUS  current
             DESCRIPTION
             "A private version is loaded"
             ::= { rmxTraps 15110 } 



rmxNtpSyncFailureAlarmFault  NOTIFICATION-TYPE
             OBJECTS   { rmxAlarmDescription , rmxActiveAlarmDateAndTime, rmxActiveAlarmIndex , rmxActiveAlarmListName , rmxActiveAlarmRmxStatus }
             STATUS  current
             DESCRIPTION
             "NTP synchronization failure"
             ::= { rmxTraps 5111 } 



rmxNtpSyncFailureAlarmClear  NOTIFICATION-TYPE
             OBJECTS   { rmxAlarmDescription , rmxActiveAlarmDateAndTime, rmxActiveAlarmIndex , rmxActiveAlarmListName , rmxActiveAlarmRmxStatus }
             STATUS  current
             DESCRIPTION
             "NTP synchronization failure"
             ::= { rmxTraps 15111 } 



rmxIllegalTimeAlarmFault  NOTIFICATION-TYPE
             OBJECTS   { rmxAlarmDescription , rmxActiveAlarmDateAndTime, rmxActiveAlarmIndex , rmxActiveAlarmListName , rmxActiveAlarmRmxStatus }
             STATUS  current
             DESCRIPTION
             "Invalid date and time"
             ::= { rmxTraps 5112 } 



rmxIllegalTimeAlarmClear  NOTIFICATION-TYPE
             OBJECTS   { rmxAlarmDescription , rmxActiveAlarmDateAndTime, rmxActiveAlarmIndex , rmxActiveAlarmListName , rmxActiveAlarmRmxStatus }
             STATUS  current
             DESCRIPTION
             "Invalid date and time"
             ::= { rmxTraps 15112 } 



rmxExternalNtpServersFailureAlarmFault  NOTIFICATION-TYPE
             OBJECTS   { rmxAlarmDescription , rmxActiveAlarmDateAndTime, rmxActiveAlarmIndex , rmxActiveAlarmListName , rmxActiveAlarmRmxStatus }
             STATUS  current
             DESCRIPTION
             "External NTP servers failure"
             ::= { rmxTraps 5113 } 



rmxExternalNtpServersFailureAlarmClear  NOTIFICATION-TYPE
             OBJECTS   { rmxAlarmDescription , rmxActiveAlarmDateAndTime, rmxActiveAlarmIndex , rmxActiveAlarmListName , rmxActiveAlarmRmxStatus }
             STATUS  current
             DESCRIPTION
             "External NTP servers failure"
             ::= { rmxTraps 15113 } 



rmxRunningVersionMismatchesCurrentVersionAlarmFault  NOTIFICATION-TYPE
             OBJECTS   { rmxAlarmDescription , rmxActiveAlarmDateAndTime, rmxActiveAlarmIndex , rmxActiveAlarmListName , rmxActiveAlarmRmxStatus }
             STATUS  current
             DESCRIPTION
             "Fallback version is being used"
             ::= { rmxTraps 5114 } 



rmxRunningVersionMismatchesCurrentVersionAlarmClear  NOTIFICATION-TYPE
             OBJECTS   { rmxAlarmDescription , rmxActiveAlarmDateAndTime, rmxActiveAlarmIndex , rmxActiveAlarmListName , rmxActiveAlarmRmxStatus }
             STATUS  current
             DESCRIPTION
             "Fallback version is being used"
             ::= { rmxTraps 15114 } 



rmxIdeNotInDmaModeAlarmFault  NOTIFICATION-TYPE
             OBJECTS   { rmxAlarmDescription , rmxActiveAlarmDateAndTime, rmxActiveAlarmIndex , rmxActiveAlarmListName , rmxActiveAlarmRmxStatus }
             STATUS  current
             DESCRIPTION
             "DMA not supported by IDE device"
             ::= { rmxTraps 5115 } 



rmxIdeNotInDmaModeAlarmClear  NOTIFICATION-TYPE
             OBJECTS   { rmxAlarmDescription , rmxActiveAlarmDateAndTime, rmxActiveAlarmIndex , rmxActiveAlarmListName , rmxActiveAlarmRmxStatus }
             STATUS  current
             DESCRIPTION
             "DMA not supported by IDE device"
             ::= { rmxTraps 15115 } 



rmxBadEthernetSettingsAlarmFault  NOTIFICATION-TYPE
             OBJECTS   { rmxAlarmDescription , rmxActiveAlarmDateAndTime, rmxActiveAlarmIndex , rmxActiveAlarmListName , rmxActiveAlarmRmxStatus }
             STATUS  current
             DESCRIPTION
             "Incorrect Ethernet Settings"
             ::= { rmxTraps 5116 } 



rmxBadEthernetSettingsAlarmClear  NOTIFICATION-TYPE
             OBJECTS   { rmxAlarmDescription , rmxActiveAlarmDateAndTime, rmxActiveAlarmIndex , rmxActiveAlarmListName , rmxActiveAlarmRmxStatus }
             STATUS  current
             DESCRIPTION
             "Incorrect Ethernet Settings"
             ::= { rmxTraps 15116 } 



rmxSmartReportErrorsOnHdAlarmFault  NOTIFICATION-TYPE
             OBJECTS   { rmxAlarmDescription , rmxActiveAlarmDateAndTime, rmxActiveAlarmIndex , rmxActiveAlarmListName , rmxActiveAlarmRmxStatus }
             STATUS  current
             DESCRIPTION
             "Smart Report found errors on hard disk"
             ::= { rmxTraps 5117 } 



rmxSmartReportErrorsOnHdAlarmClear  NOTIFICATION-TYPE
             OBJECTS   { rmxAlarmDescription , rmxActiveAlarmDateAndTime, rmxActiveAlarmIndex , rmxActiveAlarmListName , rmxActiveAlarmRmxStatus }
             STATUS  current
             DESCRIPTION
             "Smart Report found errors on hard disk"
             ::= { rmxTraps 15117 } 



rmxIllegalMcuVersionAlarmFault  NOTIFICATION-TYPE
             OBJECTS   { rmxAlarmDescription , rmxActiveAlarmDateAndTime, rmxActiveAlarmIndex , rmxActiveAlarmListName , rmxActiveAlarmRmxStatus }
             STATUS  current
             DESCRIPTION
             "Invalid MCU Version"
             ::= { rmxTraps 5118 } 



rmxIllegalMcuVersionAlarmClear  NOTIFICATION-TYPE
             OBJECTS   { rmxAlarmDescription , rmxActiveAlarmDateAndTime, rmxActiveAlarmIndex , rmxActiveAlarmListName , rmxActiveAlarmRmxStatus }
             STATUS  current
             DESCRIPTION
             "Invalid MCU Version"
             ::= { rmxTraps 15118 } 



rmxDebugCfgExistAlarmFault  NOTIFICATION-TYPE
             OBJECTS   { rmxAlarmDescription , rmxActiveAlarmDateAndTime, rmxActiveAlarmIndex , rmxActiveAlarmListName , rmxActiveAlarmRmxStatus }
             STATUS  current
             DESCRIPTION
             "DEBUG mode flags in use"
             ::= { rmxTraps 5119 } 



rmxDebugCfgExistAlarmClear  NOTIFICATION-TYPE
             OBJECTS   { rmxAlarmDescription , rmxActiveAlarmDateAndTime, rmxActiveAlarmIndex , rmxActiveAlarmListName , rmxActiveAlarmRmxStatus }
             STATUS  current
             DESCRIPTION
             "DEBUG mode flags in use"
             ::= { rmxTraps 15119 } 



rmxInstallingNewVersionAlarmFault  NOTIFICATION-TYPE
             OBJECTS   { rmxAlarmDescription , rmxActiveAlarmDateAndTime, rmxActiveAlarmIndex , rmxActiveAlarmListName , rmxActiveAlarmRmxStatus }
             STATUS  current
             DESCRIPTION
             "Version upgrade is in progress"
             ::= { rmxTraps 5120 } 



rmxInstallingNewVersionAlarmClear  NOTIFICATION-TYPE
             OBJECTS   { rmxAlarmDescription , rmxActiveAlarmDateAndTime, rmxActiveAlarmIndex , rmxActiveAlarmListName , rmxActiveAlarmRmxStatus }
             STATUS  current
             DESCRIPTION
             "Version upgrade is in progress"
             ::= { rmxTraps 15120 } 



rmxSshEnabledAlarmFault  NOTIFICATION-TYPE
             OBJECTS   { rmxAlarmDescription , rmxActiveAlarmDateAndTime, rmxActiveAlarmIndex , rmxActiveAlarmListName , rmxActiveAlarmRmxStatus }
             STATUS  current
             DESCRIPTION
             "SSH is enabled"
             ::= { rmxTraps 5121 } 



rmxSshEnabledAlarmClear  NOTIFICATION-TYPE
             OBJECTS   { rmxAlarmDescription , rmxActiveAlarmDateAndTime, rmxActiveAlarmIndex , rmxActiveAlarmListName , rmxActiveAlarmRmxStatus }
             STATUS  current
             DESCRIPTION
             "SSH is enabled"
             ::= { rmxTraps 15121 } 



rmxFailedToValidateCertificateAlarmFault  NOTIFICATION-TYPE
             OBJECTS   { rmxAlarmDescription , rmxActiveAlarmDateAndTime, rmxActiveAlarmIndex , rmxActiveAlarmListName , rmxActiveAlarmRmxStatus }
             STATUS  current
             DESCRIPTION
             "Security mode failed. Error in certificate file."
             ::= { rmxTraps 5122 } 



rmxFailedToValidateCertificateAlarmClear  NOTIFICATION-TYPE
             OBJECTS   { rmxAlarmDescription , rmxActiveAlarmDateAndTime, rmxActiveAlarmIndex , rmxActiveAlarmListName , rmxActiveAlarmRmxStatus }
             STATUS  current
             DESCRIPTION
             "Security mode failed. Error in certificate file."
             ::= { rmxTraps 15122 } 



rmxCertificateExpiredAlarmFault  NOTIFICATION-TYPE
             OBJECTS   { rmxAlarmDescription , rmxActiveAlarmDateAndTime, rmxActiveAlarmIndex , rmxActiveAlarmListName , rmxActiveAlarmRmxStatus }
             STATUS  current
             DESCRIPTION
             "Security mode failed. Certificate has expired."
             ::= { rmxTraps 5123 } 



rmxCertificateExpiredAlarmClear  NOTIFICATION-TYPE
             OBJECTS   { rmxAlarmDescription , rmxActiveAlarmDateAndTime, rmxActiveAlarmIndex , rmxActiveAlarmListName , rmxActiveAlarmRmxStatus }
             STATUS  current
             DESCRIPTION
             "Security mode failed. Certificate has expired."
             ::= { rmxTraps 15123 } 



rmxCertificateCommonNameErrorAlarmFault  NOTIFICATION-TYPE
             OBJECTS   { rmxAlarmDescription , rmxActiveAlarmDateAndTime, rmxActiveAlarmIndex , rmxActiveAlarmListName , rmxActiveAlarmRmxStatus }
             STATUS  current
             DESCRIPTION
             "Security mode failed. Certificate host name does not match the RMX host name."
             ::= { rmxTraps 5124 } 



rmxCertificateCommonNameErrorAlarmClear  NOTIFICATION-TYPE
             OBJECTS   { rmxAlarmDescription , rmxActiveAlarmDateAndTime, rmxActiveAlarmIndex , rmxActiveAlarmListName , rmxActiveAlarmRmxStatus }
             STATUS  current
             DESCRIPTION
             "Security mode failed. Certificate host name does not match the RMX host name."
             ::= { rmxTraps 15124 } 



rmxCertificateNotValidYetAlarmFault  NOTIFICATION-TYPE
             OBJECTS   { rmxAlarmDescription , rmxActiveAlarmDateAndTime, rmxActiveAlarmIndex , rmxActiveAlarmListName , rmxActiveAlarmRmxStatus }
             STATUS  current
             DESCRIPTION
             "Security mode failed. Certificate not yet valid."
             ::= { rmxTraps 5125 } 



rmxCertificateNotValidYetAlarmClear  NOTIFICATION-TYPE
             OBJECTS   { rmxAlarmDescription , rmxActiveAlarmDateAndTime, rmxActiveAlarmIndex , rmxActiveAlarmListName , rmxActiveAlarmRmxStatus }
             STATUS  current
             DESCRIPTION
             "Security mode failed. Certificate not yet valid."
             ::= { rmxTraps 15125 } 



rmxCertificateGoingToBeExpiredAlarmFault  NOTIFICATION-TYPE
             OBJECTS   { rmxAlarmDescription , rmxActiveAlarmDateAndTime, rmxActiveAlarmIndex , rmxActiveAlarmListName , rmxActiveAlarmRmxStatus }
             STATUS  current
             DESCRIPTION
             "Security mode failed. Certificate is about to expire."
             ::= { rmxTraps 5126 } 



rmxCertificateGoingToBeExpiredAlarmClear  NOTIFICATION-TYPE
             OBJECTS   { rmxAlarmDescription , rmxActiveAlarmDateAndTime, rmxActiveAlarmIndex , rmxActiveAlarmListName , rmxActiveAlarmRmxStatus }
             STATUS  current
             DESCRIPTION
             "Security mode failed. Certificate is about to expire."
             ::= { rmxTraps 15126 } 



rmxProductTypeMismatchAlarmFault  NOTIFICATION-TYPE
             OBJECTS   { rmxAlarmDescription , rmxActiveAlarmDateAndTime, rmxActiveAlarmIndex , rmxActiveAlarmListName , rmxActiveAlarmRmxStatus }
             STATUS  current
             DESCRIPTION
             "Product Type mismatch. System is restarting."
             ::= { rmxTraps 5127 } 



rmxProductTypeMismatchAlarmClear  NOTIFICATION-TYPE
             OBJECTS   { rmxAlarmDescription , rmxActiveAlarmDateAndTime, rmxActiveAlarmIndex , rmxActiveAlarmListName , rmxActiveAlarmRmxStatus }
             STATUS  current
             DESCRIPTION
             "Product Type mismatch. System is restarting."
             ::= { rmxTraps 15127 } 



rmxUnknownCpuSlotIdAlarmFault  NOTIFICATION-TYPE
             OBJECTS   { rmxAlarmDescription , rmxActiveAlarmDateAndTime, rmxActiveAlarmIndex , rmxActiveAlarmListName , rmxActiveAlarmRmxStatus }
             STATUS  current
             DESCRIPTION
             "CPU slot ID not identified"
             ::= { rmxTraps 5128 } 



rmxUnknownCpuSlotIdAlarmClear  NOTIFICATION-TYPE
             OBJECTS   { rmxAlarmDescription , rmxActiveAlarmDateAndTime, rmxActiveAlarmIndex , rmxActiveAlarmListName , rmxActiveAlarmRmxStatus }
             STATUS  current
             DESCRIPTION
             "CPU slot ID not identified"
             ::= { rmxTraps 15128 } 



rmxNoFipsTestResultFromEncryptionkeyserverAlarmFault  NOTIFICATION-TYPE
             OBJECTS   { rmxAlarmDescription , rmxActiveAlarmDateAndTime, rmxActiveAlarmIndex , rmxActiveAlarmListName , rmxActiveAlarmRmxStatus }
             STATUS  current
             DESCRIPTION
             "FIPS 140 test result not received"
             ::= { rmxTraps 5129 } 



rmxNoFipsTestResultFromEncryptionkeyserverAlarmClear  NOTIFICATION-TYPE
             OBJECTS   { rmxAlarmDescription , rmxActiveAlarmDateAndTime, rmxActiveAlarmIndex , rmxActiveAlarmListName , rmxActiveAlarmRmxStatus }
             STATUS  current
             DESCRIPTION
             "FIPS 140 test result not received"
             ::= { rmxTraps 15129 } 



rmxFipsFailureWithinEncryptionkeyserverAlarmFault  NOTIFICATION-TYPE
             OBJECTS   { rmxAlarmDescription , rmxActiveAlarmDateAndTime, rmxActiveAlarmIndex , rmxActiveAlarmListName , rmxActiveAlarmRmxStatus }
             STATUS  current
             DESCRIPTION
             "FIPS 140 failure"
             ::= { rmxTraps 5130 } 



rmxFipsFailureWithinEncryptionkeyserverAlarmClear  NOTIFICATION-TYPE
             OBJECTS   { rmxAlarmDescription , rmxActiveAlarmDateAndTime, rmxActiveAlarmIndex , rmxActiveAlarmListName , rmxActiveAlarmRmxStatus }
             STATUS  current
             DESCRIPTION
             "FIPS 140 failure"
             ::= { rmxTraps 15130 } 



rmxHttpsDisabledInJitcAlarmFault  NOTIFICATION-TYPE
             OBJECTS   { rmxAlarmDescription , rmxActiveAlarmDateAndTime, rmxActiveAlarmIndex , rmxActiveAlarmListName , rmxActiveAlarmRmxStatus }
             STATUS  current
             DESCRIPTION
             "The system has been configured for JITC mode, but communication is not secured until a TLS certificate is installed and the MCU is set to Secured communication."
             ::= { rmxTraps 5131 } 



rmxHttpsDisabledInJitcAlarmClear  NOTIFICATION-TYPE
             OBJECTS   { rmxAlarmDescription , rmxActiveAlarmDateAndTime, rmxActiveAlarmIndex , rmxActiveAlarmListName , rmxActiveAlarmRmxStatus }
             STATUS  current
             DESCRIPTION
             "The system has been configured for JITC mode, but communication is not secured until a TLS certificate is installed and the MCU is set to Secured communication."
             ::= { rmxTraps 15131 } 



rmxBackupOfCdrFilesIsRequiredAlarmFault  NOTIFICATION-TYPE
             OBJECTS   { rmxAlarmDescription , rmxActiveAlarmDateAndTime, rmxActiveAlarmIndex , rmxActiveAlarmListName , rmxActiveAlarmRmxStatus }
             STATUS  current
             DESCRIPTION
             "Backup of CDR files is required"
             ::= { rmxTraps 5140 } 



rmxBackupOfCdrFilesIsRequiredAlarmClear  NOTIFICATION-TYPE
             OBJECTS   { rmxAlarmDescription , rmxActiveAlarmDateAndTime, rmxActiveAlarmIndex , rmxActiveAlarmListName , rmxActiveAlarmRmxStatus }
             STATUS  current
             DESCRIPTION
             "Backup of CDR files is required"
             ::= { rmxTraps 15140 } 



rmxNoMusicSourceAlarmFault  NOTIFICATION-TYPE
             OBJECTS   { rmxAlarmDescription , rmxActiveAlarmDateAndTime, rmxActiveAlarmIndex , rmxActiveAlarmListName , rmxActiveAlarmRmxStatus }
             STATUS  current
             DESCRIPTION
             "Music file error"
             ::= { rmxTraps 5150 } 



rmxNoMusicSourceAlarmClear  NOTIFICATION-TYPE
             OBJECTS   { rmxAlarmDescription , rmxActiveAlarmDateAndTime, rmxActiveAlarmIndex , rmxActiveAlarmListName , rmxActiveAlarmRmxStatus }
             STATUS  current
             DESCRIPTION
             "Music file error"
             ::= { rmxTraps 15150 } 



rmxSwitchNotLoadedAlarmFault  NOTIFICATION-TYPE
             OBJECTS   { rmxAlarmDescription , rmxActiveAlarmDateAndTime, rmxActiveAlarmIndex , rmxActiveAlarmListName , rmxActiveAlarmRmxStatus }
             STATUS  current
             DESCRIPTION
             "SWITCH not responding"
             ::= { rmxTraps 5151 } 



rmxSwitchNotLoadedAlarmClear  NOTIFICATION-TYPE
             OBJECTS   { rmxAlarmDescription , rmxActiveAlarmDateAndTime, rmxActiveAlarmIndex , rmxActiveAlarmListName , rmxActiveAlarmRmxStatus }
             STATUS  current
             DESCRIPTION
             "SWITCH not responding"
             ::= { rmxTraps 15151 } 



rmxNoIsdnServiceParamsAlarmFault  NOTIFICATION-TYPE
             OBJECTS   { rmxAlarmDescription , rmxActiveAlarmDateAndTime, rmxActiveAlarmIndex , rmxActiveAlarmListName , rmxActiveAlarmRmxStatus }
             STATUS  current
             DESCRIPTION
             "No ISDN/PSTN Network Services defined"
             ::= { rmxTraps 5152 } 



rmxNoIsdnServiceParamsAlarmClear  NOTIFICATION-TYPE
             OBJECTS   { rmxAlarmDescription , rmxActiveAlarmDateAndTime, rmxActiveAlarmIndex , rmxActiveAlarmListName , rmxActiveAlarmRmxStatus }
             STATUS  current
             DESCRIPTION
             "No ISDN/PSTN Network Services defined"
             ::= { rmxTraps 15152 } 



rmxModuleDoesNotExistAlarmFault  NOTIFICATION-TYPE
             OBJECTS   { rmxAlarmDescription , rmxActiveAlarmDateAndTime, rmxActiveAlarmIndex , rmxActiveAlarmListName , rmxActiveAlarmRmxStatus }
             STATUS  current
             DESCRIPTION
             "Card not found"
             ::= { rmxTraps 5153 } 



rmxModuleDoesNotExistAlarmClear  NOTIFICATION-TYPE
             OBJECTS   { rmxAlarmDescription , rmxActiveAlarmDateAndTime, rmxActiveAlarmIndex , rmxActiveAlarmListName , rmxActiveAlarmRmxStatus }
             STATUS  current
             DESCRIPTION
             "Card not found"
             ::= { rmxTraps 15153 } 



rmxNoDefaultIsdnServiceAlarmFault  NOTIFICATION-TYPE
             OBJECTS   { rmxAlarmDescription , rmxActiveAlarmDateAndTime, rmxActiveAlarmIndex , rmxActiveAlarmListName , rmxActiveAlarmRmxStatus }
             STATUS  current
             DESCRIPTION
             "No default ISDN/PSTN Network Service defined in ISDN/PSTN Network Services list"
             ::= { rmxTraps 5154 } 



rmxNoDefaultIsdnServiceAlarmClear  NOTIFICATION-TYPE
             OBJECTS   { rmxAlarmDescription , rmxActiveAlarmDateAndTime, rmxActiveAlarmIndex , rmxActiveAlarmListName , rmxActiveAlarmRmxStatus }
             STATUS  current
             DESCRIPTION
             "No default ISDN/PSTN Network Service defined in ISDN/PSTN Network Services list"
             ::= { rmxTraps 15154 } 



rmxExternalAlertEmbAlarmFault  NOTIFICATION-TYPE
             OBJECTS   { rmxAlarmDescription , rmxActiveAlarmDateAndTime, rmxActiveAlarmIndex , rmxActiveAlarmListName , rmxActiveAlarmRmxStatus }
             STATUS  current
             DESCRIPTION
             "Alarm generated by an internal component"
             ::= { rmxTraps 5155 } 



rmxExternalAlertEmbAlarmClear  NOTIFICATION-TYPE
             OBJECTS   { rmxAlarmDescription , rmxActiveAlarmDateAndTime, rmxActiveAlarmIndex , rmxActiveAlarmListName , rmxActiveAlarmRmxStatus }
             STATUS  current
             DESCRIPTION
             "Alarm generated by an internal component"
             ::= { rmxTraps 15155 } 



rmxVersionInstallProgressAlarmFault  NOTIFICATION-TYPE
             OBJECTS   { rmxAlarmDescription , rmxActiveAlarmDateAndTime, rmxActiveAlarmIndex , rmxActiveAlarmListName , rmxActiveAlarmRmxStatus }
             STATUS  current
             DESCRIPTION
             "Software upgrade in component"
             ::= { rmxTraps 5156 } 



rmxVersionInstallProgressAlarmClear  NOTIFICATION-TYPE
             OBJECTS   { rmxAlarmDescription , rmxActiveAlarmDateAndTime, rmxActiveAlarmIndex , rmxActiveAlarmListName , rmxActiveAlarmRmxStatus }
             STATUS  current
             DESCRIPTION
             "Software upgrade in component"
             ::= { rmxTraps 15156 } 



rmxVersionIpmcInstallProgressAlarmFault  NOTIFICATION-TYPE
             OBJECTS   { rmxAlarmDescription , rmxActiveAlarmDateAndTime, rmxActiveAlarmIndex , rmxActiveAlarmListName , rmxActiveAlarmRmxStatus }
             STATUS  current
             DESCRIPTION
             "IPMC software upgrade in component"
             ::= { rmxTraps 5157 } 



rmxVersionIpmcInstallProgressAlarmClear  NOTIFICATION-TYPE
             OBJECTS   { rmxAlarmDescription , rmxActiveAlarmDateAndTime, rmxActiveAlarmIndex , rmxActiveAlarmListName , rmxActiveAlarmRmxStatus }
             STATUS  current
             DESCRIPTION
             "IPMC software upgrade in component"
             ::= { rmxTraps 15157 } 



rmxVoltageProblemAlarmFault  NOTIFICATION-TYPE
             OBJECTS   { rmxAlarmDescription , rmxActiveAlarmDateAndTime, rmxActiveAlarmIndex , rmxActiveAlarmListName , rmxActiveAlarmRmxStatus }
             STATUS  current
             DESCRIPTION
             "Voltage problem"
             ::= { rmxTraps 5200 } 



rmxVoltageProblemAlarmClear  NOTIFICATION-TYPE
             OBJECTS   { rmxAlarmDescription , rmxActiveAlarmDateAndTime, rmxActiveAlarmIndex , rmxActiveAlarmListName , rmxActiveAlarmRmxStatus }
             STATUS  current
             DESCRIPTION
             "Voltage problem"
             ::= { rmxTraps 15200 } 



rmxTemperatureMajorProblemAlarmFault  NOTIFICATION-TYPE
             OBJECTS   { rmxAlarmDescription , rmxActiveAlarmDateAndTime, rmxActiveAlarmIndex , rmxActiveAlarmListName , rmxActiveAlarmRmxStatus }
             STATUS  current
             DESCRIPTION
             "Temperature Level Major"
             ::= { rmxTraps 5201 } 



rmxTemperatureMajorProblemAlarmClear  NOTIFICATION-TYPE
             OBJECTS   { rmxAlarmDescription , rmxActiveAlarmDateAndTime, rmxActiveAlarmIndex , rmxActiveAlarmListName , rmxActiveAlarmRmxStatus }
             STATUS  current
             DESCRIPTION
             "Temperature Level Major"
             ::= { rmxTraps 15201 } 



rmxTemperatureCriticalProblemAlarmFault  NOTIFICATION-TYPE
             OBJECTS   { rmxAlarmDescription , rmxActiveAlarmDateAndTime, rmxActiveAlarmIndex , rmxActiveAlarmListName , rmxActiveAlarmRmxStatus }
             STATUS  current
             DESCRIPTION
             "Temperature Level Critical"
             ::= { rmxTraps 5202 } 



rmxTemperatureCriticalProblemAlarmClear  NOTIFICATION-TYPE
             OBJECTS   { rmxAlarmDescription , rmxActiveAlarmDateAndTime, rmxActiveAlarmIndex , rmxActiveAlarmListName , rmxActiveAlarmRmxStatus }
             STATUS  current
             DESCRIPTION
             "Temperature Level Critical"
             ::= { rmxTraps 15202 } 



rmxFailureProblemAlarmFault  NOTIFICATION-TYPE
             OBJECTS   { rmxAlarmDescription , rmxActiveAlarmDateAndTime, rmxActiveAlarmIndex , rmxActiveAlarmListName , rmxActiveAlarmRmxStatus }
             STATUS  current
             DESCRIPTION
             "Card failure"
             ::= { rmxTraps 5203 } 



rmxFailureProblemAlarmClear  NOTIFICATION-TYPE
             OBJECTS   { rmxAlarmDescription , rmxActiveAlarmDateAndTime, rmxActiveAlarmIndex , rmxActiveAlarmListName , rmxActiveAlarmRmxStatus }
             STATUS  current
             DESCRIPTION
             "Card failure"
             ::= { rmxTraps 15203 } 



rmxPowerOffProblemAlarmFault  NOTIFICATION-TYPE
             OBJECTS   { rmxAlarmDescription , rmxActiveAlarmDateAndTime, rmxActiveAlarmIndex , rmxActiveAlarmListName , rmxActiveAlarmRmxStatus }
             STATUS  current
             DESCRIPTION
             "Power off"
             ::= { rmxTraps 5204 } 



rmxPowerOffProblemAlarmClear  NOTIFICATION-TYPE
             OBJECTS   { rmxAlarmDescription , rmxActiveAlarmDateAndTime, rmxActiveAlarmIndex , rmxActiveAlarmListName , rmxActiveAlarmRmxStatus }
             STATUS  current
             DESCRIPTION
             "Power off"
             ::= { rmxTraps 15204 } 



rmxOtherProblemAlarmFault  NOTIFICATION-TYPE
             OBJECTS   { rmxAlarmDescription , rmxActiveAlarmDateAndTime, rmxActiveAlarmIndex , rmxActiveAlarmListName , rmxActiveAlarmRmxStatus }
             STATUS  current
             DESCRIPTION
             "Unspecified problem"
             ::= { rmxTraps 5205 } 



rmxOtherProblemAlarmClear  NOTIFICATION-TYPE
             OBJECTS   { rmxAlarmDescription , rmxActiveAlarmDateAndTime, rmxActiveAlarmIndex , rmxActiveAlarmListName , rmxActiveAlarmRmxStatus }
             STATUS  current
             DESCRIPTION
             "Unspecified problem"
             ::= { rmxTraps 15205 } 



rmxNoConnectionWithCardAlarmFault  NOTIFICATION-TYPE
             OBJECTS   { rmxAlarmDescription , rmxActiveAlarmDateAndTime, rmxActiveAlarmIndex , rmxActiveAlarmListName , rmxActiveAlarmRmxStatus }
             STATUS  current
             DESCRIPTION
             "Card not responding"
             ::= { rmxTraps 5206 } 



rmxNoConnectionWithCardAlarmClear  NOTIFICATION-TYPE
             OBJECTS   { rmxAlarmDescription , rmxActiveAlarmDateAndTime, rmxActiveAlarmIndex , rmxActiveAlarmListName , rmxActiveAlarmRmxStatus }
             STATUS  current
             DESCRIPTION
             "Card not responding"
             ::= { rmxTraps 15206 } 



rmxUnitNotRespondingAlarmFault  NOTIFICATION-TYPE
             OBJECTS   { rmxAlarmDescription , rmxActiveAlarmDateAndTime, rmxActiveAlarmIndex , rmxActiveAlarmListName , rmxActiveAlarmRmxStatus }
             STATUS  current
             DESCRIPTION
             "Unit not responding"
             ::= { rmxTraps 5207 } 



rmxUnitNotRespondingAlarmClear  NOTIFICATION-TYPE
             OBJECTS   { rmxAlarmDescription , rmxActiveAlarmDateAndTime, rmxActiveAlarmIndex , rmxActiveAlarmListName , rmxActiveAlarmRmxStatus }
             STATUS  current
             DESCRIPTION
             "Unit not responding"
             ::= { rmxTraps 15207 } 



rmxMediaIpConfigurationFailureAlarmFault  NOTIFICATION-TYPE
             OBJECTS   { rmxAlarmDescription , rmxActiveAlarmDateAndTime, rmxActiveAlarmIndex , rmxActiveAlarmListName , rmxActiveAlarmRmxStatus }
             STATUS  current
             DESCRIPTION
             "Failed to configure the Media card IP address"
             ::= { rmxTraps 5208 } 



rmxMediaIpConfigurationFailureAlarmClear  NOTIFICATION-TYPE
             OBJECTS   { rmxAlarmDescription , rmxActiveAlarmDateAndTime, rmxActiveAlarmIndex , rmxActiveAlarmListName , rmxActiveAlarmRmxStatus }
             STATUS  current
             DESCRIPTION
             "Failed to configure the Media card IP address"
             ::= { rmxTraps 15208 } 



rmxCardFolderMountingFailedAlarmFault  NOTIFICATION-TYPE
             OBJECTS   { rmxAlarmDescription , rmxActiveAlarmDateAndTime, rmxActiveAlarmIndex , rmxActiveAlarmListName , rmxActiveAlarmRmxStatus }
             STATUS  current
             DESCRIPTION
             "Failed to mount Card folder"
             ::= { rmxTraps 5209 } 



rmxCardFolderMountingFailedAlarmClear  NOTIFICATION-TYPE
             OBJECTS   { rmxAlarmDescription , rmxActiveAlarmDateAndTime, rmxActiveAlarmIndex , rmxActiveAlarmListName , rmxActiveAlarmRmxStatus }
             STATUS  current
             DESCRIPTION
             "Failed to mount Card folder"
             ::= { rmxTraps 15209 } 



rmxCardStartupFailureAlarmFault  NOTIFICATION-TYPE
             OBJECTS   { rmxAlarmDescription , rmxActiveAlarmDateAndTime, rmxActiveAlarmIndex , rmxActiveAlarmListName , rmxActiveAlarmRmxStatus }
             STATUS  current
             DESCRIPTION
             "Could not complete MPM Card startup procedure"
             ::= { rmxTraps 5211 } 



rmxCardStartupFailureAlarmClear  NOTIFICATION-TYPE
             OBJECTS   { rmxAlarmDescription , rmxActiveAlarmDateAndTime, rmxActiveAlarmIndex , rmxActiveAlarmListName , rmxActiveAlarmRmxStatus }
             STATUS  current
             DESCRIPTION
             "Could not complete MPM Card startup procedure"
             ::= { rmxTraps 15211 } 



rmxRtmIsdnStartupFailureAlarmFault  NOTIFICATION-TYPE
             OBJECTS   { rmxAlarmDescription , rmxActiveAlarmDateAndTime, rmxActiveAlarmIndex , rmxActiveAlarmListName , rmxActiveAlarmRmxStatus }
             STATUS  current
             DESCRIPTION
             "Could not complete RTM ISDN Card startup procedure"
             ::= { rmxTraps 5212 } 



rmxRtmIsdnStartupFailureAlarmClear  NOTIFICATION-TYPE
             OBJECTS   { rmxAlarmDescription , rmxActiveAlarmDateAndTime, rmxActiveAlarmIndex , rmxActiveAlarmListName , rmxActiveAlarmRmxStatus }
             STATUS  current
             DESCRIPTION
             "Could not complete RTM ISDN Card startup procedure"
             ::= { rmxTraps 15212 } 



rmxRtmIsdnStartupProblemAlarmFault  NOTIFICATION-TYPE
             OBJECTS   { rmxAlarmDescription , rmxActiveAlarmDateAndTime, rmxActiveAlarmIndex , rmxActiveAlarmListName , rmxActiveAlarmRmxStatus }
             STATUS  current
             DESCRIPTION
             "RTM ISDN card startup procedure error"
             ::= { rmxTraps 5213 } 



rmxRtmIsdnStartupProblemAlarmClear  NOTIFICATION-TYPE
             OBJECTS   { rmxAlarmDescription , rmxActiveAlarmDateAndTime, rmxActiveAlarmIndex , rmxActiveAlarmListName , rmxActiveAlarmRmxStatus }
             STATUS  current
             DESCRIPTION
             "RTM ISDN card startup procedure error"
             ::= { rmxTraps 15213 } 



rmxNoConnectionWithRtmIsdnAlarmFault  NOTIFICATION-TYPE
             OBJECTS   { rmxAlarmDescription , rmxActiveAlarmDateAndTime, rmxActiveAlarmIndex , rmxActiveAlarmListName , rmxActiveAlarmRmxStatus }
             STATUS  current
             DESCRIPTION
             "No response from RTM ISDN card"
             ::= { rmxTraps 5214 } 



rmxNoConnectionWithRtmIsdnAlarmClear  NOTIFICATION-TYPE
             OBJECTS   { rmxAlarmDescription , rmxActiveAlarmDateAndTime, rmxActiveAlarmIndex , rmxActiveAlarmListName , rmxActiveAlarmRmxStatus }
             STATUS  current
             DESCRIPTION
             "No response from RTM ISDN card"
             ::= { rmxTraps 15214 } 



rmxRedAlarmAlarmFault  NOTIFICATION-TYPE
             OBJECTS   { rmxAlarmDescription , rmxActiveAlarmDateAndTime, rmxActiveAlarmIndex , rmxActiveAlarmListName , rmxActiveAlarmRmxStatus }
             STATUS  current
             DESCRIPTION
             "Red Alarm"
             ::= { rmxTraps 5215 } 



rmxRedAlarmAlarmClear  NOTIFICATION-TYPE
             OBJECTS   { rmxAlarmDescription , rmxActiveAlarmDateAndTime, rmxActiveAlarmIndex , rmxActiveAlarmListName , rmxActiveAlarmRmxStatus }
             STATUS  current
             DESCRIPTION
             "Red Alarm"
             ::= { rmxTraps 15215 } 



rmxYellowAlarmAlarmFault  NOTIFICATION-TYPE
             OBJECTS   { rmxAlarmDescription , rmxActiveAlarmDateAndTime, rmxActiveAlarmIndex , rmxActiveAlarmListName , rmxActiveAlarmRmxStatus }
             STATUS  current
             DESCRIPTION
             "Yellow Alarm"
             ::= { rmxTraps 5216 } 



rmxYellowAlarmAlarmClear  NOTIFICATION-TYPE
             OBJECTS   { rmxAlarmDescription , rmxActiveAlarmDateAndTime, rmxActiveAlarmIndex , rmxActiveAlarmListName , rmxActiveAlarmRmxStatus }
             STATUS  current
             DESCRIPTION
             "Yellow Alarm"
             ::= { rmxTraps 15216 } 



rmxDChannelNotEstablishedAlarmFault  NOTIFICATION-TYPE
             OBJECTS   { rmxAlarmDescription , rmxActiveAlarmDateAndTime, rmxActiveAlarmIndex , rmxActiveAlarmListName , rmxActiveAlarmRmxStatus }
             STATUS  current
             DESCRIPTION
             "D channel cannot be established"
             ::= { rmxTraps 5217 } 



rmxDChannelNotEstablishedAlarmClear  NOTIFICATION-TYPE
             OBJECTS   { rmxAlarmDescription , rmxActiveAlarmDateAndTime, rmxActiveAlarmIndex , rmxActiveAlarmListName , rmxActiveAlarmRmxStatus }
             STATUS  current
             DESCRIPTION
             "D channel cannot be established"
             ::= { rmxTraps 15217 } 



rmxCardsConfigEventAlarmFault  NOTIFICATION-TYPE
             OBJECTS   { rmxAlarmDescription , rmxActiveAlarmDateAndTime, rmxActiveAlarmIndex , rmxActiveAlarmListName , rmxActiveAlarmRmxStatus }
             STATUS  current
             DESCRIPTION
             "Card configuration event"
             ::= { rmxTraps 5218 } 



rmxCardsConfigEventAlarmClear  NOTIFICATION-TYPE
             OBJECTS   { rmxAlarmDescription , rmxActiveAlarmDateAndTime, rmxActiveAlarmIndex , rmxActiveAlarmListName , rmxActiveAlarmRmxStatus }
             STATUS  current
             DESCRIPTION
             "Card configuration event"
             ::= { rmxTraps 15218 } 



rmxCardsWrongFileModeAlarmFault  NOTIFICATION-TYPE
             OBJECTS   { rmxAlarmDescription , rmxActiveAlarmDateAndTime, rmxActiveAlarmIndex , rmxActiveAlarmListName , rmxActiveAlarmRmxStatus }
             STATUS  current
             DESCRIPTION
             "Cards wrong file's mode"
             ::= { rmxTraps 5219 } 



rmxCardsWrongFileModeAlarmClear  NOTIFICATION-TYPE
             OBJECTS   { rmxAlarmDescription , rmxActiveAlarmDateAndTime, rmxActiveAlarmIndex , rmxActiveAlarmListName , rmxActiveAlarmRmxStatus }
             STATUS  current
             DESCRIPTION
             "Cards wrong file's mode"
             ::= { rmxTraps 15219 } 



rmxCardsFlashAccessProblemAlarmFault  NOTIFICATION-TYPE
             OBJECTS   { rmxAlarmDescription , rmxActiveAlarmDateAndTime, rmxActiveAlarmIndex , rmxActiveAlarmListName , rmxActiveAlarmRmxStatus }
             STATUS  current
             DESCRIPTION
             "Card failed to switch to Enhanced Security Mode"
             ::= { rmxTraps 5220 } 



rmxCardsFlashAccessProblemAlarmClear  NOTIFICATION-TYPE
             OBJECTS   { rmxAlarmDescription , rmxActiveAlarmDateAndTime, rmxActiveAlarmIndex , rmxActiveAlarmListName , rmxActiveAlarmRmxStatus }
             STATUS  current
             DESCRIPTION
             "Card failed to switch to Enhanced Security Mode"
             ::= { rmxTraps 15220 } 



rmxRtmLanOrIsdnMissingAlarmFault  NOTIFICATION-TYPE
             OBJECTS   { rmxAlarmDescription , rmxActiveAlarmDateAndTime, rmxActiveAlarmIndex , rmxActiveAlarmListName , rmxActiveAlarmRmxStatus }
             STATUS  current
             DESCRIPTION
             "No RTM-LAN or RTM-ISDN installed. One of these cards must be installed in the RMX 4000"
             ::= { rmxTraps 5221 } 



rmxRtmLanOrIsdnMissingAlarmClear  NOTIFICATION-TYPE
             OBJECTS   { rmxAlarmDescription , rmxActiveAlarmDateAndTime, rmxActiveAlarmIndex , rmxActiveAlarmListName , rmxActiveAlarmRmxStatus }
             STATUS  current
             DESCRIPTION
             "No RTM-LAN or RTM-ISDN installed. One of these cards must be installed in the RMX 4000"
             ::= { rmxTraps 15221 } 



rmxNoLanConnectionAlarmFault  NOTIFICATION-TYPE
             OBJECTS   { rmxAlarmDescription , rmxActiveAlarmDateAndTime, rmxActiveAlarmIndex , rmxActiveAlarmListName , rmxActiveAlarmRmxStatus }
             STATUS  current
             DESCRIPTION
             "No LAN connection"
             ::= { rmxTraps 5222 } 



rmxNoLanConnectionAlarmClear  NOTIFICATION-TYPE
             OBJECTS   { rmxAlarmDescription , rmxActiveAlarmDateAndTime, rmxActiveAlarmIndex , rmxActiveAlarmListName , rmxActiveAlarmRmxStatus }
             STATUS  current
             DESCRIPTION
             "No LAN connection"
             ::= { rmxTraps 15222 } 



rmxCanNotEstablishConnectionWithSipRegistrarAlarmFault  NOTIFICATION-TYPE
             OBJECTS   { rmxAlarmDescription , rmxActiveAlarmDateAndTime, rmxActiveAlarmIndex , rmxActiveAlarmListName , rmxActiveAlarmRmxStatus }
             STATUS  current
             DESCRIPTION
             "Failed to connect to SIP registrar"
             ::= { rmxTraps 5300 } 



rmxCanNotEstablishConnectionWithSipRegistrarAlarmClear  NOTIFICATION-TYPE
             OBJECTS   { rmxAlarmDescription , rmxActiveAlarmDateAndTime, rmxActiveAlarmIndex , rmxActiveAlarmListName , rmxActiveAlarmRmxStatus }
             STATUS  current
             DESCRIPTION
             "Failed to connect to SIP registrar"
             ::= { rmxTraps 15300 } 



rmxSipRegistrationLimitReachedAlarmFault  NOTIFICATION-TYPE
             OBJECTS   { rmxAlarmDescription , rmxActiveAlarmDateAndTime, rmxActiveAlarmIndex , rmxActiveAlarmListName , rmxActiveAlarmRmxStatus }
             STATUS  current
             DESCRIPTION
             "SIP registrations limit reached"
             ::= { rmxTraps 5301 } 



rmxSipRegistrationLimitReachedAlarmClear  NOTIFICATION-TYPE
             OBJECTS   { rmxAlarmDescription , rmxActiveAlarmDateAndTime, rmxActiveAlarmIndex , rmxActiveAlarmListName , rmxActiveAlarmRmxStatus }
             STATUS  current
             DESCRIPTION
             "SIP registrations limit reached"
             ::= { rmxTraps 15301 } 



rmxFailedToAccessDnsServerAlarmFault  NOTIFICATION-TYPE
             OBJECTS   { rmxAlarmDescription , rmxActiveAlarmDateAndTime, rmxActiveAlarmIndex , rmxActiveAlarmListName , rmxActiveAlarmRmxStatus }
             STATUS  current
             DESCRIPTION
             "Failed to access DNS server"
             ::= { rmxTraps 5350 } 



rmxFailedToAccessDnsServerAlarmClear  NOTIFICATION-TYPE
             OBJECTS   { rmxAlarmDescription , rmxActiveAlarmDateAndTime, rmxActiveAlarmIndex , rmxActiveAlarmListName , rmxActiveAlarmRmxStatus }
             STATUS  current
             DESCRIPTION
             "Failed to access DNS server"
             ::= { rmxTraps 15350 } 



rmxNoIndDnsSuccessAlarmFault  NOTIFICATION-TYPE
             OBJECTS   { rmxAlarmDescription , rmxActiveAlarmDateAndTime, rmxActiveAlarmIndex , rmxActiveAlarmListName , rmxActiveAlarmRmxStatus }
             STATUS  current
             DESCRIPTION
             "DNS configuration error"
             ::= { rmxTraps 5351 } 



rmxNoIndDnsSuccessAlarmClear  NOTIFICATION-TYPE
             OBJECTS   { rmxAlarmDescription , rmxActiveAlarmDateAndTime, rmxActiveAlarmIndex , rmxActiveAlarmListName , rmxActiveAlarmRmxStatus }
             STATUS  current
             DESCRIPTION
             "DNS configuration error"
             ::= { rmxTraps 15351 } 



rmxFailedToInitFileSystemAlarmFault  NOTIFICATION-TYPE
             OBJECTS   { rmxAlarmDescription , rmxActiveAlarmDateAndTime, rmxActiveAlarmIndex , rmxActiveAlarmListName , rmxActiveAlarmRmxStatus }
             STATUS  current
             DESCRIPTION
             "Failed to initialize the file system"
             ::= { rmxTraps 5400 } 



rmxFailedToInitFileSystemAlarmClear  NOTIFICATION-TYPE
             OBJECTS   { rmxAlarmDescription , rmxActiveAlarmDateAndTime, rmxActiveAlarmIndex , rmxActiveAlarmListName , rmxActiveAlarmRmxStatus }
             STATUS  current
             DESCRIPTION
             "Failed to initialize the file system"
             ::= { rmxTraps 15400 } 



rmxBadFileSystemAlarmFault  NOTIFICATION-TYPE
             OBJECTS   { rmxAlarmDescription , rmxActiveAlarmDateAndTime, rmxActiveAlarmIndex , rmxActiveAlarmListName , rmxActiveAlarmRmxStatus }
             STATUS  current
             DESCRIPTION
             "The Log file system is disabled"
             ::= { rmxTraps 5401 } 



rmxBadFileSystemAlarmClear  NOTIFICATION-TYPE
             OBJECTS   { rmxAlarmDescription , rmxActiveAlarmDateAndTime, rmxActiveAlarmIndex , rmxActiveAlarmListName , rmxActiveAlarmRmxStatus }
             STATUS  current
             DESCRIPTION
             "The Log file system is disabled"
             ::= { rmxTraps 15401 } 



rmxBadHardDiskAlarmFault  NOTIFICATION-TYPE
             OBJECTS   { rmxAlarmDescription , rmxActiveAlarmDateAndTime, rmxActiveAlarmIndex , rmxActiveAlarmListName , rmxActiveAlarmRmxStatus }
             STATUS  current
             DESCRIPTION
             "Hard disk error"
             ::= { rmxTraps 5402 } 



rmxBadHardDiskAlarmClear  NOTIFICATION-TYPE
             OBJECTS   { rmxAlarmDescription , rmxActiveAlarmDateAndTime, rmxActiveAlarmIndex , rmxActiveAlarmListName , rmxActiveAlarmRmxStatus }
             STATUS  current
             DESCRIPTION
             "Hard disk error"
             ::= { rmxTraps 15402 } 



rmxBackupOfLogFilesIsRequiredAlarmFault  NOTIFICATION-TYPE
             OBJECTS   { rmxAlarmDescription , rmxActiveAlarmDateAndTime, rmxActiveAlarmIndex , rmxActiveAlarmListName , rmxActiveAlarmRmxStatus }
             STATUS  current
             DESCRIPTION
             "Backup of log files is required"
             ::= { rmxTraps 5403 } 



rmxBackupOfLogFilesIsRequiredAlarmClear  NOTIFICATION-TYPE
             OBJECTS   { rmxAlarmDescription , rmxActiveAlarmDateAndTime, rmxActiveAlarmIndex , rmxActiveAlarmListName , rmxActiveAlarmRmxStatus }
             STATUS  current
             DESCRIPTION
             "Backup of log files is required"
             ::= { rmxTraps 15403 } 



rmxBackupOfAuditFilesIsRequiredAlarmFault  NOTIFICATION-TYPE
             OBJECTS   { rmxAlarmDescription , rmxActiveAlarmDateAndTime, rmxActiveAlarmIndex , rmxActiveAlarmListName , rmxActiveAlarmRmxStatus }
             STATUS  current
             DESCRIPTION
             "Backup of audit files is required"
             ::= { rmxTraps 5430 } 



rmxBackupOfAuditFilesIsRequiredAlarmClear  NOTIFICATION-TYPE
             OBJECTS   { rmxAlarmDescription , rmxActiveAlarmDateAndTime, rmxActiveAlarmIndex , rmxActiveAlarmListName , rmxActiveAlarmRmxStatus }
             STATUS  current
             DESCRIPTION
             "Backup of audit files is required"
             ::= { rmxTraps 15430 } 



rmxFailedToFillActionRedirectionAlarmFault  NOTIFICATION-TYPE
             OBJECTS   { rmxAlarmDescription , rmxActiveAlarmDateAndTime, rmxActiveAlarmIndex , rmxActiveAlarmListName , rmxActiveAlarmRmxStatus }
             STATUS  current
             DESCRIPTION
             "Action redirection failure"
             ::= { rmxTraps 5450 } 



rmxFailedToFillActionRedirectionAlarmClear  NOTIFICATION-TYPE
             OBJECTS   { rmxAlarmDescription , rmxActiveAlarmDateAndTime, rmxActiveAlarmIndex , rmxActiveAlarmListName , rmxActiveAlarmRmxStatus }
             STATUS  current
             DESCRIPTION
             "Action redirection failure"
             ::= { rmxTraps 15450 } 



rmxFailedConfigUserListInLinuxAlarmFault  NOTIFICATION-TYPE
             OBJECTS   { rmxAlarmDescription , rmxActiveAlarmDateAndTime, rmxActiveAlarmIndex , rmxActiveAlarmListName , rmxActiveAlarmRmxStatus }
             STATUS  current
             DESCRIPTION
             "Failed to configure the Users list in Linux"
             ::= { rmxTraps 5500 } 



rmxFailedConfigUserListInLinuxAlarmClear  NOTIFICATION-TYPE
             OBJECTS   { rmxAlarmDescription , rmxActiveAlarmDateAndTime, rmxActiveAlarmIndex , rmxActiveAlarmListName , rmxActiveAlarmRmxStatus }
             STATUS  current
             DESCRIPTION
             "Failed to configure the Users list in Linux"
             ::= { rmxTraps 15500 } 



rmxInsufficientResourcesAlarmFault  NOTIFICATION-TYPE
             OBJECTS   { rmxAlarmDescription , rmxActiveAlarmDateAndTime, rmxActiveAlarmIndex , rmxActiveAlarmListName , rmxActiveAlarmRmxStatus }
             STATUS  current
             DESCRIPTION
             "Insufficient resources"
             ::= { rmxTraps 5550 } 



rmxInsufficientResourcesAlarmClear  NOTIFICATION-TYPE
             OBJECTS   { rmxAlarmDescription , rmxActiveAlarmDateAndTime, rmxActiveAlarmIndex , rmxActiveAlarmListName , rmxActiveAlarmRmxStatus }
             STATUS  current
             DESCRIPTION
             "Insufficient resources"
             ::= { rmxTraps 15550 } 



rmxPortConfigurationChangedAlarmFault  NOTIFICATION-TYPE
             OBJECTS   { rmxAlarmDescription , rmxActiveAlarmDateAndTime, rmxActiveAlarmIndex , rmxActiveAlarmListName , rmxActiveAlarmRmxStatus }
             STATUS  current
             DESCRIPTION
             "Port configuration was modified"
             ::= { rmxTraps 5551 } 



rmxPortConfigurationChangedAlarmClear  NOTIFICATION-TYPE
             OBJECTS   { rmxAlarmDescription , rmxActiveAlarmDateAndTime, rmxActiveAlarmIndex , rmxActiveAlarmListName , rmxActiveAlarmRmxStatus }
             STATUS  current
             DESCRIPTION
             "Port configuration was modified"
             ::= { rmxTraps 15551 } 



rmxNoUtilizableUnitForAudioControllerAlarmFault  NOTIFICATION-TYPE
             OBJECTS   { rmxAlarmDescription , rmxActiveAlarmDateAndTime, rmxActiveAlarmIndex , rmxActiveAlarmListName , rmxActiveAlarmRmxStatus }
             STATUS  current
             DESCRIPTION
             "No usable unit for audio controller"
             ::= { rmxTraps 5552 } 



rmxNoUtilizableUnitForAudioControllerAlarmClear  NOTIFICATION-TYPE
             OBJECTS   { rmxAlarmDescription , rmxActiveAlarmDateAndTime, rmxActiveAlarmIndex , rmxActiveAlarmListName , rmxActiveAlarmRmxStatus }
             STATUS  current
             DESCRIPTION
             "No usable unit for audio controller"
             ::= { rmxTraps 15552 } 



rmxAllocationModeChangedAlarmFault  NOTIFICATION-TYPE
             OBJECTS   { rmxAlarmDescription , rmxActiveAlarmDateAndTime, rmxActiveAlarmIndex , rmxActiveAlarmListName , rmxActiveAlarmRmxStatus }
             STATUS  current
             DESCRIPTION
             "Allocation mode was modified"
             ::= { rmxTraps 5553 } 



rmxAllocationModeChangedAlarmClear  NOTIFICATION-TYPE
             OBJECTS   { rmxAlarmDescription , rmxActiveAlarmDateAndTime, rmxActiveAlarmIndex , rmxActiveAlarmListName , rmxActiveAlarmRmxStatus }
             STATUS  current
             DESCRIPTION
             "Allocation mode was modified"
             ::= { rmxTraps 15553 } 



rmxProcessTerminatedAlarmFault  NOTIFICATION-TYPE
             OBJECTS   { rmxAlarmDescription , rmxActiveAlarmDateAndTime, rmxActiveAlarmIndex , rmxActiveAlarmListName , rmxActiveAlarmRmxStatus }
             STATUS  current
             DESCRIPTION
             "Process terminated"
             ::= { rmxTraps 5601 } 



rmxProcessTerminatedAlarmClear  NOTIFICATION-TYPE
             OBJECTS   { rmxAlarmDescription , rmxActiveAlarmDateAndTime, rmxActiveAlarmIndex , rmxActiveAlarmListName , rmxActiveAlarmRmxStatus }
             STATUS  current
             DESCRIPTION
             "Process terminated"
             ::= { rmxTraps 15601 } 



rmxResetMcuByTerminalAlarmFault  NOTIFICATION-TYPE
             OBJECTS   { rmxAlarmDescription , rmxActiveAlarmDateAndTime, rmxActiveAlarmIndex , rmxActiveAlarmListName , rmxActiveAlarmRmxStatus }
             STATUS  current
             DESCRIPTION
             "Terminal initiated MCU reset"
             ::= { rmxTraps 5602 } 



rmxResetMcuByTerminalAlarmClear  NOTIFICATION-TYPE
             OBJECTS   { rmxAlarmDescription , rmxActiveAlarmDateAndTime, rmxActiveAlarmIndex , rmxActiveAlarmListName , rmxActiveAlarmRmxStatus }
             STATUS  current
             DESCRIPTION
             "Terminal initiated MCU reset"
             ::= { rmxTraps 15602 } 



rmxResetMcuByOperatorAlarmFault  NOTIFICATION-TYPE
             OBJECTS   { rmxAlarmDescription , rmxActiveAlarmDateAndTime, rmxActiveAlarmIndex , rmxActiveAlarmListName , rmxActiveAlarmRmxStatus }
             STATUS  current
             DESCRIPTION
             "User initiated MCU reset"
             ::= { rmxTraps 5603 } 



rmxResetMcuByOperatorAlarmClear  NOTIFICATION-TYPE
             OBJECTS   { rmxAlarmDescription , rmxActiveAlarmDateAndTime, rmxActiveAlarmIndex , rmxActiveAlarmListName , rmxActiveAlarmRmxStatus }
             STATUS  current
             DESCRIPTION
             "User initiated MCU reset"
             ::= { rmxTraps 15603 } 



rmxResetMcuInternalAlarmFault  NOTIFICATION-TYPE
             OBJECTS   { rmxAlarmDescription , rmxActiveAlarmDateAndTime, rmxActiveAlarmIndex , rmxActiveAlarmListName , rmxActiveAlarmRmxStatus }
             STATUS  current
             DESCRIPTION
             "Internal MCU reset"
             ::= { rmxTraps 5604 } 



rmxResetMcuInternalAlarmClear  NOTIFICATION-TYPE
             OBJECTS   { rmxAlarmDescription , rmxActiveAlarmDateAndTime, rmxActiveAlarmIndex , rmxActiveAlarmListName , rmxActiveAlarmRmxStatus }
             STATUS  current
             DESCRIPTION
             "Internal MCU reset"
             ::= { rmxTraps 15604 } 



rmxResetMcuAlarmFault  NOTIFICATION-TYPE
             OBJECTS   { rmxAlarmDescription , rmxActiveAlarmDateAndTime, rmxActiveAlarmIndex , rmxActiveAlarmListName , rmxActiveAlarmRmxStatus }
             STATUS  current
             DESCRIPTION
             "MCU reset"
             ::= { rmxTraps 5605 } 



rmxResetMcuAlarmClear  NOTIFICATION-TYPE
             OBJECTS   { rmxAlarmDescription , rmxActiveAlarmDateAndTime, rmxActiveAlarmIndex , rmxActiveAlarmListName , rmxActiveAlarmRmxStatus }
             STATUS  current
             DESCRIPTION
             "MCU reset"
             ::= { rmxTraps 15605 } 



rmxResetMcuDiagnosticsAlarmFault  NOTIFICATION-TYPE
             OBJECTS   { rmxAlarmDescription , rmxActiveAlarmDateAndTime, rmxActiveAlarmIndex , rmxActiveAlarmListName , rmxActiveAlarmRmxStatus }
             STATUS  current
             DESCRIPTION
             "MCU Reset to enable Diagnostics mode"
             ::= { rmxTraps 5606 } 



rmxResetMcuDiagnosticsAlarmClear  NOTIFICATION-TYPE
             OBJECTS   { rmxAlarmDescription , rmxActiveAlarmDateAndTime, rmxActiveAlarmIndex , rmxActiveAlarmListName , rmxActiveAlarmRmxStatus }
             STATUS  current
             DESCRIPTION
             "MCU Reset to enable Diagnostics mode"
             ::= { rmxTraps 15606 } 



rmxProcessStartupFailedAlarmFault  NOTIFICATION-TYPE
             OBJECTS   { rmxAlarmDescription , rmxActiveAlarmDateAndTime, rmxActiveAlarmIndex , rmxActiveAlarmListName , rmxActiveAlarmRmxStatus }
             STATUS  current
             DESCRIPTION
             "Startup process failure"
             ::= { rmxTraps 5607 } 



rmxProcessStartupFailedAlarmClear  NOTIFICATION-TYPE
             OBJECTS   { rmxAlarmDescription , rmxActiveAlarmDateAndTime, rmxActiveAlarmIndex , rmxActiveAlarmListName , rmxActiveAlarmRmxStatus }
             STATUS  current
             DESCRIPTION
             "Startup process failure"
             ::= { rmxTraps 15607 } 



rmxSystemInSafeModeAlarmFault  NOTIFICATION-TYPE
             OBJECTS   { rmxAlarmDescription , rmxActiveAlarmDateAndTime, rmxActiveAlarmIndex , rmxActiveAlarmListName , rmxActiveAlarmRmxStatus }
             STATUS  current
             DESCRIPTION
             "Automatic reset is unavailable in Safe Mode"
             ::= { rmxTraps 5608 } 



rmxSystemInSafeModeAlarmClear  NOTIFICATION-TYPE
             OBJECTS   { rmxAlarmDescription , rmxActiveAlarmDateAndTime, rmxActiveAlarmIndex , rmxActiveAlarmListName , rmxActiveAlarmRmxStatus }
             STATUS  current
             DESCRIPTION
             "Automatic reset is unavailable in Safe Mode"
             ::= { rmxTraps 15608 } 



rmxGuiSystemConfigIsIllegalAlarmFault  NOTIFICATION-TYPE
             OBJECTS   { rmxAlarmDescription , rmxActiveAlarmDateAndTime, rmxActiveAlarmIndex , rmxActiveAlarmListName , rmxActiveAlarmRmxStatus }
             STATUS  current
             DESCRIPTION
             "GUI System configuration file is invalid xml file"
             ::= { rmxTraps 5609 } 



rmxGuiSystemConfigIsIllegalAlarmClear  NOTIFICATION-TYPE
             OBJECTS   { rmxAlarmDescription , rmxActiveAlarmDateAndTime, rmxActiveAlarmIndex , rmxActiveAlarmListName , rmxActiveAlarmRmxStatus }
             STATUS  current
             DESCRIPTION
             "GUI System configuration file is invalid xml file"
             ::= { rmxTraps 15609 } 



rmxFileSystemFailedToScanAlarmFault  NOTIFICATION-TYPE
             OBJECTS   { rmxAlarmDescription , rmxActiveAlarmDateAndTime, rmxActiveAlarmIndex , rmxActiveAlarmListName , rmxActiveAlarmRmxStatus }
             STATUS  current
             DESCRIPTION
             "File system scan failure"
             ::= { rmxTraps 5650 } 



rmxFileSystemFailedToScanAlarmClear  NOTIFICATION-TYPE
             OBJECTS   { rmxAlarmDescription , rmxActiveAlarmDateAndTime, rmxActiveAlarmIndex , rmxActiveAlarmListName , rmxActiveAlarmRmxStatus }
             STATUS  current
             DESCRIPTION
             "File system scan failure"
             ::= { rmxTraps 15650 } 



rmxFileSystemOverflowAlarmFault  NOTIFICATION-TYPE
             OBJECTS   { rmxAlarmDescription , rmxActiveAlarmDateAndTime, rmxActiveAlarmIndex , rmxActiveAlarmListName , rmxActiveAlarmRmxStatus }
             STATUS  current
             DESCRIPTION
             "File system space shortage"
             ::= { rmxTraps 5651 } 



rmxFileSystemOverflowAlarmClear  NOTIFICATION-TYPE
             OBJECTS   { rmxAlarmDescription , rmxActiveAlarmDateAndTime, rmxActiveAlarmIndex , rmxActiveAlarmListName , rmxActiveAlarmRmxStatus }
             STATUS  current
             DESCRIPTION
             "File system space shortage"
             ::= { rmxTraps 15651 } 



rmxHardDiskFailureAlarmFault  NOTIFICATION-TYPE
             OBJECTS   { rmxAlarmDescription , rmxActiveAlarmDateAndTime, rmxActiveAlarmIndex , rmxActiveAlarmListName , rmxActiveAlarmRmxStatus }
             STATUS  current
             DESCRIPTION
             "Hard disk error"
             ::= { rmxTraps 5652 } 



rmxHardDiskFailureAlarmClear  NOTIFICATION-TYPE
             OBJECTS   { rmxAlarmDescription , rmxActiveAlarmDateAndTime, rmxActiveAlarmIndex , rmxActiveAlarmListName , rmxActiveAlarmRmxStatus }
             STATUS  current
             DESCRIPTION
             "Hard disk error"
             ::= { rmxTraps 15652 } 



rmxCpuIpcmSoftwareIsNotUpdatedAlarmFault  NOTIFICATION-TYPE
             OBJECTS   { rmxAlarmDescription , rmxActiveAlarmDateAndTime, rmxActiveAlarmIndex , rmxActiveAlarmListName , rmxActiveAlarmRmxStatus }
             STATUS  current
             DESCRIPTION
             "CPU IPMC software was not updated."
             ::= { rmxTraps 5690 } 



rmxCpuIpcmSoftwareIsNotUpdatedAlarmClear  NOTIFICATION-TYPE
             OBJECTS   { rmxAlarmDescription , rmxActiveAlarmDateAndTime, rmxActiveAlarmIndex , rmxActiveAlarmListName , rmxActiveAlarmRmxStatus }
             STATUS  current
             DESCRIPTION
             "CPU IPMC software was not updated."
             ::= { rmxTraps 15690 } 



rmxNewVersionInstalledAlarmFault  NOTIFICATION-TYPE
             OBJECTS   { rmxAlarmDescription , rmxActiveAlarmDateAndTime, rmxActiveAlarmIndex , rmxActiveAlarmListName , rmxActiveAlarmRmxStatus }
             STATUS  current
             DESCRIPTION
             "A new version was installed. Reset the system."
             ::= { rmxTraps 5700 } 



rmxNewVersionInstalledAlarmClear  NOTIFICATION-TYPE
             OBJECTS   { rmxAlarmDescription , rmxActiveAlarmDateAndTime, rmxActiveAlarmIndex , rmxActiveAlarmListName , rmxActiveAlarmRmxStatus }
             STATUS  current
             DESCRIPTION
             "A new version was installed. Reset the system."
             ::= { rmxTraps 15700 } 



rmxNewActivationKeyLoadedAlarmFault  NOTIFICATION-TYPE
             OBJECTS   { rmxAlarmDescription , rmxActiveAlarmDateAndTime, rmxActiveAlarmIndex , rmxActiveAlarmListName , rmxActiveAlarmRmxStatus }
             STATUS  current
             DESCRIPTION
             "A new activation key was loaded. Reset the system."
             ::= { rmxTraps 5701 } 



rmxNewActivationKeyLoadedAlarmClear  NOTIFICATION-TYPE
             OBJECTS   { rmxAlarmDescription , rmxActiveAlarmDateAndTime, rmxActiveAlarmIndex , rmxActiveAlarmListName , rmxActiveAlarmRmxStatus }
             STATUS  current
             DESCRIPTION
             "A new activation key was loaded. Reset the system."
             ::= { rmxTraps 15701 } 



rmxInsufficientUdpPortsAlarmFault  NOTIFICATION-TYPE
             OBJECTS   { rmxAlarmDescription , rmxActiveAlarmDateAndTime, rmxActiveAlarmIndex , rmxActiveAlarmListName , rmxActiveAlarmRmxStatus }
             STATUS  current
             DESCRIPTION
             "Insufficient UDP Ports"
             ::= { rmxTraps 5751 } 



rmxInsufficientUdpPortsAlarmClear  NOTIFICATION-TYPE
             OBJECTS   { rmxAlarmDescription , rmxActiveAlarmDateAndTime, rmxActiveAlarmIndex , rmxActiveAlarmListName , rmxActiveAlarmRmxStatus }
             STATUS  current
             DESCRIPTION
             "Insufficient UDP Ports"
             ::= { rmxTraps 15751 } 



rmxUsersListCorruptedAlarmFault  NOTIFICATION-TYPE
             OBJECTS   { rmxAlarmDescription , rmxActiveAlarmDateAndTime, rmxActiveAlarmIndex , rmxActiveAlarmListName , rmxActiveAlarmRmxStatus }
             STATUS  current
             DESCRIPTION
             "Failed to open Users list file"
             ::= { rmxTraps 5800 } 



rmxUsersListCorruptedAlarmClear  NOTIFICATION-TYPE
             OBJECTS   { rmxAlarmDescription , rmxActiveAlarmDateAndTime, rmxActiveAlarmIndex , rmxActiveAlarmListName , rmxActiveAlarmRmxStatus }
             STATUS  current
             DESCRIPTION
             "Failed to open Users list file"
             ::= { rmxTraps 15800 } 



rmxDefaultUserExistsAlarmFault  NOTIFICATION-TYPE
             OBJECTS   { rmxAlarmDescription , rmxActiveAlarmDateAndTime, rmxActiveAlarmIndex , rmxActiveAlarmListName , rmxActiveAlarmRmxStatus }
             STATUS  current
             DESCRIPTION
             "Polycom default User exists. For security reasons, it is recommended to delete this User and create your own User."
             ::= { rmxTraps 5801 } 



rmxDefaultUserExistsAlarmClear  NOTIFICATION-TYPE
             OBJECTS   { rmxAlarmDescription , rmxActiveAlarmDateAndTime, rmxActiveAlarmIndex , rmxActiveAlarmListName , rmxActiveAlarmRmxStatus }
             STATUS  current
             DESCRIPTION
             "Polycom default User exists. For security reasons, it is recommended to delete this User and create your own User."
             ::= { rmxTraps 15801 } 



rmxSupportOperatorIllegalInFederalModeAlarmFault  NOTIFICATION-TYPE
             OBJECTS   { rmxAlarmDescription , rmxActiveAlarmDateAndTime, rmxActiveAlarmIndex , rmxActiveAlarmListName , rmxActiveAlarmRmxStatus }
             STATUS  current
             DESCRIPTION
             "User Name  SUPPORT cannot be used in Enhanced Security Mode"
             ::= { rmxTraps 5802 } 



rmxSupportOperatorIllegalInFederalModeAlarmClear  NOTIFICATION-TYPE
             OBJECTS   { rmxAlarmDescription , rmxActiveAlarmDateAndTime, rmxActiveAlarmIndex , rmxActiveAlarmListName , rmxActiveAlarmRmxStatus }
             STATUS  current
             DESCRIPTION
             "User Name  SUPPORT cannot be used in Enhanced Security Mode"
             ::= { rmxTraps 15802 } 



rmxIsdnServicesConfigurationChangedAlarmFault  NOTIFICATION-TYPE
             OBJECTS   { rmxAlarmDescription , rmxActiveAlarmDateAndTime, rmxActiveAlarmIndex , rmxActiveAlarmListName , rmxActiveAlarmRmxStatus }
             STATUS  current
             DESCRIPTION
             "ISDN/PSTN Network Services configuration changed"
             ::= { rmxTraps 5900 } 



rmxIsdnServicesConfigurationChangedAlarmClear  NOTIFICATION-TYPE
             OBJECTS   { rmxAlarmDescription , rmxActiveAlarmDateAndTime, rmxActiveAlarmIndex , rmxActiveAlarmListName , rmxActiveAlarmRmxStatus }
             STATUS  current
             DESCRIPTION
             "ISDN/PSTN Network Services configuration changed"
             ::= { rmxTraps 15900 } 



rmxNoIsdnPstnLicensingAlarmFault  NOTIFICATION-TYPE
             OBJECTS   { rmxAlarmDescription , rmxActiveAlarmDateAndTime, rmxActiveAlarmIndex , rmxActiveAlarmListName , rmxActiveAlarmRmxStatus }
             STATUS  current
             DESCRIPTION
             "No License for ISDN/PSTN. Please activate the RTM ISDN card through Polycom website"
             ::= { rmxTraps 5901 } 



rmxNoIsdnPstnLicensingAlarmClear  NOTIFICATION-TYPE
             OBJECTS   { rmxAlarmDescription , rmxActiveAlarmDateAndTime, rmxActiveAlarmIndex , rmxActiveAlarmListName , rmxActiveAlarmRmxStatus }
             STATUS  current
             DESCRIPTION
             "No License for ISDN/PSTN. Please activate the RTM ISDN card through Polycom website"
             ::= { rmxTraps 15901 } 



rmxNoRtmIsdnCardAlarmFault  NOTIFICATION-TYPE
             OBJECTS   { rmxAlarmDescription , rmxActiveAlarmDateAndTime, rmxActiveAlarmIndex , rmxActiveAlarmListName , rmxActiveAlarmRmxStatus }
             STATUS  current
             DESCRIPTION
             "RTM ISDN card not found"
             ::= { rmxTraps 5902 } 



rmxNoRtmIsdnCardAlarmClear  NOTIFICATION-TYPE
             OBJECTS   { rmxAlarmDescription , rmxActiveAlarmDateAndTime, rmxActiveAlarmIndex , rmxActiveAlarmListName , rmxActiveAlarmRmxStatus }
             STATUS  current
             DESCRIPTION
             "RTM ISDN card not found"
             ::= { rmxTraps 15902 } 



rmxNoClockSourceAlarmFault  NOTIFICATION-TYPE
             OBJECTS   { rmxAlarmDescription , rmxActiveAlarmDateAndTime, rmxActiveAlarmIndex , rmxActiveAlarmListName , rmxActiveAlarmRmxStatus }
             STATUS  current
             DESCRIPTION
             "No clock source"
             ::= { rmxTraps 5903 } 



rmxNoClockSourceAlarmClear  NOTIFICATION-TYPE
             OBJECTS   { rmxAlarmDescription , rmxActiveAlarmDateAndTime, rmxActiveAlarmIndex , rmxActiveAlarmListName , rmxActiveAlarmRmxStatus }
             STATUS  current
             DESCRIPTION
             "No clock source"
             ::= { rmxTraps 15903 } 



rmxSingleClockSourceAlarmFault  NOTIFICATION-TYPE
             OBJECTS   { rmxAlarmDescription , rmxActiveAlarmDateAndTime, rmxActiveAlarmIndex , rmxActiveAlarmListName , rmxActiveAlarmRmxStatus }
             STATUS  current
             DESCRIPTION
             "Single clock source"
             ::= { rmxTraps 5904 } 



rmxSingleClockSourceAlarmClear  NOTIFICATION-TYPE
             OBJECTS   { rmxAlarmDescription , rmxActiveAlarmDateAndTime, rmxActiveAlarmIndex , rmxActiveAlarmListName , rmxActiveAlarmRmxStatus }
             STATUS  current
             DESCRIPTION
             "Single clock source"
             ::= { rmxTraps 15904 } 



rmxGkmngrAvfWrongMcuConfigAlarmFault  NOTIFICATION-TYPE
             OBJECTS   { rmxAlarmDescription , rmxActiveAlarmDateAndTime, rmxActiveAlarmIndex , rmxActiveAlarmListName , rmxActiveAlarmRmxStatus }
             STATUS  current
             DESCRIPTION
             "MCU is not configured for AVF gatekeeper mode"
             ::= { rmxTraps 5950 } 



rmxGkmngrAvfWrongMcuConfigAlarmClear  NOTIFICATION-TYPE
             OBJECTS   { rmxAlarmDescription , rmxActiveAlarmDateAndTime, rmxActiveAlarmIndex , rmxActiveAlarmListName , rmxActiveAlarmRmxStatus }
             STATUS  current
             DESCRIPTION
             "MCU is not configured for AVF gatekeeper mode"
             ::= { rmxTraps 15950 } 



rmxGateKeeperErrorAlarmFault  NOTIFICATION-TYPE
             OBJECTS   { rmxAlarmDescription , rmxActiveAlarmDateAndTime, rmxActiveAlarmIndex , rmxActiveAlarmListName , rmxActiveAlarmRmxStatus }
             STATUS  current
             DESCRIPTION
             "Gatekeeper failure"
             ::= { rmxTraps 5951 } 



rmxGateKeeperErrorAlarmClear  NOTIFICATION-TYPE
             OBJECTS   { rmxAlarmDescription , rmxActiveAlarmDateAndTime, rmxActiveAlarmIndex , rmxActiveAlarmListName , rmxActiveAlarmRmxStatus }
             STATUS  current
             DESCRIPTION
             "Gatekeeper failure"
             ::= { rmxTraps 15951 } 



rmxCanNotEstablishConnectionWithApplicationServerAlarmFault  NOTIFICATION-TYPE
             OBJECTS   { rmxAlarmDescription , rmxActiveAlarmDateAndTime, rmxActiveAlarmIndex , rmxActiveAlarmListName , rmxActiveAlarmRmxStatus }
             STATUS  current
             DESCRIPTION
             "Failed to connect to application server"
             ::= { rmxTraps 6000 } 



rmxCanNotEstablishConnectionWithApplicationServerAlarmClear  NOTIFICATION-TYPE
             OBJECTS   { rmxAlarmDescription , rmxActiveAlarmDateAndTime, rmxActiveAlarmIndex , rmxActiveAlarmListName , rmxActiveAlarmRmxStatus }
             STATUS  current
             DESCRIPTION
             "Failed to connect to application server"
             ::= { rmxTraps 16000 } 



rmxSystemConfigurationAlarmFault  NOTIFICATION-TYPE
             OBJECTS   { rmxAlarmDescription , rmxActiveAlarmDateAndTime, rmxActiveAlarmIndex , rmxActiveAlarmListName , rmxActiveAlarmRmxStatus }
             STATUS  current
             DESCRIPTION
             "Configuration of external database did not complete."
             ::= { rmxTraps 6001 } 



rmxSystemConfigurationAlarmClear  NOTIFICATION-TYPE
             OBJECTS   { rmxAlarmDescription , rmxActiveAlarmDateAndTime, rmxActiveAlarmIndex , rmxActiveAlarmListName , rmxActiveAlarmRmxStatus }
             STATUS  current
             DESCRIPTION
             "Configuration of external database did not complete."
             ::= { rmxTraps 16001 } 



rmxExternalDbCertificateErrorAlarmFault  NOTIFICATION-TYPE
             OBJECTS   { rmxAlarmDescription , rmxActiveAlarmDateAndTime, rmxActiveAlarmIndex , rmxActiveAlarmListName , rmxActiveAlarmRmxStatus }
             STATUS  current
             DESCRIPTION
             "Error in external database certificate"
             ::= { rmxTraps 6002 } 



rmxExternalDbCertificateErrorAlarmClear  NOTIFICATION-TYPE
             OBJECTS   { rmxAlarmDescription , rmxActiveAlarmDateAndTime, rmxActiveAlarmIndex , rmxActiveAlarmListName , rmxActiveAlarmRmxStatus }
             STATUS  current
             DESCRIPTION
             "Error in external database certificate"
             ::= { rmxTraps 16002 } 



rmxIvrServiceListMissingDefaultServiceAlarmFault  NOTIFICATION-TYPE
             OBJECTS   { rmxAlarmDescription , rmxActiveAlarmDateAndTime, rmxActiveAlarmIndex , rmxActiveAlarmListName , rmxActiveAlarmRmxStatus }
             STATUS  current
             DESCRIPTION
             "No default IVR Service in IVR Services list"
             ::= { rmxTraps 6050 } 



rmxIvrServiceListMissingDefaultServiceAlarmClear  NOTIFICATION-TYPE
             OBJECTS   { rmxAlarmDescription , rmxActiveAlarmDateAndTime, rmxActiveAlarmIndex , rmxActiveAlarmListName , rmxActiveAlarmRmxStatus }
             STATUS  current
             DESCRIPTION
             "No default IVR Service in IVR Services list"
             ::= { rmxTraps 16050 } 



rmxCanNotCreateDefaultProfileAlarmFault  NOTIFICATION-TYPE
             OBJECTS   { rmxAlarmDescription , rmxActiveAlarmDateAndTime, rmxActiveAlarmIndex , rmxActiveAlarmListName , rmxActiveAlarmRmxStatus }
             STATUS  current
             DESCRIPTION
             "Failed to create Default Profile"
             ::= { rmxTraps 6051 } 



rmxCanNotCreateDefaultProfileAlarmClear  NOTIFICATION-TYPE
             OBJECTS   { rmxAlarmDescription , rmxActiveAlarmDateAndTime, rmxActiveAlarmIndex , rmxActiveAlarmListName , rmxActiveAlarmRmxStatus }
             STATUS  current
             DESCRIPTION
             "Failed to create Default Profile"
             ::= { rmxTraps 16051 } 



rmxNoReadMrDbReqRecievedFromRsrcAlarmFault  NOTIFICATION-TYPE
             OBJECTS   { rmxAlarmDescription , rmxActiveAlarmDateAndTime, rmxActiveAlarmIndex , rmxActiveAlarmListName , rmxActiveAlarmRmxStatus }
             STATUS  current
             DESCRIPTION
             "Resource process failed to request the Meeting Room list during startup."
             ::= { rmxTraps 6052 } 



rmxNoReadMrDbReqRecievedFromRsrcAlarmClear  NOTIFICATION-TYPE
             OBJECTS   { rmxAlarmDescription , rmxActiveAlarmDateAndTime, rmxActiveAlarmIndex , rmxActiveAlarmListName , rmxActiveAlarmRmxStatus }
             STATUS  current
             DESCRIPTION
             "Resource process failed to request the Meeting Room list during startup."
             ::= { rmxTraps 16052 } 



rmxFailedToConnectRecordingLinkAlarmFault  NOTIFICATION-TYPE
             OBJECTS   { rmxAlarmDescription , rmxActiveAlarmDateAndTime, rmxActiveAlarmIndex , rmxActiveAlarmListName , rmxActiveAlarmRmxStatus }
             STATUS  current
             DESCRIPTION
             "Failed to connect to recording device"
             ::= { rmxTraps 6053 } 



rmxFailedToConnectRecordingLinkAlarmClear  NOTIFICATION-TYPE
             OBJECTS   { rmxAlarmDescription , rmxActiveAlarmDateAndTime, rmxActiveAlarmIndex , rmxActiveAlarmListName , rmxActiveAlarmRmxStatus }
             STATUS  current
             DESCRIPTION
             "Failed to connect to recording device"
             ::= { rmxTraps 16053 } 



rmxRecordingLinkDisconnecedUnexpectedlyAlarmFault  NOTIFICATION-TYPE
             OBJECTS   { rmxAlarmDescription , rmxActiveAlarmDateAndTime, rmxActiveAlarmIndex , rmxActiveAlarmListName , rmxActiveAlarmRmxStatus }
             STATUS  current
             DESCRIPTION
             "Recording device has disconnected unexpectedly"
             ::= { rmxTraps 6054 } 



rmxRecordingLinkDisconnecedUnexpectedlyAlarmClear  NOTIFICATION-TYPE
             OBJECTS   { rmxAlarmDescription , rmxActiveAlarmDateAndTime, rmxActiveAlarmIndex , rmxActiveAlarmListName , rmxActiveAlarmRmxStatus }
             STATUS  current
             DESCRIPTION
             "Recording device has disconnected unexpectedly"
             ::= { rmxTraps 16054 } 



rmxSystemBasedModeNotIntializedAlarmFault  NOTIFICATION-TYPE
             OBJECTS   { rmxAlarmDescription , rmxActiveAlarmDateAndTime, rmxActiveAlarmIndex , rmxActiveAlarmListName , rmxActiveAlarmRmxStatus }
             STATUS  current
             DESCRIPTION
             "Failed to initialize system base mode"
             ::= { rmxTraps 6055 } 



rmxSystemBasedModeNotIntializedAlarmClear  NOTIFICATION-TYPE
             OBJECTS   { rmxAlarmDescription , rmxActiveAlarmDateAndTime, rmxActiveAlarmIndex , rmxActiveAlarmListName , rmxActiveAlarmRmxStatus }
             STATUS  current
             DESCRIPTION
             "Failed to initialize system base mode"
             ::= { rmxTraps 16055 } 



rmxConfEncryptionErrorAlarmFault  NOTIFICATION-TYPE
             OBJECTS   { rmxAlarmDescription , rmxActiveAlarmDateAndTime, rmxActiveAlarmIndex , rmxActiveAlarmListName , rmxActiveAlarmRmxStatus }
             STATUS  current
             DESCRIPTION
             "Conference Encryption Error"
             ::= { rmxTraps 6056 } 



rmxConfEncryptionErrorAlarmClear  NOTIFICATION-TYPE
             OBJECTS   { rmxAlarmDescription , rmxActiveAlarmDateAndTime, rmxActiveAlarmIndex , rmxActiveAlarmListName , rmxActiveAlarmRmxStatus }
             STATUS  current
             DESCRIPTION
             "Conference Encryption Error"
             ::= { rmxTraps 16056 } 



rmxSnmpAgentInitFailedAlarmFault  NOTIFICATION-TYPE
             OBJECTS   { rmxAlarmDescription , rmxActiveAlarmDateAndTime, rmxActiveAlarmIndex , rmxActiveAlarmListName , rmxActiveAlarmRmxStatus }
             STATUS  current
             DESCRIPTION
             "Failure in initialization of SNMP agent."
             ::= { rmxTraps 6100 } 



rmxSnmpAgentInitFailedAlarmClear  NOTIFICATION-TYPE
             OBJECTS   { rmxAlarmDescription , rmxActiveAlarmDateAndTime, rmxActiveAlarmIndex , rmxActiveAlarmListName , rmxActiveAlarmRmxStatus }
             STATUS  current
             DESCRIPTION
             "Failure in initialization of SNMP agent."
             ::= { rmxTraps 16100 } 



rmxRestoreSucceededAlarmFault  NOTIFICATION-TYPE
             OBJECTS   { rmxAlarmDescription , rmxActiveAlarmDateAndTime, rmxActiveAlarmIndex , rmxActiveAlarmListName , rmxActiveAlarmRmxStatus }
             STATUS  current
             DESCRIPTION
             "Restore Succeeded"
             ::= { rmxTraps 6200 } 



rmxRestoreSucceededAlarmClear  NOTIFICATION-TYPE
             OBJECTS   { rmxAlarmDescription , rmxActiveAlarmDateAndTime, rmxActiveAlarmIndex , rmxActiveAlarmListName , rmxActiveAlarmRmxStatus }
             STATUS  current
             DESCRIPTION
             "Restore Succeeded"
             ::= { rmxTraps 16200 } 



rmxRestoreFailedAlarmFault  NOTIFICATION-TYPE
             OBJECTS   { rmxAlarmDescription , rmxActiveAlarmDateAndTime, rmxActiveAlarmIndex , rmxActiveAlarmListName , rmxActiveAlarmRmxStatus }
             STATUS  current
             DESCRIPTION
             "Restore Failed"
             ::= { rmxTraps 6201 } 



rmxRestoreFailedAlarmClear  NOTIFICATION-TYPE
             OBJECTS   { rmxAlarmDescription , rmxActiveAlarmDateAndTime, rmxActiveAlarmIndex , rmxActiveAlarmListName , rmxActiveAlarmRmxStatus }
             STATUS  current
             DESCRIPTION
             "Restore Failed"
             ::= { rmxTraps 16201 } 



rmxEncryptionServerErrorAlarmFault  NOTIFICATION-TYPE
             OBJECTS   { rmxAlarmDescription , rmxActiveAlarmDateAndTime, rmxActiveAlarmIndex , rmxActiveAlarmListName , rmxActiveAlarmRmxStatus }
             STATUS  current
             DESCRIPTION
             "Encryption Server Error. Failed to generate the encryption key"
             ::= { rmxTraps 7010 } 



rmxEncryptionServerErrorAlarmClear  NOTIFICATION-TYPE
             OBJECTS   { rmxAlarmDescription , rmxActiveAlarmDateAndTime, rmxActiveAlarmIndex , rmxActiveAlarmListName , rmxActiveAlarmRmxStatus }
             STATUS  current
             DESCRIPTION
             "Encryption Server Error. Failed to generate the encryption key"
             ::= { rmxTraps 17010 } 



rmxExchangeServerConnectionErrorAlarmFault  NOTIFICATION-TYPE
             OBJECTS   { rmxAlarmDescription , rmxActiveAlarmDateAndTime, rmxActiveAlarmIndex , rmxActiveAlarmListName , rmxActiveAlarmRmxStatus }
             STATUS  current
             DESCRIPTION
             "Unable to connect to Exchange Server."
             ::= { rmxTraps 7050 } 



rmxExchangeServerConnectionErrorAlarmClear  NOTIFICATION-TYPE
             OBJECTS   { rmxAlarmDescription , rmxActiveAlarmDateAndTime, rmxActiveAlarmIndex , rmxActiveAlarmListName , rmxActiveAlarmRmxStatus }
             STATUS  current
             DESCRIPTION
             "Unable to connect to Exchange Server."
             ::= { rmxTraps 17050 } 

END
