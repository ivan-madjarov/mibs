-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


MX-FILE-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpAddress,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

fileMIB MODULE-IDENTITY
 LAST-UPDATED   "0610200000Z"
 ORGANIZATION " Mediatrix Telecom, Inc. "
 CONTACT-INFO " Mediatrix Telecom, Inc.
                4229, Garlock Street
                Sherbrooke (Quebec)
                Canada
                Phone: (819) 829-8749
                "
 DESCRIPTION  " File Manager

                This service allows the user to manage files.
                "
 -- ****************************************************************************
 
 -- Revision history
 -- ****************************************************************************
 REVISION       "0610200000Z"
 DESCRIPTION  " Initial Revision "
 REVISION       "0707120000Z"
 DESCRIPTION  " Made Files.FileName and Files.Delete Obsolete. Added
                Files.Index, Files.FileName and Delete "
 REVISION       "1205140000Z"
 DESCRIPTION  " Added Files.Type, Files.FileDescription, Files.FileSize,
                FileSystemQuotaSize and also the DownloadFile command. "
 ::= { mediatrixServices 2600 }

fileMIBObjects OBJECT IDENTIFIER ::= { fileMIB 1 }

-- *****************************************************************************

-- Table:Files

-- *****************************************************************************

filesTable OBJECT-TYPE
 SYNTAX         SEQUENCE OF FilesEntry
 MAX-ACCESS     not-accessible
 STATUS         current
 DESCRIPTION  " Files

                This table contains all the files saved by the user.
                "
 ::= { fileMIBObjects 100 }
 filesEntry OBJECT-TYPE
  SYNTAX        FilesEntry
  MAX-ACCESS    not-accessible
  STATUS        current
  DESCRIPTION " A row in table Files. "
  INDEX         {
                  filesIndex
                }

  ::= { filesTable 1 }

 FilesEntry ::= SEQUENCE
 {
   filesIndex           Unsigned32,
   filesFileName        OCTET STRING,
   filesFileDescription OCTET STRING,
   filesFileSize        Unsigned32
 }

 -- Index:Index

 filesIndex OBJECT-TYPE
  SYNTAX        Unsigned32
  MAX-ACCESS    read-only
  STATUS        current
  DESCRIPTION " Index

                Unique identifier of the row in the table.
                "
  ::= { filesEntry 101 }

 -- Columnar:File Name

 filesFileName OBJECT-TYPE
  SYNTAX        OCTET STRING ( SIZE(1..255) )
  MAX-ACCESS    read-only
  STATUS        current
  DESCRIPTION " File Name

                Relative path and name of the file (directories are split with
                '/').
                "
  ::= { filesEntry 201 }

 -- Columnar:File Description

 filesFileDescription OBJECT-TYPE
  SYNTAX        OCTET STRING ( SIZE(0..255) )
  MAX-ACCESS    read-only
  STATUS        current
  DESCRIPTION " File Description

                Textual description describing the content of the file.

                The file description uses special tags in the file to built the
                string description.


                "
  ::= { filesEntry 400 }

 -- Columnar:File Size

 filesFileSize OBJECT-TYPE
  SYNTAX        Unsigned32
  MAX-ACCESS    read-only
  STATUS        current
  DESCRIPTION " File Size

                File size of the associated file.

                This value is expressed in kiloBytes (kb).


                "
  ::= { filesEntry 500 }


-- End of table:Files

-- Scalar:File system quota size

fileSystemQuotaSize OBJECT-TYPE
 SYNTAX        Unsigned32
 MAX-ACCESS    read-only
 STATUS        current
 DESCRIPTION " File system quota size

               This value indicates the file system quota allocated for the
               service file system.

               This value is expressed in kiloBytes (kb).


               "
 ::= { fileMIBObjects 200 }

-- ****************************************************************************

-- Group:Notification Messages Configuration

-- ****************************************************************************

notificationsGroup OBJECT IDENTIFIER
 ::= { fileMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { fileMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
