-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


MX-SIPEP-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpAddress,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

sipEpMIB MODULE-IDENTITY
 LAST-UPDATED   "0604180000Z"
 ORGANIZATION " Mediatrix Telecom, Inc. "
 CONTACT-INFO " Mediatrix Telecom, Inc.
                4229, Garlock Street
                Sherbrooke (Quebec)
                Canada
                Phone: (819) 829-8749
                "
 DESCRIPTION  " SIP Endpoint

                The SIP Endpoint service is a voice over IP gateway based on
                the SIP protocol suite.
                "
 -- ****************************************************************************
 
 -- Revision history
 -- ****************************************************************************
 REVISION       "0604180000Z"
 DESCRIPTION  " Initial Revision "
 REVISION       "0702190000Z"
 DESCRIPTION  " Add SippingTransfer01UsingReferRfc3515 value in
                InteropTransferVersion. "
 REVISION       "0703230000Z"
 DESCRIPTION  " Add values UserAgent.Publish, PublicationRefresh,
                DefaultPublicationRefreshTime,
                DefaultPublicationProposedExpirationValue,
                DefaultStaticPresenceCompositorServerHost and
                InteropDefaultPublicationExpiration. Add tables
                GwSpecificPublication and PublicationStatus. Add group
                PublicationGroup. "
 REVISION       "0704180000Z"
 DESCRIPTION  " Add InteropDefaultUsernameValue. "
 REVISION       "0705030000Z"
 DESCRIPTION  " Add interopUseMultiStepsRegistration and Gateway.Domain. "
 REVISION       "0705160000Z"
 DESCRIPTION  " Added Authentication.ValidateRealm. "
 REVISION       "0708010000Z"
 DESCRIPTION  " Added InteropCallWaitingToneControlViaSipInfo. "
 REVISION       "0708080000Z"
 DESCRIPTION  " Added InteropSdpT38ParametersEncoding variable. "
 REVISION       "0708200000Z"
 DESCRIPTION  " Made table ErrorMappingSipToCause and ErrorMappingCauseToSip
                user sizable with MaxSize=40. "
 REVISION       "0709060000Z"
 DESCRIPTION  " Added InteropReInviteForVoiceOn606NotAcceptable "
 REVISION       "0710180000Z"
 DESCRIPTION  " Added InteropAllowMultipleActiveMediaInAnswer "
 REVISION       "0711140000Z"
 DESCRIPTION  " Added enum 'Username' in Authentication.ApplyTo. Added columns
                Authentication.Up, Authentication.Down, Authentication.Insert
                and Authentication.Delete. Added command InsertAuthentication.
                Set Authentication user sizable with a maximum of 64. Change
                EpAdm.RegistrationUsers maximum size to 64. "
 REVISION       "0711210000Z"
 DESCRIPTION  " Added SipKeepAliveGroup (SipKeepAliveMethod,
                SipKeepAliveErrorCauseNumber and SipKeepAliveInterval) and
                added InteropSipOptionsMethodSupport. "
 REVISION       "0803110000Z"
 DESCRIPTION  " Add enum 'InvalidResponse' in RegistrationStatus.State. Modify
                default value of InteropMaxForwardsValue to 70. Modify range
                value of InteropMaxForwardsValue to 0..200. Modify the
                structure of the TransportConfig table. Added Tls to the
                TransportConfig table. Added TransportTlsPersistentBasePort to
                the TransportGroup. Added TlsPersistentConnectionStatus table
                to the TransportGroup. Added
                interopSiemensTransportHeaderEnable and
                interopTlsClientAuthenticationEnable to the interopGroup. "
 REVISION       "0805020000Z"
 DESCRIPTION  " Added InteropIgnoreSipOptionsOnNoUsuableEndpoints. "
 REVISION       "0808060000Z"
 DESCRIPTION  " Added InteropIgnorePlusInUsername variable. "
 REVISION       "0809040000Z"
 DESCRIPTION  " Added BehaviorOnT38InviteNotAccepted interop table. "
 REVISION       "0810100000Z"
 DESCRIPTION  " Modify InteropEnforceOfferAnswerModel description. "
 REVISION       "0811100000Z"
 DESCRIPTION  " Added RemoteHostIpAddr to the TlsPersistentConnectionStatus
                table. "
 REVISION       "0811180000Z"
 DESCRIPTION  " Added InteropTlsCertificateValidation to the interopGroup. "
 REVISION       "0812050000Z"
 DESCRIPTION  " Modified the InteropTlsCertificateValidation description. "
 REVISION       "0901060000Z"
 DESCRIPTION  " Added InteropOnHoldAnswerSdpStreamDirection variable. "
 REVISION       "0901290000Z"
 DESCRIPTION  " Modified the description of
                InteropTlsClientAuthenticationEnable. "
 REVISION       "0902190000Z"
 DESCRIPTION  " Added InteropTcpConnectTimeout variable. "
 REVISION       "0904150000Z"
 DESCRIPTION  " Added PrackAndUpdateGroup group. (UasPrackSupport and
                UacPrackSupport variables) "
 REVISION       "0904160000Z"
 DESCRIPTION  " Added InteropEscapePoundInSipUriUsername variable. "
 REVISION       "0905120000Z"
 DESCRIPTION  " Added InteropSipUriUserParameterValue variable. Updated
                InteropMapPlusToTonInternational. "
 REVISION       "0907200000Z"
 DESCRIPTION  " Added
                InteropCodecVsBearerCapabilitiesMappingPreferredCodecChoice
                variable. "
 REVISION       "0907270000Z"
 DESCRIPTION  " Added InteropBehaviorOnMachineDetection variable. "
 REVISION       "0909080000Z"
 DESCRIPTION  " Added TransportTlsPersistentRetryInterval variable. Modified
                the description of the PenaltyBox and InteropTcpConnectTimeout
                variables. "
 REVISION       "0910160000Z"
 DESCRIPTION  " Added NoRouteHeader option to DefaultProxyOutboundType and
                GwSpecificProxy.OutboundType "
 REVISION       "0910210000Z"
 DESCRIPTION  " Updated BehaviorOnT38InviteNotAccepted.Behavior. "
 REVISION       "0912140000Z"
 DESCRIPTION  " Added InteropListenForEarlyRtpEnable variable. "
 REVISION       "0912150000Z"
 DESCRIPTION  " Added InteropRegistrationContactMatching. "
 REVISION       "1002150000Z"
 DESCRIPTION  " Clarified variable InteropTlsCertificateValidation description.
                "
 REVISION       "1004070000Z"
 DESCRIPTION  " Added OfferAnswerGroup group and AnswerCodecNegotiation
                variable. "
 REVISION       "1004080000Z"
 DESCRIPTION  " Added group DiversionGroup. "
 REVISION       "1005040000Z"
 DESCRIPTION  " Modified description of the GatewayStatus.State variable. "
 REVISION       "1012010000Z"
 DESCRIPTION  " Added DNS Group, added SupportedDnsQueries variable. "
 REVISION       "1012010000Z"
 DESCRIPTION  " Added InteropCallWaitingSipInfoPrivateNumberCriteria variable
                and removed InteropCallWaitingToneControlViaSipInfo. "
 REVISION       "1012090000Z"
 DESCRIPTION  " Added ePing enum in SipKeepAliveMethod variable. "
 REVISION       "1101180000Z"
 DESCRIPTION  " Added ReInviteUnconditional enum in
                InteropBehaviorOnMachineDetection variable. "
 REVISION       "1102080000Z"
 DESCRIPTION  " Added MessageWaitingIndication group and
                UserAgent.MwiSubscription columnar. "
 REVISION       "1104280000Z"
 DESCRIPTION  " Added Conference Group and modify description for
                GwSpecificProxy.EnableConfig. "
 REVISION       "1105160000Z"
 DESCRIPTION  " Added InteropResolveRouteHeader. "
 REVISION       "1105180000Z"
 DESCRIPTION  " Removed group PublicationGroup, removed variables
                InteropReplacesType, InteropTransferVersion,
                InteropSessionTimerVersion, InteropReplacesVersion,
                InteropReferredByConfig, InteropReuseCredentialEnable,
                InteropBranchMatchingMethod,
                InteropIgnoreViaBranchIdInCancelEnable,
                InteropDefaultRegistrationExpiration, InteropAuthenticationQop,
                InteropIgnoreUsernameParam, InteropDefaultPublicationExpiration
                and InteropUseMultiStepsRegistration. "
 REVISION       "1105170000Z"
 DESCRIPTION  " Added InteropForceDnsNaptrInTls variable. "
 REVISION       "1106140000Z"
 DESCRIPTION  " Added DefaultRegistrationExpirationValue and
                GwSpecificRegistration.ExpirationValue. "
 REVISION       "1106150000Z"
 DESCRIPTION  " Added InteropAckBranchMatching. "
 REVISION       "1106150000Z"
 DESCRIPTION  " Increased the max size of the Authentication and
                RegistrationUsers tables to 100. "
 REVISION       "1107110000Z"
 DESCRIPTION  " Added DefaultOutboundPriorityCallRouting in new Priority group.
                "
 REVISION       "1108010000Z"
 DESCRIPTION  " Increased maximum value of InsertAuthentication to 100. "
 REVISION       "1108160000Z"
 DESCRIPTION  " Added SessionRefreshRequestMethod in group SessionRefresh.
                PrackAndUpdateGroup is renamed PrackGroup. SessionTimerGroup is
                renamed SessionRefreshGroup. "
 REVISION       "1108220000Z"
 DESCRIPTION  " Added group EventHandlingGroup. "
 REVISION       "1108220000Z"
 DESCRIPTION  " Added InteropIgnoreRequireHeaderEnable. "
 REVISION       "1109140000Z"
 DESCRIPTION  " Added ReasonHeaderSupport variable. "
 REVISION       "1110050000Z"
 DESCRIPTION  " Changed the description of the
                DefaultRegistrationProposedExpirationValue and
                GwSpecificRegistrationProposedExpirationValue variables. "
 REVISION       "1110250000Z"
 DESCRIPTION  " Modified description of variables
                InteropSdpDirectionAttributeEnable,
                InteropOnHoldSdpStreamDirection and
                InteropOnHoldAnswerSdpStreamDirection. Added
                Gateway.MediaNetworks and TransportTlsCertificateTrustLevel. "
 REVISION       "1111010000Z"
 DESCRIPTION  " Added InteropRejectCodeForUnsupportedSdpOffer. "
 REVISION       "1111010000Z"
 DESCRIPTION  " Added variable InteropSdpDirectionAttributeLevel. "
 REVISION       "1111020000Z"
 DESCRIPTION  " Added InteropUAHeaderFormat variable. "
 REVISION       "1111230000Z"
 DESCRIPTION  " Added InteropSipInfoWithoutContentAnswer variable. "
 REVISION       "1112010000Z"
 DESCRIPTION  " Added BehaviorOnInitialRegistrationReception and
                RegistrationDelayOnInitialRegistrationReception variables. "
 REVISION       "1112010000Z"
 DESCRIPTION  " Added DefaultUserRegistrationUnregisteredBehavior variable. "
 REVISION       "1112120000Z"
 DESCRIPTION  " Added InteropSdpDetectPeerDirectionAttributeSupportEnable
                variable. "
 REVISION       "1112200000Z"
 DESCRIPTION  " Converted InteropLocalRingOnProvisionalResponse variable to an
                enum. "
 REVISION       "1112210000Z"
 DESCRIPTION  " Added SipKeepAliveDestination and
                GwKeepAliveAlternateDestination variables. "
 REVISION       "1201090000Z"
 DESCRIPTION  " Added the ContactDomain columnar to the UserAgent table. "
 REVISION       "1201260000Z"
 DESCRIPTION  " Modified description of PenaltyBoxEnable variable. "
 REVISION       "1202140000Z"
 DESCRIPTION  " Added InteropOnHoldSdpConnectionAddress variable and modified
                description of InteropSdpDirectionAttributeEnable and
                InteropOnHoldAnswerSdpStreamDirection variables. "
 REVISION       "1203050000Z"
 DESCRIPTION  " Added InteropRegistrationDelayValue variable. "
 REVISION       "1203090000Z"
 DESCRIPTION  " Added InteropUnsupportedContentType variable. "
 REVISION       "1205080000Z"
 DESCRIPTION  " Added InteropWaitConfirmedDialogForBlindTransfer and
                InteropPendingBlindTransferTimeout. "
 REVISION       "1205220000Z"
 DESCRIPTION  " "
 REVISION       "1205240000Z"
 DESCRIPTION  " Added MonitoringGroup group. "
 REVISION       "1207100000Z"
 DESCRIPTION  " Added TransferGroup group. "
 REVISION       "1301130000Z"
 DESCRIPTION  " Added InteropSipContactDisplayNamePresence variable. "
 REVISION       "1303180000Z"
 DESCRIPTION  " Added DefaultRegistrationRetryTime and
                GwSpecificRegistration.RetryTime variables. "
 REVISION       "1303220000Z"
 DESCRIPTION  " Added InteropEscapeFormat and BlindTransferMethod variables.
                Set deprecated the InteropWaitConfirmedDialogForBlindTransfer
                and modified documentation of the Gateway.Port variable. "
 REVISION       "1304040000Z"
 DESCRIPTION  " Modified BehaviorOnT38InviteNotAccepted.SipErrorCode variable
                range. "
 REVISION       "1304180000Z"
 DESCRIPTION  " Set the secret tag for the Aunthentication.Password variable. "
 REVISION       "1308110000Z"
 DESCRIPTION  " Create a group AocGroup. "
 ::= { mediatrixServices 1400 }

sipEpMIBObjects OBJECT IDENTIFIER ::= { sipEpMIB 1 }

-- *****************************************************************************

-- Table:Gateway

-- *****************************************************************************

gatewayTable OBJECT-TYPE
 SYNTAX            SEQUENCE OF GatewayEntry
 MAX-ACCESS        not-accessible
 STATUS            current
 DESCRIPTION   "   Gateway

                   This table holds the basic configuration of the IP gateways.
                   "
 ::= { sipEpMIBObjects 100 }
 gatewayEntry OBJECT-TYPE
  SYNTAX        GatewayEntry
  MAX-ACCESS    not-accessible
  STATUS        current
  DESCRIPTION " A row in table Gateway. "
  INDEX         {
                  gatewayName
                }

  ::= { gatewayTable 1 }

 GatewayEntry ::= SEQUENCE
 {
   gatewayName             OCTET STRING,
   gatewayNetworkInterface OCTET STRING,
   gatewayMediaNetworks    OCTET STRING,
   gatewayPort             MxAdvancedIpPort,
   gatewaySecurePort       MxAdvancedIpPort,
   gatewayDomain           OCTET STRING,
   gatewayDelete           INTEGER
 }

 -- Index:Name

 gatewayName OBJECT-TYPE
  SYNTAX        OCTET STRING
  MAX-ACCESS    read-only
  STATUS        current
  DESCRIPTION " Name

                Name of the SIP gateway. It identifies the gateway in other
                tables.
                "
  ::= { gatewayEntry 100 }

 -- Columnar:Network Interface

 gatewayNetworkInterface OBJECT-TYPE
  SYNTAX        OCTET STRING ( SIZE(1..20) )
  MAX-ACCESS    read-write
  STATUS        current
  DESCRIPTION " Network Interface

                The network on which the gateway listens for incoming SIP
                traffic.

                The value must match one of the 'InterfaceName' values in the
                'NetworkInterfaces' or 'NetworkInterfacesStatus' table of the
                BNI service.

                This value applies to all transports (e.g., UDP, TCP, etc.).


                "
  DEFVAL        { "Lan1" }
  ::= { gatewayEntry 200 }

 -- Columnar:Media Networks

 gatewayMediaNetworks OBJECT-TYPE
  SYNTAX        OCTET STRING ( SIZE(0..255) )
  MAX-ACCESS    read-write
  STATUS        current
  DESCRIPTION " Media Networks

                List of networks (separated by ',') to use for the media
                (voice, fax, etc.) stream. The value must match one of the
                'InterfaceName' values in the 'NetworkInterfacesStatus' table
                of the BNI service. The order in the list defines the priority.
                If the list of media network is empty, the network defined in
                Gateway.NetworkInterface is used.

                When the media stream is negotiated, only the first active
                network (NetworkInterfacesStatus.Status columnar of the network
                in the BNI service is active) of an IP address family (IPv4,
                IPv6) is used. All subsequent networks of the same IP family
                are ignored.

                Note: When generating an offer and multiple networks are
                available for the media, ANAT grouping (RFC 4091) is
                automatically activated. When generating an answer, ANAT
                grouping is activated when it is detected in the offer. The SDP
                answer will always have only one active media with the
                preferred IP address family.


                "
  DEFVAL        { "" }
  ::= { gatewayEntry 250 }

 -- Columnar:SIP Port

 gatewayPort OBJECT-TYPE
  SYNTAX        MxAdvancedIpPort
  MAX-ACCESS    read-write
  STATUS        current
  DESCRIPTION " SIP Port

                Port on which the gateway listens for incoming unsecure SIP
                traffic.

                This is used only when UDP and/or TCP transports are enabled.

                Note: If set to 0, the unit uses the default SIP port 5060.


                "
  DEFVAL        { 0 }
  ::= { gatewayEntry 300 }

 -- Columnar:SIP Secure Port

 gatewaySecurePort OBJECT-TYPE
  SYNTAX        MxAdvancedIpPort
  MAX-ACCESS    read-write
  STATUS        current
  DESCRIPTION " SIP Secure Port

                Port on which the gateway listens for incoming secure SIP
                traffic.

                This is used only when the TLS transport is enabled.

                Note: If set to 0, the unit uses the default SIP port 5061.


                "
  DEFVAL        { 0 }
  ::= { gatewayEntry 325 }

 -- Columnar:SIP Domain

 gatewayDomain OBJECT-TYPE
  SYNTAX        OCTET STRING ( SIZE(0..255) )
  MAX-ACCESS    read-write
  STATUS        current
  DESCRIPTION " SIP Domain

                SIP domain name. If not empty, the address of record uses this
                string instead of the home domain proxy (refer to the variable
                'DefaultStaticProxyHomeDomainHost').
                "
  DEFVAL        { "" }
  ::= { gatewayEntry 350 }

 -- Row command:Delete

 gatewayDelete OBJECT-TYPE
  SYNTAX        INTEGER { noOp(0), delete(10) }
  MAX-ACCESS    read-write
  STATUS        current
  DESCRIPTION " Delete

                Deletes this row.
                "
  DEFVAL        { noOp }
  ::= { gatewayEntry 400 }


-- End of table:Gateway

-- *****************************************************************************

-- Table:GatewayStatus

-- *****************************************************************************

gatewayStatusTable OBJECT-TYPE
 SYNTAX              SEQUENCE OF GatewayStatusEntry
 MAX-ACCESS          not-accessible
 STATUS              current
 DESCRIPTION       " GatewayStatus

                     This table holds the status of the current IP gateways.
                     "
 ::= { sipEpMIBObjects 150 }
 gatewayStatusEntry OBJECT-TYPE
  SYNTAX        GatewayStatusEntry
  MAX-ACCESS    not-accessible
  STATUS        current
  DESCRIPTION " A row in table GatewayStatus. "
  INDEX         {
                  gatewayStatusName
                }

  ::= { gatewayStatusTable 1 }

 GatewayStatusEntry ::= SEQUENCE
 {
   gatewayStatusName             OCTET STRING,
   gatewayStatusNetworkInterface OCTET STRING,
   gatewayStatusMediaNetworks    OCTET STRING,
   gatewayStatusPort             MxAdvancedIpPort,
   gatewayStatusSecurePort       MxAdvancedIpPort,
   gatewayStatusDomain           OCTET STRING,
   gatewayStatusState            OCTET STRING
 }

 -- Index:Name

 gatewayStatusName OBJECT-TYPE
  SYNTAX        OCTET STRING
  MAX-ACCESS    read-only
  STATUS        current
  DESCRIPTION " Name

                Name of the SIP gateway. It identifies the gateway in other
                tables.
                "
  ::= { gatewayStatusEntry 100 }

 -- Columnar:Network Interface

 gatewayStatusNetworkInterface OBJECT-TYPE
  SYNTAX        OCTET STRING
  MAX-ACCESS    read-only
  STATUS        current
  DESCRIPTION " Network Interface

                The network on which the gateway listens for incoming SIP
                traffic.

                This value applies to all transports (e.g., UDP, TCP, etc.).


                "
  ::= { gatewayStatusEntry 200 }

 -- Columnar:Media Networks

 gatewayStatusMediaNetworks OBJECT-TYPE
  SYNTAX        OCTET STRING
  MAX-ACCESS    read-only
  STATUS        current
  DESCRIPTION " Media Networks

                List of networks (separated by ',') to use for the media
                (voice, fax, etc.) stream. Only the first active network of an
                IP address family (IPv4, IPv6) is present. The order in the
                list defines the priority.

                Note: When generating an offer and multiple network are
                available for the media, ANAT grouping (RFC 4091) is
                automatically activated. When generating an answer, ANAT
                grouping is activated when it is detected in the offer. The SDP
                answer will always have only one active media with the
                preferred IP address family.


                "
  ::= { gatewayStatusEntry 250 }

 -- Columnar:SIP Port

 gatewayStatusPort OBJECT-TYPE
  SYNTAX        MxAdvancedIpPort
  MAX-ACCESS    read-only
  STATUS        current
  DESCRIPTION " SIP Port

                Port on which the gateway listens for incoming unsecure SIP
                traffic.

                This value applies to UDP and TCP transports.

                Note: If set to 0, the unit uses the default SIP port 5060.


                "
  ::= { gatewayStatusEntry 300 }

 -- Columnar:SIP Secure Port

 gatewayStatusSecurePort OBJECT-TYPE
  SYNTAX        MxAdvancedIpPort
  MAX-ACCESS    read-only
  STATUS        current
  DESCRIPTION " SIP Secure Port

                Port on which the gateway listens for incoming SIP traffic.

                This value applies to TLS transport.

                Note: If set to 0, the unit uses the default SIP port 5061.


                "
  ::= { gatewayStatusEntry 325 }

 -- Columnar:SIP Domain

 gatewayStatusDomain OBJECT-TYPE
  SYNTAX        OCTET STRING
  MAX-ACCESS    read-only
  STATUS        current
  DESCRIPTION " SIP Domain

                SIP domain name. String used to build the address of record.
                "
  ::= { gatewayStatusEntry 350 }

 -- Columnar:State

 gatewayStatusState OBJECT-TYPE
  SYNTAX        OCTET STRING
  MAX-ACCESS    read-only
  STATUS        current
  DESCRIPTION " State

                The current state of the gateway.

                  * Ready: The gateway is ready to make and receive calls.
                  * Cannot start, port already in use: The gateway cannot open
                    its IP port because the port is already used by another
                    service. This generally occurs when the administrator adds
                    a new gateway but forgets to configure a different IP port.
                  * Network down: The SIP gateway is not started or the network
                    interface on which the SIP gateway is associated does not
                    have an IP address.
                  * Restarting: The SIP gateway cannot make or receive calls
                    while it is restarting.
                  * Waiting for time synchronization: The gateway is started
                    but it cannot open its SIP TLS port because the real-time
                    clock is not synchronized. This generally occurs when the
                    SNTP server is not set or is unreachable.
                  * Server unreachable: The gateway is started but it cannot
                    make and receive calls because the SIP server is
                    unreachable. This state is only reported when a KeepAlive
                    mechanism is used.


                "
  ::= { gatewayStatusEntry 400 }


-- End of table:GatewayStatus

-- *****************************************************************************

-- Table:User Agent SIP

-- *****************************************************************************

userAgentTable OBJECT-TYPE
 SYNTAX        SEQUENCE OF UserAgentEntry
 MAX-ACCESS    not-accessible
 STATUS        current
 DESCRIPTION " User Agent SIP

               This table holds the user agent configuration variables. A user
               agent is a logical entity that can act as both a client and a
               server for the duration of a dialog. The information contained
               in this table will be used to dynamically create the To, From
               and Contact headers used in the request sent by the UAC (User
               Agent Client).
               "
 ::= { sipEpMIBObjects 400 }
 userAgentEntry OBJECT-TYPE
  SYNTAX        UserAgentEntry
  MAX-ACCESS    not-accessible
  STATUS        current
  DESCRIPTION " A row in table User Agent SIP. "
  INDEX         {
                  userAgentEpId
                }

  ::= { userAgentTable 1 }

 UserAgentEntry ::= SEQUENCE
 {
   userAgentEpId          OCTET STRING,
   userAgentUsername      OCTET STRING,
   userAgentFriendlyName  OCTET STRING,
   userAgentRegister      MxEnableState,
   userAgentGatewayName   OCTET STRING,
   userAgentPublish       MxEnableState,
   userAgentMwiSubscribe  MxEnableState,
   userAgentContactDomain OCTET STRING
 }

 -- Index:Endpoint Identifier

 userAgentEpId OBJECT-TYPE
  SYNTAX        OCTET STRING
  MAX-ACCESS    read-only
  STATUS        current
  DESCRIPTION " Endpoint Identifier

                String that identifies an endpoint in other tables.
                "
  ::= { userAgentEntry 100 }

 -- Columnar:User Name

 userAgentUsername OBJECT-TYPE
  SYNTAX        OCTET STRING ( SIZE(0..255) )
  MAX-ACCESS    read-write
  STATUS        current
  DESCRIPTION " User Name

                A string that uniquely identifies this endpoint in the domain.
                For example, a telephone number.

                This string is used when creating the Contact and From headers.
                The SIP From header carries the permanent location (IP address,
                home domain) where the endpoint is. The SIP Contact header
                carries the CURRENT location (IP address) where the endpoint
                can be reached.

                Contact headers are used in two ways:

                First, contacts are registered to the SIP registrar. This
                enables callers to be redirected to the endpoint's current
                location.

                Second, a contact header is sent along with any request the UA
                sends (e.g.: INVITE), and is used by the target UA as a return
                address for later requests sent by the target to this endpoint.


                "
  DEFVAL        { "" }
  ::= { userAgentEntry 200 }

 -- Columnar:Friendly Name

 userAgentFriendlyName OBJECT-TYPE
  SYNTAX        OCTET STRING ( SIZE(0..255) )
  MAX-ACCESS    read-write
  STATUS        current
  DESCRIPTION " Friendly Name

                Friendly name for SIP User Agent. A friendly name or display
                name is meant to contain a descriptive version of the URI and
                is intended to be displayed to a user interface.
                "
  DEFVAL        { "" }
  ::= { userAgentEntry 300 }

 -- Columnar:Register

 userAgentRegister OBJECT-TYPE
  SYNTAX        MxEnableState
  MAX-ACCESS    read-write
  STATUS        current
  DESCRIPTION " Register

                Indicate if the endpoint need to register to the registrar.

                Endpoint configured to register will become unavailable when
                not registerer. The variable RegistrationUnregisteredBehavior
                can modify this behavior.


                "
  DEFVAL        { disable }
  ::= { userAgentEntry 400 }

 -- Columnar:Gateway

 userAgentGatewayName OBJECT-TYPE
  SYNTAX        OCTET STRING
  MAX-ACCESS    read-write
  STATUS        current
  DESCRIPTION " Gateway

                Selects on which SIP gateway the user configuration is applied.
                The value must match the gateway name as defined in
                Gateway.Name.

                The value 'all' means all gateways.


                "
  DEFVAL        { "all" }
  ::= { userAgentEntry 500 }

 -- Columnar:Publish

 userAgentPublish OBJECT-TYPE
  SYNTAX        MxEnableState
  MAX-ACCESS    read-write
  STATUS        current
  DESCRIPTION " Publish

                Indicates if the endpoint needs to publish its event state to
                the Presence Compositor server.
                "
  DEFVAL        { disable }
  ::= { userAgentEntry 600 }

 -- Columnar:MWI Subscribe

 userAgentMwiSubscribe OBJECT-TYPE
  SYNTAX        MxEnableState
  MAX-ACCESS    read-write
  STATUS        current
  DESCRIPTION " MWI Subscribe

                Indicates if the endpoint needs to subscribe to messaging
                system.
                "
  DEFVAL        { disable }
  ::= { userAgentEntry 700 }

 -- Columnar:Contact Domain

 userAgentContactDomain OBJECT-TYPE
  SYNTAX        OCTET STRING ( SIZE(0..127) )
  MAX-ACCESS    read-write
  STATUS        current
  DESCRIPTION " Contact Domain

                Indicates the host part of the SIP contact field. If an empty
                string is specified, the listening IP address is used.
                "
  DEFVAL        { "" }
  ::= { userAgentEntry 800 }


-- End of table:User Agent SIP

-- ****************************************************************************

-- Group:Proxy

-- ****************************************************************************

proxyGroup OBJECT IDENTIFIER
 ::= { sipEpMIBObjects 500 }
 -- Scalar:Default Static Home Domain Proxy Server Host.

 defaultStaticProxyHomeDomainHost OBJECT-TYPE
  SYNTAX        MxIpHostNamePort
  MAX-ACCESS    read-write
  STATUS        current
  DESCRIPTION " Default Static Home Domain Proxy Server Host.

                SIP proxy server FQDN and port.

                An intermediary entity that acts as both a server and a client
                for the purpose of making requests on behalf of other clients.
                A proxy server primarily plays the role of routing, which
                means its job is to ensure that a request is passed on to
                another entity that can further process the request. Proxies
                are also useful for enforcing policy and for firewall
                traversal. A proxy interprets, and, if necessary, rewrites
                parts of a request message before forwarding it.

                Note: If the host corresponds to a domain name that is bound
                to a SRV record, the port must be set to 0 for the unit to
                perform DNS SRV queries; otherwise only A type record lookups
                will be used.


                "
  DEFVAL        { "192.168.10.10:0" }
  ::= { proxyGroup 100 }

 -- Scalar:Default Static Outboud Proxy Server Host

 defaultStaticProxyOutboundHost OBJECT-TYPE
  SYNTAX        MxIpHostNamePort
  MAX-ACCESS    read-write
  STATUS        current
  DESCRIPTION " Default Static Outboud Proxy Server Host

                SIP outbound proxy server FQDN and port

                To disable the outbound proxy, set it to '0.0.0.0'.

                From RFC 3261: A proxy that receives requests from a client,
                even though it may not be the server resolved by the
                Request-URI. Typically, a UA is manually configured with an
                outbound proxy, or can learn about one through
                auto-configuration protocols.

                When enabled, the initial route for all SIP requests will
                contain the outbound proxy address, suffixed with the loose
                routing parameter 'lr'. The Request-URI still contains the
                home domain proxy address. Requests are directed to the first
                route (the outbound proxy).

                Note: If the host corresponds to a domain name that is bound
                to a SRV record, the port must be set to 0 for the unit to
                perform DNS SRV queries; otherwise only A type record lookups
                will be used.


                "
  DEFVAL        { "" }
  ::= { proxyGroup 200 }

 -- Scalar:Outbound Proxy Type

 defaultProxyOutboundType OBJECT-TYPE
  SYNTAX        INTEGER { looseRouter(100) , strictRouter(200) , noRouteHeader
                (300) }
  MAX-ACCESS    read-write
  STATUS        current
  DESCRIPTION " Outbound Proxy Type

                Default type of routing that the configured outbound proxy
                does.

                  * LooseRouter: This is the most current method for SIP
                    routing, as per RFC 3261, and will become the standard
                    behavior once RFC 3261 compliance is achieved. See the
                    DefaultStaticProxyOutboundHost variable for a description.
                  * StrictRouter: Pre-RFC 3261, RFC 2543 compatible SIP
                    routing.
                  * NoRouteHeader: Removes the route header from all SIP
                    packets sent to an outbound proxy. Does not modify
                    persistent TLS connection headers.

                The initial route for all SIP requests contains the home
                domain proxy address (the Request-URI). Requests are directed
                to the outbound proxy.

                In other words, the Request-URI is constructed as usual by
                using the home domain proxy and the user name, but is used in
                the route set. The Request-URI is filled by the outbound proxy
                address.

                Also see 'DefaultStaticProxyHomeDomainHost'.


                "
  DEFVAL        { looseRouter }
  ::= { proxyGroup 300 }

 -- ***************************************************************************
 
 -- Table:SIP Gateway Specific Proxy

 -- ***************************************************************************
 
 gwSpecificProxyTable OBJECT-TYPE
  SYNTAX        SEQUENCE OF GwSpecificProxyEntry
  MAX-ACCESS    not-accessible
  STATUS        current
  DESCRIPTION " SIP Gateway Specific Proxy

                A table of the proxy configuration indexed by the SIP gateway
                name. It is used to override the default value.
                "
  ::= { proxyGroup 400 }
  gwSpecificProxyEntry OBJECT-TYPE
   SYNTAX        GwSpecificProxyEntry
   MAX-ACCESS    not-accessible
   STATUS        current
   DESCRIPTION " A row in table SIP Gateway Specific Proxy. "
   INDEX         {
                   gwSpecificProxyGatewayName
                 }

   ::= { gwSpecificProxyTable 1 }

  GwSpecificProxyEntry ::= SEQUENCE
  {
    gwSpecificProxyGatewayName    OCTET STRING,
    gwSpecificProxyEnableConfig   MxEnableState,
    gwSpecificProxyHomeDomainHost MxIpHostNamePort,
    gwSpecificProxyOutboundHost   MxIpHostNamePort,
    gwSpecificProxyOutboundType   INTEGER
  }

  -- Index:Gateway Name

  gwSpecificProxyGatewayName OBJECT-TYPE
   SYNTAX        OCTET STRING
   MAX-ACCESS    read-only
   STATUS        current
   DESCRIPTION " Gateway Name

                 String that identifies a SIP gateway in other tables.
                 "
   ::= { gwSpecificProxyEntry 100 }

  -- Columnar:Enable Configuration

  gwSpecificProxyEnableConfig OBJECT-TYPE
   SYNTAX        MxEnableState
   MAX-ACCESS    read-write
   STATUS        current
   DESCRIPTION " Enable Configuration

                 Defines the configuration to use for a specific SIP gateway.

                   * Disable: The SIP gateway uses the default configuration
                     as defined in the DefaultStaticProxyHomeDomainHost,
                     DefaultStaticProxyOutboundHost, and
                     DefaultProxyOutboundType variables.
                   * Enable: The SIP gateway uses the specific configuration
                     as defined in the GwSpecificProxy.HomeDomainHost,
                     GwSpecificProxy.OutboundHost, and
                     GwSpecificProxy.OutboundType variables.


                 "
   DEFVAL        { disable }
   ::= { gwSpecificProxyEntry 200 }

  -- Columnar:SIP Gateway Specific Home Domain Proxy Server Host

  gwSpecificProxyHomeDomainHost OBJECT-TYPE
   SYNTAX        MxIpHostNamePort
   MAX-ACCESS    read-write
   STATUS        current
   DESCRIPTION " SIP Gateway Specific Home Domain Proxy Server Host

                 SIP proxy server FQDN and port for a specific SIP gateway.

                 An intermediary entity that acts as both a server and a
                 client for the purpose of making requests on behalf of other
                 clients. A proxy server primarily plays the role of routing,
                 which means its job is to ensure that a request is passed on
                 to another entity that can further process the request.
                 Proxies are also useful for enforcing policy and for firewall
                 traversal. A proxy interprets, and, if necessary, rewrites
                 parts of a request message before forwarding it.

                 Note: If the host corresponds to a domain name that is bound
                 to a SRV record, the port must be set to 0 for the unit to
                 perform DNS SRV queries; otherwise, only A type record
                 lookups will be used.


                 "
   DEFVAL        { "192.168.0.10:0" }
   ::= { gwSpecificProxyEntry 300 }

  -- Columnar:SIP Gateway Specific Outboud Proxy Server Host

  gwSpecificProxyOutboundHost OBJECT-TYPE
   SYNTAX        MxIpHostNamePort
   MAX-ACCESS    read-write
   STATUS        current
   DESCRIPTION " SIP Gateway Specific Outboud Proxy Server Host

                 SIP outbound proxy server FQDN and port for a specific SIP
                 gateway.

                 To disable the outbound proxy, set it to '0.0.0.0'.

                 From RFC 3261: A proxy that receives requests from a client,
                 even though it may not be the server resolved by the
                 Request-URI. Typically, a UA is manually configured with an
                 outbound proxy, or can learn about one through
                 auto-configuration protocols.

                 When enabled, the initial route for all SIP requests will
                 contain the outbound proxy address, suffixed with the loose
                 routing parameter 'lr'. The Request-URI still contains the
                 home domain proxy address. Requests are directed to the first
                 route (the outbound proxy).

                 Note: If the host corresponds to a domain name that is bound
                 to a SRV record, the port must be set to 0 for the unit to
                 perform DNS SRV queries; otherwise, only A type record
                 lookups will be used.


                 "
   DEFVAL        { "0.0.0.0:0" }
   ::= { gwSpecificProxyEntry 400 }

  -- Columnar:SIP Gateway Specific Outbound Proxy Type

  gwSpecificProxyOutboundType OBJECT-TYPE
   SYNTAX        INTEGER { looseRouter(100) , strictRouter(200) ,
                 noRouteHeader(300) }
   MAX-ACCESS    read-write
   STATUS        current
   DESCRIPTION " SIP Gateway Specific Outbound Proxy Type

                 Type of routing that the configured outbound proxy does for a
                 specific SIP gateway.

                   * LooseRouter: This is the most current method for SIP
                     routing, as per RFC 3261, and will become the standard
                     behavior once RFC 3261 compliance is achieved. See the
                     DefaultStaticProxyOutboundHost variable for a
                     description.
                   * StrictRouter: Pre-RFC 3261, RFC 2543 compatible SIP
                     routing.
                   * NoRouteHeader: Removes the route header from all SIP
                     packets sent to an outbound proxy. Does not modify
                     persistent TLS connection headers.

                 The initial route for all SIP requests contains the home
                 domain proxy address (the Request-URI). Requests are directed
                 to the outbound proxy.

                 In other words, the Request-URI is constructed as usual by
                 using the home domain proxy and the user name, but is used in
                 the route set. The Request-URI is filled by the outbound
                 proxy address.

                 Also see 'DefaultStaticProxyHomeDomainHost'.


                 "
   DEFVAL        { looseRouter }
   ::= { gwSpecificProxyEntry 500 }


 -- End of table:SIP Gateway Specific Proxy

-- End of group:Proxy

-- ****************************************************************************

-- Group:Session Timer

-- ****************************************************************************

sessionRefreshGroup OBJECT IDENTIFIER
 ::= { sipEpMIBObjects 600 }
 -- Scalar:Default Enable/Disable Session Expiration Services

 defaultSessionTimerEnable OBJECT-TYPE
  SYNTAX        MxEnableState
  MAX-ACCESS    read-write
  STATUS        current
  DESCRIPTION " Default Enable/Disable Session Expiration Services

                Enables/Disables the session expiration services.

                Disabling this service is not recommended since it will make
                'dead' calls impossible to detect.

                Questions and Answers:

                Q - What is the session timer extension?

                A - The session timer extension allows the detection of the
                premature end of a call caused by a network problem or a
                peer's failure.

                The session timer mechanism sends a refresh request every n
                seconds. This refresh request is either an reINVITE or an
                UPDATE, according to configuration in
                SessionRefreshRequestMethod. A sucessful response (200 OK) to
                this refresh request means that the peer is still alive and
                reachable. A timeout to this refresh request may mean that
                there are problems in the signaling path, or that the peer is
                simply not there anymore. In that case the call will be shut
                down by using normal SIP means.

                Q - SDP in Session Timer reINVITEs or UPDATEs:

                A - If the reINVITE method is used, it is sent with the last
                SDP that was negotiated. Reception of a session timer reINVITE
                should not modify the connection characteristics. If the
                UPDATE method is used, it is sent without any SDP offer.

                Q - Relation between minimum and maximum values:

                A - A UA that receives a Session-Expires header whose value is
                smaller than the minimum it is willing to accept will reply a
                422 Timer too low to the INVITE and terminate the call. The
                phone will not ring.

                It is up to the caller to decide what to do when it receives a
                422 to its INVITE. The service will automatically retry the
                INVITE, with a Session-Expires value equal to the minimum
                value that the UAS was ready to accept (found in the Min-SE
                header). This means that the maximum value as set in the
                service might not be followed. This has the advantageous
                effect of establishing the call even if the two endpoints have
                conflicting values. The service will also keep retrying as
                long as it gets 422 answers with different Min-SE values.

                Q - Who refreshes?

                A - Sending a session timer reINVITE or UPDATE is referred to
                as refreshing the session. Normally, the UAS that receives the
                INVITE will have the last word on who refreshes. The service
                will always let the UAC (caller) do the refreshes if the
                caller supports session timers. In the case the caller does
                not support session timers, the service will assume the role
                of the refresher.

                If a specific configuration is set in the
                EpSpecificSessionTimer.Enable variable and the
                EpSpecificSessionTimer.EnableConfig variable is set to
                'Enable', then it overrides the current default configuration.


                "
  DEFVAL        { enable }
  ::= { sessionRefreshGroup 100 }

 -- Scalar:Default Minimum Session Expiration Delay

 defaultSessionTimerMinimumExpirationDelay OBJECT-TYPE
  SYNTAX        Unsigned32 ( 180..3600 )
  MAX-ACCESS    read-write
  STATUS        current
  DESCRIPTION " Default Minimum Session Expiration Delay

                Minimum value for the periodical session refreshes.

                This value is reflected in the Min-SE header.

                The Min-SE value is a threshold under which proxies and/or UAs
                on the signaling path are not allowed to go.

                Increasing the minimum helps to reduce network traffic, but
                also makes 'dead' calls longer to detect.

                This value is expressed in seconds (s).

                Also see DefaultSessionTimerMaximumExpirationDelay.

                If a specific configuration is set in the
                EpSpecificSessionTimer.MinimumSessionExpirationDelay variable
                and the EpSpecificSessionTimer.EnableConfig variable is set to
                'Enable', then it overrides the current default configuration.


                "
  DEFVAL        { 1800 }
  ::= { sessionRefreshGroup 200 }

 -- Scalar:Default Maximum Session Expiration Delay

 defaultSessionTimerMaximumExpirationDelay OBJECT-TYPE
  SYNTAX        Unsigned32 ( 180..3600 )
  MAX-ACCESS    read-write
  STATUS        current
  DESCRIPTION " Default Maximum Session Expiration Delay

                Suggested maximum time for the periodical session refreshes.

                This value is reflected in the Session-Expires header.

                Increasing the maximum helps to reduce network traffic, but
                also makes 'dead' calls longer to detect.

                This value is expressed in seconds (s).

                Also see DefaultSessionTimerMinimumExpirationDelay.

                If a specific configuration is set in the
                EpSpecificSessionTimer.MaximumSessionExpirationDelay variable
                and the EpSpecificSessionTimer.EnableConfig variable is set to
                'Enable', then it overrides the current default configuration.


                "
  DEFVAL        { 3600 }
  ::= { sessionRefreshGroup 300 }

 -- Scalar:Method for Session Refresh Requests

 sessionRefreshRequestMethod OBJECT-TYPE
  SYNTAX        INTEGER { reInvite(100) , update(200) }
  MAX-ACCESS    read-write
  STATUS        current
  DESCRIPTION " Method for Session Refresh Requests

                Selects the method used for sending Session Refresh Requests.

                  * ReInvite: Session Refresh Requests are sent with the
                    INVITE method.
                  * Update: Session Refresh Requests are sent with the UPDATE
                    method.

                Session Refresh Requests can be received via both methods,
                regardless of how this variable is configured.


                "
  DEFVAL        { reInvite }
  ::= { sessionRefreshGroup 400 }

-- End of group:Session Timer

-- ****************************************************************************

-- Group:Authentication Group

-- ****************************************************************************

authenticationGroup OBJECT IDENTIFIER
 ::= { sipEpMIBObjects 700 }
 -- ***************************************************************************
 
 -- Table:SIP Authentication Configuration

 -- ***************************************************************************
 
 authenticationTable OBJECT-TYPE
  SYNTAX        SEQUENCE OF AuthenticationEntry
  MAX-ACCESS    not-accessible
  STATUS        current
  DESCRIPTION " SIP Authentication Configuration

                This table holds the user agent authentication configuration
                variables. Authentication information adds some level of
                security.
                "
  ::= { authenticationGroup 100 }
  authenticationEntry OBJECT-TYPE
   SYNTAX        AuthenticationEntry
   MAX-ACCESS    not-accessible
   STATUS        current
   DESCRIPTION " A row in table SIP Authentication Configuration. "
   INDEX         {
                   authenticationIndex
                 }

   ::= { authenticationTable 1 }

  AuthenticationEntry ::= SEQUENCE
  {
    authenticationIndex         Unsigned32,
    authenticationApplyTo       INTEGER,
    authenticationEpId          OCTET STRING,
    authenticationGatewayName   OCTET STRING,
    authenticationValidateRealm MxEnableState,
    authenticationRealm         OCTET STRING,
    authenticationUsername      OCTET STRING,
    authenticationPassword      OCTET STRING,
    authenticationUp            INTEGER,
    authenticationDown          INTEGER,
    authenticationInsert        INTEGER,
    authenticationDelete        INTEGER
  }

  -- Index:Authentication Entry Index

  authenticationIndex OBJECT-TYPE
   SYNTAX        Unsigned32
   MAX-ACCESS    read-only
   STATUS        current
   DESCRIPTION " Authentication Entry Index

                 Authentication index for this row.

                 The table's entries are searched in ascending
                 Authentication.Index order.


                 "
   ::= { authenticationEntry 100 }

  -- Row command:Delete

  authenticationDelete OBJECT-TYPE
   SYNTAX        INTEGER { noOp(0), delete(10) }
   MAX-ACCESS    read-write
   STATUS        current
   DESCRIPTION " Delete

                 Deletes this row.

                 The Authentication table has a minimum size of 20 rows. When
                 calling the 'DeleteAllRows' command on this table, all the
                 rows are deleted and 20 new rows are added. When the user
                 deletes a specific row, a new row is added at the end of the
                 table if the number of rows is inferior to 20.


                 "
   DEFVAL        { noOp }
   ::= { authenticationEntry 1000 }

  -- Columnar:Entity to Apply the Authentication Entry

  authenticationApplyTo OBJECT-TYPE
   SYNTAX        INTEGER { unit(100) , endpoint(200) , gateway(300) , username
                 (400) }
   MAX-ACCESS    read-write
   STATUS        current
   DESCRIPTION " Entity to Apply the Authentication Entry

                 Selects which criterion to use for matching an authentication
                 request with an authentication entry.

                   * Unit: The authentication entry is used on all challenges.
                   * Endpoint: The authentication entry is used for all
                     challenges related to the endpoint specified in
                     'Authentication.EpId'.
                   * Gateway: The authentication entry is used for all
                     challenges related to the gateway specified in
                     'Authentication.GatewayName'.
                   * Username: The authentication entry is used for all
                     challenges related to the username specified in
                     'Authentication.Username'. Only the username part of the
                     'Authentication.Username' is used if the value has the
                     format 'username@domain'.


                 "
   DEFVAL        { unit }
   ::= { authenticationEntry 200 }

  -- Columnar:Endpoint Identification

  authenticationEpId OBJECT-TYPE
   SYNTAX        OCTET STRING
   MAX-ACCESS    read-write
   STATUS        current
   DESCRIPTION " Endpoint Identification

                 String that identifies an endpoint in other tables. Used only
                 if the variable 'ApplyTo' is set to 'Endpoint'.
                 "
   DEFVAL        { "" }
   ::= { authenticationEntry 300 }

  -- Columnar:Gateway Name

  authenticationGatewayName OBJECT-TYPE
   SYNTAX        OCTET STRING
   MAX-ACCESS    read-write
   STATUS        current
   DESCRIPTION " Gateway Name

                 String that identifies a SIP gateway in other tables. It is
                 used only if the variable 'ApplyTo' is set to 'Gateway'.
                 "
   DEFVAL        { "" }
   ::= { authenticationEntry 350 }

  -- Columnar:Validate Realm

  authenticationValidateRealm OBJECT-TYPE
   SYNTAX        MxEnableState
   MAX-ACCESS    read-write
   STATUS        current
   DESCRIPTION " Validate Realm

                 Configures how to interpret the realm in the challenge.

                   * Disable: The credential defined in this row will be used
                     with any realm given in the challenge.
                   * Enable: The credential defined in this row will be used
                     only when the realm given in the challenge is the same as
                     the one defined in 'Realm'.


                 "
   DEFVAL        { enable }
   ::= { authenticationEntry 375 }

  -- Columnar:Authentication Realm

  authenticationRealm OBJECT-TYPE
   SYNTAX        OCTET STRING ( SIZE(0..128) )
   MAX-ACCESS    read-write
   STATUS        current
   DESCRIPTION " Authentication Realm

                 When authentication informations are required from users, the
                 realm identifies who requested the information.
                 "
   DEFVAL        { "" }
   ::= { authenticationEntry 400 }

  -- Columnar:Authentification User Name

  authenticationUsername OBJECT-TYPE
   SYNTAX        OCTET STRING ( SIZE(0..128) )
   MAX-ACCESS    read-write
   STATUS        current
   DESCRIPTION " Authentification User Name

                 A string that uniquely identifies this entity in the realm,
                 used for authentication purposes. The user name always maps
                 to a password.
                 "
   DEFVAL        { "" }
   ::= { authenticationEntry 500 }

  -- Columnar:Authentication Password

  authenticationPassword OBJECT-TYPE
   SYNTAX        OCTET STRING ( SIZE(0..128) )
   MAX-ACCESS    read-write
   STATUS        current
   DESCRIPTION " Authentication Password

                 User password.
                 "
   DEFVAL        { "" }
   ::= { authenticationEntry 600 }

  -- Row command:Up

  authenticationUp OBJECT-TYPE
   SYNTAX        INTEGER { noOp(0), up(10) }
   MAX-ACCESS    read-write
   STATUS        current
   DESCRIPTION " Up

                 Moves the current row upside.
                 "
   DEFVAL        { noOp }
   ::= { authenticationEntry 700 }

  -- Row command:Down

  authenticationDown OBJECT-TYPE
   SYNTAX        INTEGER { noOp(0), down(10) }
   MAX-ACCESS    read-write
   STATUS        current
   DESCRIPTION " Down

                 Moves the current row downside.
                 "
   DEFVAL        { noOp }
   ::= { authenticationEntry 800 }

  -- Row command:Insert

  authenticationInsert OBJECT-TYPE
   SYNTAX        INTEGER { noOp(0), insert(10) }
   MAX-ACCESS    read-write
   STATUS        current
   DESCRIPTION " Insert

                 Inserts a new row before this row.
                 "
   DEFVAL        { noOp }
   ::= { authenticationEntry 900 }


 -- End of table:SIP Authentication Configuration

-- End of group:Authentication Group

-- ****************************************************************************

-- Group:Registration Group

-- ****************************************************************************

registrationGroup OBJECT IDENTIFIER
 ::= { sipEpMIBObjects 800 }
 -- Scalar:Default Registration Refresh Time

 defaultRegistrationRefreshTime OBJECT-TYPE
  SYNTAX        Unsigned32 ( 0..600 )
  MAX-ACCESS    read-write
  STATUS        current
  DESCRIPTION " Default Registration Refresh Time

                In SIP, a registration is valid for a period of time defined
                by the registrar. Once a unit is registered, the SIP protocol
                requires the User Agent to refresh this registration before
                the registration expires. Typically, this re-registration must
                be completed before the ongoing registration expires, so that
                the User Agent's registration state does not change (i.e.,
                remains 'registered').

                This variable defines the time, relative to the end of the
                registration, at which a registered unit will begin updating
                its registration.

                For example, if the registration lasts 60 minutes and
                RegistrationRefreshTime is set to 43, the unit will send new
                REGISTER requests 59 minutes and 17 seconds after the
                reception of the registration acknowledgement (43 seconds
                before the end of the registration period).

                Setting RegistrationRefreshTime to 0 means that the User Agent
                will fall into the 'unregistered' state BEFORE sending the
                re-REGISTER requests.

                This value is expressed in seconds (s).

                If a specific configuration is set in the
                GwSpecificRegistration.RefreshTime variable and the
                GwSpecificRegistration.EnableConfig variable is set to
                'Enable', then it overrides the current default configuration.


                "
  DEFVAL        { 60 }
  ::= { registrationGroup 200 }

 -- Scalar:Default Expiration Value In Registration

 defaultRegistrationExpirationValue OBJECT-TYPE
  SYNTAX        Unsigned32 ( 1..86400 )
  MAX-ACCESS    read-write
  STATUS        current
  DESCRIPTION " Default Expiration Value In Registration

                Configures the default registration expiration.

                This value is used when the contact in a registration response
                contains no expires or the expires is badly formatted. In this
                case, the delay before a re-REGISTER is the value set in this
                variable minus the value set in the
                'DefaultRegistrationRefreshTime' variable.

                See also the 'DefaultRegistrationRefreshTime' variable.

                This value is expressed in seconds (s).

                If a specific configuration is set in the
                GwSpecificRegistration.ExpirationValue variable and the
                GwSpecificRegistration.EnableConfig variable is set to
                'Enable', then it overrides the current default configuration.


                "
  DEFVAL        { 3600 }
  ::= { registrationGroup 250 }

 -- Scalar:Proposed Expiration Value In Registration

 defaultRegistrationProposedExpirationValue OBJECT-TYPE
  SYNTAX        Unsigned32 ( 0..86400 )
  MAX-ACCESS    read-write
  STATUS        current
  DESCRIPTION " Proposed Expiration Value In Registration

                Configures the suggested expiration delay of a contact in the
                SIP REGISTER.

                Set the value to 0 to disable the expiration proposition.

                This value does not modify the delay before a re-REGISTER. The
                delay is the expires of the contact in the 200 OK response to
                the REGISTER minus the value set in the
                'RegistrationRefreshTime' variable. If the expires of the
                contact in the 200 OK response to the REGISTER is not present
                or badly formatted, then the delay is the default registration
                proposed expiration value minus the value set in the
                'RegistrationRefreshTime' variable.

                See also the 'DefaultRegistrationRefreshTime' variable.

                This value is expressed in seconds (s).

                If a specific configuration is set in the
                GwSpecificRegistration.ProposedExpirationValue variable and
                the GwSpecificRegistration.EnableConfig variable is set to
                'Enable', then it overrides the current default configuration.


                "
  DEFVAL        { 0 }
  ::= { registrationGroup 300 }

 -- Scalar:Default Registration Retry Time

 defaultRegistrationRetryTime OBJECT-TYPE
  SYNTAX        Unsigned32 ( 1..86400 )
  MAX-ACCESS    read-write
  STATUS        current
  DESCRIPTION " Default Registration Retry Time

                Configures the interval on which a failed registration is
                retried.

                This variable defines the time, relative to the failure of the
                registration, at which the device retries the registration.

                This value is expressed in seconds (s).

                If a specific configuration is set in the
                GwSpecificRegistration.RetryTime variable and the
                GwSpecificRegistration.EnableConfig variable is set to
                'Enable', then it overrides the current default configuration.


                "
  DEFVAL        { 120 }
  ::= { registrationGroup 350 }

 -- Scalar:Unregistered Behavior

 defaultRegistrationUnregisteredBehavior OBJECT-TYPE
  SYNTAX        MxEnableState
  MAX-ACCESS    read-write
  STATUS        current
  DESCRIPTION " Unregistered Behavior

                Specifies whether an endpoint should remain enabled or not
                when not registered.

                  * Disable: When an endpoint is not registered, it is
                    disabled. This prevents the user from making or receiving
                    calls. Picking up the handset yields a fast busy tone and
                    incoming INVITEs receive a '403 Forbidden' response.
                  * Enable: When an endpoint is not registered, it is still
                    enabled. The user can receive and initiate outgoing calls.
                    Note that since the endpoint is not registered to a
                    registrar, the public address of the endpoint is not
                    available to the outside world, so the endpoint will most
                    likely be unreachable except through direct IP calling.

                If a specific configuration is set in the
                GwSpecificRegistration.UnregisteredBehavior variable and the
                GwSpecificRegistration.EnableConfig variable is set to
                'Enable', then it overrides the current default configuration.


                "
  DEFVAL        { disable }
  ::= { registrationGroup 400 }

 -- Scalar:Unregistered User Behavior

 defaultUserRegistrationUnregisteredBehavior OBJECT-TYPE
  SYNTAX        INTEGER { noEffect(100) , disableGateway(200) }
  MAX-ACCESS    read-write
  STATUS        current
  DESCRIPTION " Unregistered User Behavior

                Specifies whether the SIP gateway state should be affected or
                not by the unit registrations state.

                  * NoEffect: The unit registrations state has no effect on
                    the SIP gateway state.
                  * DisableGateway: The SIP gateway goes in the 'unregistered'
                    state when all unit registrations are not in the
                    'registered' state.


                "
  DEFVAL        { noEffect }
  ::= { registrationGroup 450 }

 -- Scalar:Default Static Registrar Server Host

 defaultStaticRegistrarServerHost OBJECT-TYPE
  SYNTAX        MxIpHostNamePort
  MAX-ACCESS    read-write
  STATUS        current
  DESCRIPTION " Default Static Registrar Server Host

                SIP registrar server FQDN and port.

                A registrar is a server that accepts REGISTER requests and
                places the information it receives in those requests into the
                location service for the domain it handles.

                Note: If the host corresponds to a domain name that is bound
                to a SRV record, the port must be set to 0 for the unit to
                perform DNS SRV queries; otherwise only type A record lookups
                will be used.

                If a specific configuration is set in the
                GwSpecificRegistration.ServerHost variable and the
                GwSpecificRegistration.EnableConfig variable is set to
                'Enable', then it overrides the current default configuration.


                "
  DEFVAL        { "192.168.10.10:0" }
  ::= { registrationGroup 500 }

 -- ***************************************************************************
 
 -- Table:SIP Gateway Specific Proxy

 -- ***************************************************************************
 
 gwSpecificRegistrationTable OBJECT-TYPE
  SYNTAX        SEQUENCE OF GwSpecificRegistrationEntry
  MAX-ACCESS    not-accessible
  STATUS        current
  DESCRIPTION " SIP Gateway Specific Proxy

                A table of the registration configuration indexed by the SIP
                gateway name. It is used to override the default value.
                "
  ::= { registrationGroup 600 }
  gwSpecificRegistrationEntry OBJECT-TYPE
   SYNTAX        GwSpecificRegistrationEntry
   MAX-ACCESS    not-accessible
   STATUS        current
   DESCRIPTION " A row in table SIP Gateway Specific Proxy. "
   INDEX         {
                   gwSpecificRegistrationGatewayName
                 }

   ::= { gwSpecificRegistrationTable 1 }

  GwSpecificRegistrationEntry ::= SEQUENCE
  {
    gwSpecificRegistrationGatewayName             OCTET STRING,
    gwSpecificRegistrationEnableConfig            MxEnableState,
    gwSpecificRegistrationRefreshTime             Unsigned32,
    gwSpecificRegistrationExpirationValue         Unsigned32,
    gwSpecificRegistrationProposedExpirationValue Unsigned32,
    gwSpecificRegistrationRetryTime               Unsigned32,
    gwSpecificRegistrationUnregisteredBehavior    MxEnableState,
    gwSpecificRegistrationServerHost              MxIpHostNamePort
  }

  -- Index:Gateway Name

  gwSpecificRegistrationGatewayName OBJECT-TYPE
   SYNTAX        OCTET STRING
   MAX-ACCESS    read-only
   STATUS        current
   DESCRIPTION " Gateway Name

                 String that identifies a SIP gateway in other tables.
                 "
   ::= { gwSpecificRegistrationEntry 100 }

  -- Columnar:Enable Configuration

  gwSpecificRegistrationEnableConfig OBJECT-TYPE
   SYNTAX        MxEnableState
   MAX-ACCESS    read-write
   STATUS        current
   DESCRIPTION " Enable Configuration

                 Defines the configuration to use for a specific SIP gateway.

                   * Disable: The SIP gateway uses the default configuration
                     as defined in the DefaultStaticProxyHomeDomainHost ,
                     DefaultRegistrationRefreshTime,
                     DefaultRegistrationProposedExpirationValue,
                     DefaultRegistrationUnregisteredBehavior, and
                     DefaultStaticRegistrarServerHost. variables.
                   * Enable: The endpoint uses the specific configuration as
                     defined in the GwSpecificRegistration.RefreshTime,
                     GwSpecificRegistration.ProposedExpirationValue,
                     GwSpecificRegistration.UnregisteredBehavior, and
                     GwSpecificRegistration.ServerHost


                 "
   DEFVAL        { disable }
   ::= { gwSpecificRegistrationEntry 200 }

  -- Columnar:SIP Gateway Specific Registration Refresh Time

  gwSpecificRegistrationRefreshTime OBJECT-TYPE
   SYNTAX        Unsigned32 ( 0..600 )
   MAX-ACCESS    read-write
   STATUS        current
   DESCRIPTION " SIP Gateway Specific Registration Refresh Time

                 Refresh registration time for a specific SIP gateway.

                 In SIP, a registration is valid for a period of time defined
                 by the registrar. Once a unit is registered, the SIP protocol
                 requires the User Agent to refresh this registration before
                 the registration expires. Typically, this re-registration
                 must be completed before the ongoing registration expires, so
                 that the User Agent's registration state does not change
                 (i.e., remains 'registered').

                 This variable defines the time, relative to the end of the
                 registration, at which a registered unit will begin updating
                 its registration.

                 For instance, if the registration lasts 60 minutes and
                 RegistrationRefreshTime is set to 43, the unit will send new
                 REGISTER requests 59 minutes and 17 seconds after the
                 reception of the registration acknowledgement (43 seconds
                 before the end of the registration period).

                 Setting RegistrationRefreshTime to 0 means that the User
                 Agent will fall into the 'unregistered' state BEFORE sending
                 the re-REGISTER requests.

                 This value is expressed in seconds (s).

                 This configuration overrides the default configuration set in
                 the DefaultRegistrationRefreshTime variable if the
                 GwSpecificRegistration.EnableConfig variable is set to
                 'Enable'.


                 "
   DEFVAL        { 60 }
   ::= { gwSpecificRegistrationEntry 300 }

  -- Columnar:Default Expiration Value In Registration

  gwSpecificRegistrationExpirationValue OBJECT-TYPE
   SYNTAX        Unsigned32 ( 1..86400 )
   MAX-ACCESS    read-write
   STATUS        current
   DESCRIPTION " Default Expiration Value In Registration

                 Configures the default registration expiration.

                 This value is used when the contact in a registration
                 response contains no expires or the expires is badly
                 formatted. In this case, the delay before a re-REGISTER is
                 the value set in this variable minus the value set in the
                 'RefreshTime' variable.

                 See also the 'RefreshTime' variable.

                 This value is expressed in seconds (s).

                 This configuration overrides the default configuration set in
                 the DefaultRegistrationExpirationValue variable if the
                 GwSpecificRegistration.EnableConfig variable is set to
                 'Enable'.


                 "
   DEFVAL        { 3600 }
   ::= { gwSpecificRegistrationEntry 350 }

  -- Columnar:SIP Gateway Specific Proposed Expiration Value In Registration

  gwSpecificRegistrationProposedExpirationValue OBJECT-TYPE
   SYNTAX        Unsigned32 ( 0..86400 )
   MAX-ACCESS    read-write
   STATUS        current
   DESCRIPTION " SIP Gateway Specific Proposed Expiration Value In
                 Registration

                 Suggested expiration delay of a contact in the SIP REGISTER
                 for a specific SIP gateway.

                 Set the value to 0 to disable the expiration proposal.

                 This value does not modify the delay before a re-REGISTER.
                 The delay is the expires of the contact in the 200 OK
                 response to the REGISTER minus the value set in the
                 'RegistrationRefreshTime' variable. If the expires of the
                 contact in the 200 OK response to the REGISTER is not present
                 or badly formatted, then the delay is the default
                 registration proposed expiration value minus the value set in
                 the 'RegistrationRefreshTime' variable.

                 See also the 'RefreshTime' variable.

                 This value is expressed in seconds (s).

                 This configuration overrides the default configuration set in
                 the DefaultRegistrationProposedExpirationValue variable if
                 the GwSpecificRegistration.EnableConfig variable is set to
                 'Enable'.


                 "
   DEFVAL        { 0 }
   ::= { gwSpecificRegistrationEntry 400 }

  -- Columnar:SIP Gateway Specific Registration Retry Time

  gwSpecificRegistrationRetryTime OBJECT-TYPE
   SYNTAX        Unsigned32 ( 1..86400 )
   MAX-ACCESS    read-write
   STATUS        current
   DESCRIPTION " SIP Gateway Specific Registration Retry Time

                 Configures the interval on which a failed registration
                 retries on a specific SIP gateway.

                 This variable defines the time, relative to the failure of
                 the registration, at which the SIP gateway retries the
                 registration.

                 This value is expressed in seconds (s).

                 This configuration overrides the default configuration set in
                 the DefaultRegistrationRetryTime variable if the
                 GwSpecificRegistration.EnableConfig variable is set to
                 'Enable'.


                 "
   DEFVAL        { 120 }
   ::= { gwSpecificRegistrationEntry 450 }

  -- Columnar:SIP Gateway Specific Unregistered Behavior

  gwSpecificRegistrationUnregisteredBehavior OBJECT-TYPE
   SYNTAX        MxEnableState
   MAX-ACCESS    read-write
   STATUS        current
   DESCRIPTION " SIP Gateway Specific Unregistered Behavior

                 Specifies whether an endpoint should remain enabled or not
                 when not registered for a specific SIP gateway.

                   * Disable: When an endpoint is not registered, it is
                     disabled. This prevents the user from making or receiving
                     calls. Picking up the handset yields a fast busy tone and
                     incoming INVITEs receive a '403 Forbidden' response.
                   * Enable: When an endpoint is not registered, it is still
                     enabled. The user can receive and initiate outgoing
                     calls. Note that since the endpoint is not registered to
                     a registrar, the public address of the endpoint is not
                     available to the outside world, so the endpoint will most
                     likely be unreachable except through direct IP calling.

                 This configuration overrides the default configuration set in
                 the DefaultRegistrationUnregisteredBehavior variable if the
                 GwSpecificRegistration.EnableConfig variable is set to
                 'Enable'.


                 "
   DEFVAL        { disable }
   ::= { gwSpecificRegistrationEntry 500 }

  -- Columnar:SIP Gateway Specific Registrar Server Host

  gwSpecificRegistrationServerHost OBJECT-TYPE
   SYNTAX        MxIpHostNamePort
   MAX-ACCESS    read-write
   STATUS        current
   DESCRIPTION " SIP Gateway Specific Registrar Server Host

                 SIP registrar server FQDN and port for a specific SIP
                 gateway.

                 A registrar is a server that accepts REGISTER requests and
                 places the information it receives in those requests into the
                 location service for the domain it handles.

                 Note: If the host corresponds to a domain name that is bound
                 to a SRV record, the port must be set to 0 for the unit to
                 perform DNS SRV queries; otherwise, only type A record
                 lookups will be used.

                 This configuration overrides the default configuration set in
                 the DefaultRegistrarServerHost variable if the
                 GwSpecificRegistration.EnableConfig variable is set to
                 'Enable'.


                 "
   DEFVAL        { "192.168.0.10:0" }
   ::= { gwSpecificRegistrationEntry 600 }


 -- End of table:SIP Gateway Specific Proxy

 -- ***************************************************************************
 
 -- Table:Registration Users

 -- ***************************************************************************
 
 registrationUsersTable OBJECT-TYPE
  SYNTAX        SEQUENCE OF RegistrationUsersEntry
  MAX-ACCESS    not-accessible
  STATUS        current
  DESCRIPTION " Registration Users

                This table holds a list of users to register.

                Note: Endpoint related registration can be specify in table
                UserAgent


                "
  ::= { registrationGroup 700 }
  registrationUsersEntry OBJECT-TYPE
   SYNTAX        RegistrationUsersEntry
   MAX-ACCESS    not-accessible
   STATUS        current
   DESCRIPTION " A row in table Registration Users. "
   INDEX         {
                   registrationUsersIndex
                 }

   ::= { registrationUsersTable 1 }

  RegistrationUsersEntry ::= SEQUENCE
  {
    registrationUsersIndex       Unsigned32,
    registrationUsersUsername    OCTET STRING,
    registrationUsersGatewayName OCTET STRING,
    registrationUsersDelete      INTEGER
  }

  -- Index:Index

  registrationUsersIndex OBJECT-TYPE
   SYNTAX        Unsigned32
   MAX-ACCESS    read-only
   STATUS        current
   DESCRIPTION " Index

                 Unique identifier of the row.
                 "
   ::= { registrationUsersEntry 100 }

  -- Columnar:User Name

  registrationUsersUsername OBJECT-TYPE
   SYNTAX        OCTET STRING ( SIZE(0..255) )
   MAX-ACCESS    read-write
   STATUS        current
   DESCRIPTION " User Name

                 A string that uniquely identifies this users in the domain.
                 "
   DEFVAL        { "" }
   ::= { registrationUsersEntry 200 }

  -- Columnar:Gateway

  registrationUsersGatewayName OBJECT-TYPE
   SYNTAX        OCTET STRING
   MAX-ACCESS    read-write
   STATUS        current
   DESCRIPTION " Gateway

                 Selects on which SIP gateway the user configuration is
                 applied. The value must match the gateway name as defined in
                 Gateway.Name.

                 The value 'all' means all gateways.


                 "
   DEFVAL        { "all" }
   ::= { registrationUsersEntry 250 }

  -- Row command:Delete

  registrationUsersDelete OBJECT-TYPE
   SYNTAX        INTEGER { noOp(0), delete(10) }
   MAX-ACCESS    read-write
   STATUS        current
   DESCRIPTION " Delete

                 Delete this row.
                 "
   DEFVAL        { noOp }
   ::= { registrationUsersEntry 300 }


 -- End of table:Registration Users

 -- Scalar:Behavior on Initial-Registration Reception

 behaviorOnInitialRegistrationReception OBJECT-TYPE
  SYNTAX        INTEGER { noRegistration(100) , endpointRegistration(200) ,
                unitRegistration(300) , unitAndEndpointRegistration(400) }
  MAX-ACCESS    read-write
  STATUS        current
  DESCRIPTION " Behavior on Initial-Registration Reception

                Configures the behavior upon reception of a 380 or 504
                carrying an XML body with a specified 'initial-registration'
                action.

                  * NoRegistration: No registration refresh are sent upon
                    reception of the message.
                  * EndpointRegistration: Registration refresh of the endpoint
                    associated with the call is sent upon reception of the
                    message.
                  * UnitRegistration: Registration refresh of all the
                    usernames configured as 'unit registration' are sent upon
                    reception of the message.
                  * UnitAndEndpointRegistration: Registration refresh of the
                    endpoint associated with the call and of all the usernames
                    configured as 'unit registration' are sent upon reception
                    of the message.

                If the registration(s) succeed, then the call is re-attempted.
                If the registration(s) fail, then the call is terminated.

                See also the 'RegistrationDelayOnInitialRegistrationReception'
                variable.


                "
  DEFVAL        { noRegistration }
  ::= { registrationGroup 900 }

 -- Scalar:Registration Delay on Initial-Registration Reception

 registrationDelayOnInitialRegistrationReception OBJECT-TYPE
  SYNTAX        Unsigned32 ( 0..5000 )
  MAX-ACCESS    read-write
  STATUS        current
  DESCRIPTION " Registration Delay on Initial-Registration Reception

                This variable is only used when
                BehaviorOnInitialRegistrationReception is configured to a
                value other than 'NoRegistration'. This variable configures
                the time interval between the unregistration confirmation (or
                final response) and the registration attempt that follows.

                Note: This variable only applies on registration refresh
                triggered by the BehaviorOnInitialRegistrationReception
                feature.

                This value is expressed in milliseconds (ms).

                See also the 'BehaviorOnInitialRegistrationReception'
                variable.


                "
  DEFVAL        { 0 }
  ::= { registrationGroup 1000 }

 -- ***************************************************************************
 
 -- Table:Registration Status

 -- ***************************************************************************
 
 registrationStatusTable OBJECT-TYPE
  SYNTAX            SEQUENCE OF RegistrationStatusEntry
  MAX-ACCESS        not-accessible
  STATUS            current
  DESCRIPTION     " Registration Status

                    This table holds a list of current registration.
                    "
  ::= { registrationGroup 10000 }
  registrationStatusEntry OBJECT-TYPE
   SYNTAX        RegistrationStatusEntry
   MAX-ACCESS    not-accessible
   STATUS        current
   DESCRIPTION " A row in table Registration Status. "
   INDEX         {
                   registrationStatusIndex
                 }

   ::= { registrationStatusTable 1 }

  RegistrationStatusEntry ::= SEQUENCE
  {
    registrationStatusIndex     Unsigned32,
    registrationStatusGateway   OCTET STRING,
    registrationStatusEndpoint  OCTET STRING,
    registrationStatusState     INTEGER,
    registrationStatusRegistrar OCTET STRING,
    registrationStatusUsername  OCTET STRING
  }

  -- Index:Index

  registrationStatusIndex OBJECT-TYPE
   SYNTAX        Unsigned32
   MAX-ACCESS    read-only
   STATUS        current
   DESCRIPTION " Index

                 Unique identifier of the row.
                 "
   ::= { registrationStatusEntry 100 }

  -- Columnar:Gateway

  registrationStatusGateway OBJECT-TYPE
   SYNTAX        OCTET STRING
   MAX-ACCESS    read-only
   STATUS        current
   DESCRIPTION " Gateway

                 The SIP gateway used to register.
                 "
   ::= { registrationStatusEntry 200 }

  -- Columnar:Endpoint

  registrationStatusEndpoint OBJECT-TYPE
   SYNTAX        OCTET STRING
   MAX-ACCESS    read-only
   STATUS        current
   DESCRIPTION " Endpoint

                 The endpoint related to this registration.

                 The variable is empty for generic user registration not
                 related to an endpoint.


                 "
   ::= { registrationStatusEntry 300 }

  -- Columnar:State

  registrationStatusState OBJECT-TYPE
   SYNTAX        INTEGER { unregistered(100) , registering(200) , registered
                 (300) , refreshing(400) , unregistering(500) , unreachable
                 (600) , authFailed(700) , rejected(800) , configError(900) ,
                 invalidResponse (1000) }
   MAX-ACCESS    read-only
   STATUS        current
   DESCRIPTION " State

                 The current state of the registration.

                   * Unregistered: The registration is not registered and
                     never tries to register. This case occurs if the network
                     interface used by the SIP gateway is not up or the unit/
                     endpoint is locked.
                   * Registering: The registration is currently trying to
                     register.
                   * Registered: The registration is successfully registered.
                   * Refreshing: The registration is trying to refresh.
                   * Unreachable: The last registration attempt failed because
                     the registrar is unreachable.
                   * AuthFailed: The last registration attempt failed because
                     authentication was not successful.
                   * Rejected: The last registration attempt failed because
                     the registrar rejects the registration.
                   * ConfigError: The last registration attempt failed because
                     it was badly configured. Check if the username to
                     register and the registrar host are not empty.
                   * InvalidResponse: The received 200 OK response contact
                     don't match the contact of the register. Or the 200 OK
                     response for an un-register contains contact.


                 "
   ::= { registrationStatusEntry 400 }

  -- Columnar:Registrar

  registrationStatusRegistrar OBJECT-TYPE
   SYNTAX        OCTET STRING
   MAX-ACCESS    read-only
   STATUS        current
   DESCRIPTION " Registrar

                 The host of the registrar currently used by the registration.
                 "
   ::= { registrationStatusEntry 500 }

  -- Columnar:Username

  registrationStatusUsername OBJECT-TYPE
   SYNTAX        OCTET STRING
   MAX-ACCESS    read-only
   STATUS        current
   DESCRIPTION " Username

                 The username currently used by the registration.
                 "
   ::= { registrationStatusEntry 600 }


 -- End of table:Registration Status

-- End of group:Registration Group

-- ****************************************************************************

-- Group:Transport Group

-- ****************************************************************************

transportGroup OBJECT IDENTIFIER
 ::= { sipEpMIBObjects 900 }
 -- Scalar:Persistent TLS Connection Port

 transportTlsPersistentBasePort OBJECT-TYPE
  SYNTAX        Unsigned32 ( 1025..64535 )
  MAX-ACCESS    read-write
  STATUS        current
  DESCRIPTION " Persistent TLS Connection Port

                Base port used to establish TLS persistent connections with
                SIP servers when the TLS transport is enabled.
                "
  DEFVAL        { 16000 }
  ::= { transportGroup 50 }

 -- Scalar:TLS Persistent Retry Interval

 transportTlsPersistentRetryInterval OBJECT-TYPE
  SYNTAX        Unsigned32 ( 5..3600 )
  MAX-ACCESS    read-write
  STATUS        current
  DESCRIPTION " TLS Persistent Retry Interval

                Time interval before retrying the establishment of a TLS
                persistent connection.

                This value is the interval that the device waits before
                retrying periodically to establish a TLS persistent connection
                using a single IP address or a FQDN. This timer is started
                when a TLS persistent connection goes down or fails to connect
                to the destination. The TLS persistent connect timeout applies
                only to TLS persistent connections.

                When the destination is a single IP address and the TLS
                persistent connection goes down or fails to establish, the
                timer is started. When the timer expires, the device attempts
                to re-establish the TLS persistent connection.

                When the destination is a FQDN and the TLS persistent
                connection goes down or fails to establish with the higher
                priority target received from a DNS answer, the timer is
                started and the lower priority targets are attempted. When the
                timer expires, a new DNS request is sent and depending on the
                DNS answer, the device retries to establish the TLS persistent
                connection with the higher priority target. The timer is
                unique for all TLS persistent connections using the same FQDN.
                This means that the timer is not restarted when a connection
                using a lower priority target fails while a connection using a
                higher priority target has already failed.

                This value is expressed in seconds (s).


                "
  DEFVAL        { 15 }
  ::= { transportGroup 75 }

 -- Scalar:Certificate Trust Level for TLS connections

 transportTlsCertificateTrustLevel OBJECT-TYPE
  SYNTAX        INTEGER { locallyTrusted(100) , ocspOptional(200) ,
                ocspMandatory(300) }
  MAX-ACCESS    read-write
  STATUS        current
  DESCRIPTION " Certificate Trust Level for TLS connections

                Define how a peer certificate is considered trusted for a TLS
                connection.

                  * LocallyTrusted: A certificate is considered trusted when
                    the certificate authority (CA) that signed the peer
                    certificate is present in the Cert.OthersCertificatesInfo
                    table. The certificate revocation status is not verified.
                  * OcspOptional: A certificate is considered trusted when it
                    is locally trusted and is not revoked by its certificate
                    authority (CA). The certificate revocation status is
                    queried using the Online Certificate Status Protocol
                    (OCSP). If the OCSP server is not available or the
                    verification status is unknown, the certificate is
                    considered trusted.
                  * OcspMandatory: A certificate is considered trusted when it
                    is locally trusted and is not revoked by its certificate
                    authority (CA). The certificate revocation status is
                    queried using the Online Certificate Status Protocol
                    (OCSP). If the OCSP server is not available or the
                    verification status is unknown, the certificate is
                    considered not trusted.


                "
  DEFVAL        { locallyTrusted }
  ::= { transportGroup 85 }

 -- ***************************************************************************
 
 -- Table:Transport Configuration

 -- ***************************************************************************
 
 transportConfigTable OBJECT-TYPE
  SYNTAX        SEQUENCE OF TransportConfigEntry
  MAX-ACCESS    not-accessible
  STATUS        current
  DESCRIPTION " Transport Configuration

                This table contains the informations pertaining to the
                supported transports. It is indexed by gateway name.

                Note that the transport used for the entire unit is always the
                transport configured in the first row of this table.
                Consequently when a transport is configured on a specific row
                (gateway), the configuration is also applied to all rows
                (gateways). This characteristic could possibly change when the
                unit will be able to support different transports.


                "
  ::= { transportGroup 100 }
  transportConfigEntry OBJECT-TYPE
   SYNTAX        TransportConfigEntry
   MAX-ACCESS    not-accessible
   STATUS        current
   DESCRIPTION " A row in table Transport Configuration. "
   INDEX         {
                   transportConfigGatewayName
                 }

   ::= { transportConfigTable 1 }

  TransportConfigEntry ::= SEQUENCE
  {
    transportConfigGatewayName        OCTET STRING,
    transportConfigRegistrationEnable MxEnableState,
    transportConfigContactEnable      MxEnableState,
    transportConfigUdpEnable          MxEnableState,
    transportConfigUdpQValue          OCTET STRING,
    transportConfigTcpEnable          MxEnableState,
    transportConfigTcpQValue          OCTET STRING,
    transportConfigTlsEnable          MxEnableState,
    transportConfigTlsQValue          OCTET STRING
  }

  -- Index:Gateway Name

  transportConfigGatewayName OBJECT-TYPE
   SYNTAX        OCTET STRING
   MAX-ACCESS    read-only
   STATUS        current
   DESCRIPTION " Gateway Name

                 String that identifies a SIP gateway in other tables.
                 "
   ::= { transportConfigEntry 100 }

  -- Columnar:Enable/Disable Transport Registration

  transportConfigRegistrationEnable OBJECT-TYPE
   SYNTAX        MxEnableState
   MAX-ACCESS    read-write
   STATUS        current
   DESCRIPTION " Enable/Disable Transport Registration

                 Indicates whether or not the SIP Gateway must include its
                 supported transports in its registrations.

                 If enabled, then the gateway registers with one contact for
                 each transport that is currently enabled. Each of these
                 contacts contains a 'transport' parameter.


                 "
   DEFVAL        { disable }
   ::= { transportConfigEntry 200 }

  -- Columnar:Enable/Disable Transport Contact

  transportConfigContactEnable OBJECT-TYPE
   SYNTAX        MxEnableState
   MAX-ACCESS    read-write
   STATUS        current
   DESCRIPTION " Enable/Disable Transport Contact

                 Indicates whether or not the SIP Gateway must include its
                 supported transport in all SIP messages that have the contact
                 header, except for the REGISTER message (see the
                 'RegistrationEnable' variable).

                 If enabled, then the gateway sends SIP messages with the
                 'transport' parameter in the contact header.

                 When secure transport is not selected, it is either set to
                 'transport=tcp' when TCP is enabled and UDP is disabled,
                 'transport=udp' when UDP is enabled and TCP disabled or no
                 transport parameter when both TCP and UDP are enabled. When
                 secure transport is selected, it is set to 'transport=tls'.


                 "
   DEFVAL        { disable }
   ::= { transportConfigEntry 300 }

  -- Columnar:Enable/Disable UDP transport

  transportConfigUdpEnable OBJECT-TYPE
   SYNTAX        MxEnableState
   MAX-ACCESS    read-write
   STATUS        current
   DESCRIPTION " Enable/Disable UDP transport

                 Enables or disables the UDP transport.

                 Note that the UDP and TLS transportS are mutually exclusive.
                 The TLS transport cannot be used with the UDP transport.


                 "
   DEFVAL        { enable }
   ::= { transportConfigEntry 400 }

  -- Columnar:UDP Qvalue

  transportConfigUdpQValue OBJECT-TYPE
   SYNTAX        OCTET STRING ( SIZE(0..5) )
   MAX-ACCESS    read-write
   STATUS        current
   DESCRIPTION " UDP Qvalue

                 Indicates the priority of the UDP transport.

                 A qvalue parameter is added to each contact. This only
                 applies if the transport-specific registration is enabled
                 (see 'TransportRegistrationEnable').

                 Qvalues give each transport a weight, indicating the degree
                 of preference for that transport. A higher value means higher
                 preference.

                 The format of the qvalue string must follow the RFC 3261 ABNF
                 (a floating point value between 0.000 and 1.000). If an empty
                 string is specified, no qvalue is set in the contacts.


                 "
   DEFVAL        { "" }
   ::= { transportConfigEntry 500 }

  -- Columnar:Enable/Disable TCP transport

  transportConfigTcpEnable OBJECT-TYPE
   SYNTAX        MxEnableState
   MAX-ACCESS    read-write
   STATUS        current
   DESCRIPTION " Enable/Disable TCP transport

                 Enables or disables the TCP transport.

                 Note that the TCP and TLS transports are mutually exclusive.
                 The TLS transport cannot be used with the TCP transport.


                 "
   DEFVAL        { disable }
   ::= { transportConfigEntry 600 }

  -- Columnar:TCP Qvalue

  transportConfigTcpQValue OBJECT-TYPE
   SYNTAX        OCTET STRING ( SIZE(0..5) )
   MAX-ACCESS    read-write
   STATUS        current
   DESCRIPTION " TCP Qvalue

                 Indicates the priority of the TCP transport.

                 A qvalue parameter is added to each contact. This only
                 applies if the transport-specific registration is enabled
                 (see 'TransportRegistrationEnable').

                 Qvalues give each transport a weight, indicating the degree
                 of preference for that transport. A higher value means higher
                 preference.

                 The format of the qvalue string must follow the RFC 3261 ABNF
                 (a floating point value between 0.000 and 1.000). If an empty
                 string is specified, no qvalue is set in the contacts.


                 "
   DEFVAL        { "" }
   ::= { transportConfigEntry 700 }

  -- Columnar:Enable/Disable TLS transport

  transportConfigTlsEnable OBJECT-TYPE
   SYNTAX        MxEnableState
   MAX-ACCESS    read-write
   STATUS        current
   DESCRIPTION " Enable/Disable TLS transport

                 Enables or disables the TLS transport.

                 Note that the TLS transport is exclusive to UDP and TCP
                 transport. The TLS transport cannot be used with the TCP or
                 UDP transport.


                 "
   DEFVAL        { disable }
   ::= { transportConfigEntry 800 }

  -- Columnar:TLS Qvalue

  transportConfigTlsQValue OBJECT-TYPE
   SYNTAX        OCTET STRING ( SIZE(0..5) )
   MAX-ACCESS    read-write
   STATUS        current
   DESCRIPTION " TLS Qvalue

                 Indicates the priority of the TLS transport.

                 A qvalue parameter is added to each contact. This only
                 applies if the transport-specific registration is enabled
                 (see 'TransportRegistrationEnable').

                 Qvalues give each transport a weight, indicating the degree
                 of preference for that transport. A higher value means higher
                 preference.

                 The format of the qvalue string must follow the RFC 3261 ABNF
                 (a floating point value between 0.000 and 1.000). If an empty
                 string is specified, no qvalue is set in the contacts.


                 "
   DEFVAL        { "" }
   ::= { transportConfigEntry 900 }


 -- End of table:Transport Configuration

 -- ***************************************************************************
 
 -- Table:TLS Persistent Connection Status

 -- ***************************************************************************
 
 tlsPersistentConnectionStatusTable OBJECT-TYPE
  SYNTAX        SEQUENCE OF TlsPersistentConnectionStatusEntry
  MAX-ACCESS    not-accessible
  STATUS        current
  DESCRIPTION " TLS Persistent Connection Status

                This table holds the status of the TLS persistent connections.
                "
  ::= { transportGroup 10000 }
  tlsPersistentConnectionStatusEntry OBJECT-TYPE
   SYNTAX        TlsPersistentConnectionStatusEntry
   MAX-ACCESS    not-accessible
   STATUS        current
   DESCRIPTION " A row in table TLS Persistent Connection Status. "
   INDEX         {
                   tlsPersistentConnectionStatusIndex
                 }

   ::= { tlsPersistentConnectionStatusTable 1 }

  TlsPersistentConnectionStatusEntry ::= SEQUENCE
  {
    tlsPersistentConnectionStatusIndex            Unsigned32,
    tlsPersistentConnectionStatusGateway          OCTET STRING,
    tlsPersistentConnectionStatusLocalPort        MxAdvancedIpPort,
    tlsPersistentConnectionStatusRemoteHost       OCTET STRING,
    tlsPersistentConnectionStatusRemoteHostIpAddr OCTET STRING,
    tlsPersistentConnectionStatusState            INTEGER
  }

  -- Index:Index

  tlsPersistentConnectionStatusIndex OBJECT-TYPE
   SYNTAX        Unsigned32
   MAX-ACCESS    read-only
   STATUS        current
   DESCRIPTION " Index

                 Unique identifier of the row.
                 "
   ::= { tlsPersistentConnectionStatusEntry 100 }

  -- Columnar:Gateway

  tlsPersistentConnectionStatusGateway OBJECT-TYPE
   SYNTAX        OCTET STRING
   MAX-ACCESS    read-only
   STATUS        current
   DESCRIPTION " Gateway

                 The SIP gateway used to register.
                 "
   ::= { tlsPersistentConnectionStatusEntry 200 }

  -- Columnar:Local Port

  tlsPersistentConnectionStatusLocalPort OBJECT-TYPE
   SYNTAX        MxAdvancedIpPort
   MAX-ACCESS    read-only
   STATUS        current
   DESCRIPTION " Local Port

                 Local port used by the TLS persistent connection.
                 "
   ::= { tlsPersistentConnectionStatusEntry 300 }

  -- Columnar:Remote Host

  tlsPersistentConnectionStatusRemoteHost OBJECT-TYPE
   SYNTAX        OCTET STRING
   MAX-ACCESS    read-only
   STATUS        current
   DESCRIPTION " Remote Host

                 The remote host used to establish the TLS persistent
                 connection. The remote host can be a host name or an IP
                 address of the proxy, outbound proxy or registrar.
                 "
   ::= { tlsPersistentConnectionStatusEntry 400 }

  -- Columnar:Remote Host Ip Address

  tlsPersistentConnectionStatusRemoteHostIpAddr OBJECT-TYPE
   SYNTAX        OCTET STRING
   MAX-ACCESS    read-only
   STATUS        current
   DESCRIPTION " Remote Host Ip Address

                 The resolved IP address of the remote host used to establish
                 the TLS persistent connection.
                 "
   ::= { tlsPersistentConnectionStatusEntry 450 }

  -- Columnar:State

  tlsPersistentConnectionStatusState OBJECT-TYPE
   SYNTAX        INTEGER { up(100) , down(200) , waitingShutdown(300) ,
                 waitingUp(400) }
   MAX-ACCESS    read-only
   STATUS        current
   DESCRIPTION " State

                 The current state of the TLS persistent connection.

                   * Up: The TLS connection is established and ready to be
                     used.
                   * Down: The TLS connection is not established.
                   * WaitingShutdown: The TLS connection is established but in
                     a graceful shutdown.
                   * WaitingUp: The TLS connection is established not yet
                     ready to be used.


                 "
   ::= { tlsPersistentConnectionStatusEntry 500 }


 -- End of table:TLS Persistent Connection Status

-- End of group:Transport Group

-- ****************************************************************************

-- Group:Penalty Box

-- ****************************************************************************

penaltyBoxGroup OBJECT IDENTIFIER
 ::= { sipEpMIBObjects 1000 }
 -- Scalar:Penalty Box Enable

 penaltyBoxEnable OBJECT-TYPE
  SYNTAX        MxEnableState
  MAX-ACCESS    read-write
  STATUS        current
  DESCRIPTION " Penalty Box Enable

                Indicates whether the unit uses the penalty box feature.

                The penalty box feature is used when a given host FQDN
                resolves to a non-responding address. When the address times
                out, it is put into the penalty box for a given amount of
                time. During that time, the address in question is considered
                as 'non-responding' for all requests.

                This feature is most useful when using DNS requests returning
                multiple or varying server addresses. It makes sure that, when
                a host is down, users wait a minimal amount of time before
                trying a secondary host.

                The penalty box is always 'active'. This means that even if
                the feature is disabled, IP addresses are marked as invalid,
                but they are still tried. The advantage is that when the
                feature is enabled, IP addresses that were already marked as
                invalid are instantly put into the penalty box.

                When enabled, this feature takes effect immediately on the
                next call attempt.

                The penalty box feature is applied only when using UDP or TCP
                connections established with a FQDN. A similar penalty box
                feature for the TLS connections is available via the
                SipEp.TransportTlsPersistentRetryInterval variable.

                See also 'PenaltyBoxTime'.


                "
  DEFVAL        { disable }
  ::= { penaltyBoxGroup 100 }

 -- Scalar:Penalty Box Time

 penaltyBoxTime OBJECT-TYPE
  SYNTAX        Unsigned32 ( 30..7200 )
  MAX-ACCESS    read-write
  STATUS        current
  DESCRIPTION " Penalty Box Time

                Amount of time that a host spends in the penalty box.

                An IP address is put into the penalty box for the current
                'PenaltyBoxEnable'. Changing the 'PenaltyBoxTime' does not
                affect IP addresses that are already in the penalty box. In
                other words, the 'PenaltyBoxTime' only affects new entries in
                the penalty box.

                The penalty box feature is applied only when the
                'non-responding' destination timeout a non-persistent
                connection. A similar penalty box feature for the TLS
                persistent connections is available via the
                SipEp.TransportTlsPersistentRetryInterval variable.

                This value is expressed in seconds (s).

                Also see 'PenaltyBoxEnable'.


                "
  DEFVAL        { 300 }
  ::= { penaltyBoxGroup 200 }

-- End of group:Penalty Box

-- ****************************************************************************

-- Group:Error Mapping Group

-- ****************************************************************************

errorMappingGroup OBJECT IDENTIFIER
 ::= { sipEpMIBObjects 1100 }
 -- ***************************************************************************
 
 -- Table:Error Mapping SIP To Cause

 -- ***************************************************************************
 
 errorMappingSipToCauseTable OBJECT-TYPE
  SYNTAX        SEQUENCE OF ErrorMappingSipToCauseEntry
  MAX-ACCESS    not-accessible
  STATUS        current
  DESCRIPTION " Error Mapping SIP To Cause

                This table allow user to override the default mapping for SIP
                code to ISDN cause.

                The default mapping is defined in RFC3398


                "
  ::= { errorMappingGroup 100 }
  errorMappingSipToCauseEntry OBJECT-TYPE
   SYNTAX        ErrorMappingSipToCauseEntry
   MAX-ACCESS    not-accessible
   STATUS        current
   DESCRIPTION " A row in table Error Mapping SIP To Cause. "
   INDEX         {
                   errorMappingSipToCauseSipCode
                 }

   ::= { errorMappingSipToCauseTable 1 }

  ErrorMappingSipToCauseEntry ::= SEQUENCE
  {
    errorMappingSipToCauseSipCode Unsigned32,
    errorMappingSipToCauseCause   Unsigned32,
    errorMappingSipToCauseDelete  INTEGER
  }

  -- Index:SIP code

  errorMappingSipToCauseSipCode OBJECT-TYPE
   SYNTAX        Unsigned32 ( 400..699 )
   MAX-ACCESS    read-only
   STATUS        current
   DESCRIPTION " SIP code

                 SIP code to map to a cause. It's also the unique identifier
                 of the row.

                 SIP code:

                   * 400: Bad Request
                   * 401: Unauthorized
                   * 402: Payment required
                   * 403: Forbidden
                   * 404: Not found
                   * 405: Method not allowed
                   * 406: Not acceptable
                   * 407: Proxy authentication required
                   * 408: Request timeout
                   * 410: Gone
                   * 413: Request Entity too long
                   * 414: Request-URI too long
                   * 415: Unsupported media type
                   * 416: Unsupported URI Scheme
                   * 420: Bad extension
                   * 421: Extension Required
                   * 423: Interval Too Brief
                   * 480: Temporarily unavailable
                   * 481: Call/Transaction Does not Exist
                   * 482: Loop Detected
                   * 483: Too many hops
                   * 484: Address incomplete
                   * 485: Ambiguous
                   * 486: Busy here
                   * 500: Server internal error
                   * 501: Not implemented
                   * 502: Bad gateway
                   * 503: Service unavailable
                   * 504: Server time-out
                   * 504: Version Not Supported
                   * 513: Message Too Large
                   * 600: Busy everywhere
                   * 603: Decline
                   * 604: Does not exist anywhere


                 "
   ::= { errorMappingSipToCauseEntry 100 }

  -- Columnar:Cause

  errorMappingSipToCauseCause OBJECT-TYPE
   SYNTAX        Unsigned32 ( 1..127 )
   MAX-ACCESS    read-write
   STATUS        current
   DESCRIPTION " Cause

                 Cause to map the the SIP code.

                 The cause specified in Q.931 are:

                 Normal event:

                   * 1: Unassigned (unallocated) number.
                   * 2: No route to specified transit network.
                   * 3: No route to destination.
                   * 6: Channel unacceptable.
                   * 7: Call awarded and being delivered in an established
                     channel.
                   * 17: User busy.
                   * 18: No user responding.
                   * 19: User alerting, no answer.
                   * 20: Subscriber absent.
                   * 21: Call rejected.
                   * 22: Number changed.
                   * 23: Redirection to new destination.
                   * 26: Non-selected user clearing.
                   * 27: Destination out of order.
                   * 28: Invalid number format (incomplete number).
                   * 29: Facility rejected.
                   * 30: Response to STATUS ENQUIRY.
                   * 31: Normal, unspecified.

                 Resource unavailable:

                   * 34: No circuit/channel available.
                   * 38: Network out of order.
                   * 41: Temporary failure.
                   * 42: Switching equipment congestion.
                   * 43: Access information discarded.
                   * 44: Requested circuit/channel not available.
                   * 47: Resource unavailable, unspecified.

                 Service or option not available:

                   * 55: Incoming calls barred within CUG.
                   * 57: Bearer capability not authorized.
                   * 58: Bearer capability not presently available.
                   * 63: Service or option not available, unspecified.

                 Service or option not implemented:

                   * 65: Bearer capability not implemented.
                   * 66: Channel type not implemented.
                   * 69: Requested facility not implemented.
                   * 70: Only restricted digital information bearer capability
                     is available.
                   * 79: Service or option not implemented, unspecified.

                 Invalid message:

                   * 81: Invalid call reference value.
                   * 82: Identified channel does not exist.
                   * 83: A suspended call exists, but this call identity does
                     not.
                   * 84: Call identity in use.
                   * 85: No call suspended.
                   * 86: Call having the requested call identity has been
                     cleared.
                   * 87: user not member of CUG.
                   * 88: Incompatible destination.
                   * 91: Invalid transit network selection.
                   * 95: Invalid message, unspecified.

                 Protocol error:

                   * 96: Mandatory information element is missing
                   * 97: Message type non-existent or not implemented
                   * 98: Message not compatible with call state or message
                     type non-existent or not implemented
                   * 99: Information element non-existent or not implemented
                   * 100: Invalid information element contents
                   * 101: Message not compatible with call state
                   * 102: Recovery on time expiry
                   * 111: Protocol error, unspecified

                 Interworking:

                   * 127: Interworking, unspecified


                 "
   DEFVAL        { 127 }
   ::= { errorMappingSipToCauseEntry 200 }

  -- Row command:Delete

  errorMappingSipToCauseDelete OBJECT-TYPE
   SYNTAX        INTEGER { noOp(0), delete(10) }
   MAX-ACCESS    read-write
   STATUS        current
   DESCRIPTION " Delete

                 Delete this row.
                 "
   DEFVAL        { noOp }
   ::= { errorMappingSipToCauseEntry 300 }


 -- End of table:Error Mapping SIP To Cause

 -- ***************************************************************************
 
 -- Table:Error Mapping Cause To SIP

 -- ***************************************************************************
 
 errorMappingCauseToSipTable OBJECT-TYPE
  SYNTAX        SEQUENCE OF ErrorMappingCauseToSipEntry
  MAX-ACCESS    not-accessible
  STATUS        current
  DESCRIPTION " Error Mapping Cause To SIP

                This table allow user to override the default mapping for ISDN
                cause to SIP.

                The default mapping is defined in RFC3398


                "
  ::= { errorMappingGroup 300 }
  errorMappingCauseToSipEntry OBJECT-TYPE
   SYNTAX        ErrorMappingCauseToSipEntry
   MAX-ACCESS    not-accessible
   STATUS        current
   DESCRIPTION " A row in table Error Mapping Cause To SIP. "
   INDEX         {
                   errorMappingCauseToSipCause
                 }

   ::= { errorMappingCauseToSipTable 1 }

  ErrorMappingCauseToSipEntry ::= SEQUENCE
  {
    errorMappingCauseToSipCause   Unsigned32,
    errorMappingCauseToSipSipCode Unsigned32,
    errorMappingCauseToSipDelete  INTEGER
  }

  -- Index:Cause

  errorMappingCauseToSipCause OBJECT-TYPE
   SYNTAX        Unsigned32 ( 1..127 )
   MAX-ACCESS    read-only
   STATUS        current
   DESCRIPTION " Cause

                 Cause to map the the SIP code. It's also the unique
                 identificator of the row.

                 The cause specified in Q.931 are:

                 Normal event:

                   * 1: Unassigned (unallocated) number.
                   * 2: No route to specified transit network.
                   * 3: No route to destination.
                   * 6: Channel unacceptable.
                   * 7: Call awarded and being delivered in an established
                     channel.
                   * 17: User busy.
                   * 18: No user responding.
                   * 19: User alerting, no answer.
                   * 20: Subscriber absent.
                   * 21: Call rejected.
                   * 22: Number changed.
                   * 23: Redirection to new destination.
                   * 26: Non-selected user clearing.
                   * 27: Destination out of order.
                   * 28: Invalid number format (incomplete number).
                   * 29: Facility rejected.
                   * 30: Response to STATUS ENQUIRY.
                   * 31: Normal, unspecified.

                 Resource unavailable:

                   * 34: No circuit/channel available.
                   * 38: Network out of order.
                   * 41: Temporary failure.
                   * 42: Switching equipment congestion.
                   * 43: Access information discarded.
                   * 44: Requested circuit/channel not available.
                   * 47: Resource unavailable, unspecified.

                 Service or option not available:

                   * 55: Incoming calls barred within CUG.
                   * 57: Bearer capability not authorized.
                   * 58: Bearer capability not presently available.
                   * 63: Service or option not available, unspecified.

                 Service or option not implemented:

                   * 65: Bearer capability not implemented.
                   * 66: Channel type not implemented.
                   * 69: Requested facility not implemented.
                   * 70: Only restricted digital information bearer capability
                     is available.
                   * 79: Service or option not implemented, unspecified.

                 Invalid message:

                   * 81: Invalid call reference value.
                   * 82: Identified channel does not exist.
                   * 83: A suspended call exists, but this call identity does
                     not.
                   * 84: Call identity in use.
                   * 85: No call suspended.
                   * 86: Call having the requested call identity has been
                     cleared.
                   * 87: user not member of CUG.
                   * 88: Incompatible destination.
                   * 91: Invalid transit network selection.
                   * 95: Invalid message, unspecified.

                 Protocol error:

                   * 96: Mandatory information element is missing
                   * 97: Message type non-existent or not implemented
                   * 98: Message not compatible with call state or message
                     type non-existent or not implemented
                   * 99: Information element non-existent or not implemented
                   * 100: Invalid information element contents
                   * 101: Message not compatible with call state
                   * 102: Recovery on time expiry
                   * 111: Protocol error, unspecified

                 Interworking:

                   * 127: Interworking, unspecified


                 "
   ::= { errorMappingCauseToSipEntry 100 }

  -- Columnar:SIP code

  errorMappingCauseToSipSipCode OBJECT-TYPE
   SYNTAX        Unsigned32 ( 400..699 )
   MAX-ACCESS    read-write
   STATUS        current
   DESCRIPTION " SIP code

                 SIP code to map to a cause.

                 SIP code:

                   * 400: Bad Request
                   * 401: Unauthorized
                   * 402: Payment required
                   * 403: Forbidden
                   * 404: Not found
                   * 405: Method not allowed
                   * 406: Not acceptable
                   * 407: Proxy authentication required
                   * 408: Request timeout
                   * 410: Gone
                   * 413: Request Entity too long
                   * 414: Request-URI too long
                   * 415: Unsupported media type
                   * 416: Unsupported URI Scheme
                   * 420: Bad extension
                   * 421: Extension Required
                   * 423: Interval Too Brief
                   * 480: Temporarily unavailable
                   * 481: Call/Transaction Does not Exist
                   * 482: Loop Detected
                   * 483: Too many hops
                   * 484: Address incomplete
                   * 485: Ambiguous
                   * 486: Busy here
                   * 500: Server internal error
                   * 501: Not implemented
                   * 502: Bad gateway
                   * 503: Service unavailable
                   * 504: Server time-out
                   * 504: Version Not Supported
                   * 513: Message Too Large
                   * 600: Busy everywhere
                   * 603: Decline
                   * 604: Does not exist anywhere


                 "
   DEFVAL        { 500 }
   ::= { errorMappingCauseToSipEntry 200 }

  -- Row command:Delete

  errorMappingCauseToSipDelete OBJECT-TYPE
   SYNTAX        INTEGER { noOp(0), delete(10) }
   MAX-ACCESS    read-write
   STATUS        current
   DESCRIPTION " Delete

                 Delete this row.
                 "
   DEFVAL        { noOp }
   ::= { errorMappingCauseToSipEntry 300 }


 -- End of table:Error Mapping Cause To SIP

 -- Scalar:Reason Header Support

 reasonHeaderSupport OBJECT-TYPE
  SYNTAX        INTEGER { none(100) , sendQ850(200) , receiveQ850(300) ,
                sendReceiveQ850(400) }
  MAX-ACCESS    read-write
  STATUS        current
  DESCRIPTION " Reason Header Support

                Indicates whether or not the unit uses the SIP reason header.

                  * None: Silently ignore any incoming reason headers and do
                    not send the reason header.
                  * SendQ850: Silently ignore incoming reason codes and send
                    the SIP reason code when the original Q.850 code is
                    available. The reason code sent is not affected by the
                    entries in the ErrorMappingSipToCause table.
                  * ReceiveQ850: Use the incoming Q.850 reason cause header.
                    When received, the reason code supersedes any entries in
                    the ErrorMappingSipToCause table.
                  * SendReceiveQ850: Use the incoming Q.850 reason cause
                    header and send the SIP reason code when the original
                    Q.850 code is available. When received, the reason code
                    supersedes any entries in the ErrorMappingSipToCause
                    table. The reason code sent is not affected by the entries
                    in the ErrorMappingSipToCause table.


                "
  DEFVAL        { none }
  ::= { errorMappingGroup 500 }

-- End of group:Error Mapping Group

-- ****************************************************************************

-- Group:SIP Keep Alive

-- ****************************************************************************

sipKeepAliveGroup OBJECT IDENTIFIER
 ::= { sipEpMIBObjects 1300 }
 -- Scalar:Sip Keep Alive Method

 sipKeepAliveMethod OBJECT-TYPE
  SYNTAX        INTEGER { none(100) , sipOptions(200) , ping(300) }
  MAX-ACCESS    read-write
  STATUS        current
  DESCRIPTION " Sip Keep Alive Method

                Method used to perform the SIP keep alive.

                  * None: No keep alive is performed.
                  * SipOptions: SIP OPTIONS are sent periodically for each
                    gateway to the corresponding server. Any response received
                    from the server means that it is reachable. No additional
                    processing is performed on the response. If no response is
                    received after the retransmission timer expires
                    (configurable via the variable
                    'InteropTransmissionTimeout'), the gateway considers the
                    server as unreachable. In this case, any call attempt
                    through the gateway is refused. SIP OPTIONS are still sent
                    when the server is unreachable and as soon as it becomes
                    reachable again, new calls are allowed.
                  * Ping: A Ping is sent periodically for each gateway to the
                    corresponding server. The response received from the
                    server means that it is reachable. If no response is
                    received after the retransmission timer expires
                    (sipTransmissionTimeout), the gateway considers the server
                    as unreachable. In this case, any call attempt through the
                    gateway is refused. The Pings are still sent when the
                    server is unreachable and as soon as it becomes reachable
                    again, new calls are allowed.


                "
  DEFVAL        { none }
  ::= { sipKeepAliveGroup 100 }

 -- Scalar:SIP Keep Alive Interval

 sipKeepAliveInterval OBJECT-TYPE
  SYNTAX        Unsigned32 ( 1..3600 )
  MAX-ACCESS    read-write
  STATUS        current
  DESCRIPTION " SIP Keep Alive Interval

                Interval at which Sip Keep Alive requests using SIP OPTIONS or
                Ping are sent to verify the server status.

                This value is expressed in seconds (s).


                "
  DEFVAL        { 30 }
  ::= { sipKeepAliveGroup 200 }

 -- Scalar:Sip Keep Alive Destination

 sipKeepAliveDestination OBJECT-TYPE
  SYNTAX        INTEGER { firstSipDestination(100) , alternateDestination(200)
                }
  MAX-ACCESS    read-write
  STATUS        current
  DESCRIPTION " Sip Keep Alive Destination

                Determines the behaviour of the device when performing the
                keep alive action.

                  * FirstSipDestination: Perform the keep alive action through
                    the first SIP destination. This corresponds to the
                    outbound proxy host when specified, otherwise it is the
                    proxy host.
                  * AlternateDestination: Perform the keep alive action
                    through the alternate destination target (refer to the
                    variable 'GwKeepAliveAlternateDestination').


                "
  DEFVAL        { firstSipDestination }
  ::= { sipKeepAliveGroup 300 }

 -- ***************************************************************************
 
 -- Table:SIP Gateway Keep Alive Alternate Destination

 -- ***************************************************************************
 
 gwKeepAliveAlternateDestinationTable OBJECT-TYPE
  SYNTAX        SEQUENCE OF GwKeepAliveAlternateDestinationEntry
  MAX-ACCESS    not-accessible
  STATUS        current
  DESCRIPTION " SIP Gateway Keep Alive Alternate Destination

                A table of Keep Alive destination alternate target indexed by
                the SIP gateway name. It is used to override the default value
                when the SipKeepAliveDestination variable is set to
                'AlternateDestination'.
                "
  ::= { sipKeepAliveGroup 400 }
  gwKeepAliveAlternateDestinationEntry OBJECT-TYPE
   SYNTAX        GwKeepAliveAlternateDestinationEntry
   MAX-ACCESS    not-accessible
   STATUS        current
   DESCRIPTION " A row in table SIP Gateway Keep Alive Alternate Destination.
                 "
   INDEX         {
                   gwKeepAliveAlternateDestinationGatewayName
                 }

   ::= { gwKeepAliveAlternateDestinationTable 1 }

  GwKeepAliveAlternateDestinationEntry ::= SEQUENCE
  {
    gwKeepAliveAlternateDestinationGatewayName          OCTET STRING,
    gwKeepAliveAlternateDestinationAlternateDestination MxIpHostNamePort
  }

  -- Index:Gateway Name

  gwKeepAliveAlternateDestinationGatewayName OBJECT-TYPE
   SYNTAX        OCTET STRING
   MAX-ACCESS    read-only
   STATUS        current
   DESCRIPTION " Gateway Name

                 String that identifies a SIP gateway in other tables.
                 "
   ::= { gwKeepAliveAlternateDestinationEntry 100 }

  -- Columnar:SIP Gateway Keep Alive Alternate Destination

  gwKeepAliveAlternateDestinationAlternateDestination OBJECT-TYPE
   SYNTAX        MxIpHostNamePort
   MAX-ACCESS    read-write
   STATUS        current
   DESCRIPTION " SIP Gateway Keep Alive Alternate Destination

                 Alternate destination target server FQDN and port for a
                 specific SIP gateway.
                 "
   DEFVAL        { "192.168.0.10:0" }
   ::= { gwKeepAliveAlternateDestinationEntry 200 }


 -- End of table:SIP Gateway Keep Alive Alternate Destination

-- End of group:SIP Keep Alive

-- ****************************************************************************

-- Group:PRACK Group

-- ****************************************************************************

prackGroup OBJECT IDENTIFIER
 ::= { sipEpMIBObjects 1400 }
 -- Scalar:UAS PRACK Support

 uasPrackSupport OBJECT-TYPE
  SYNTAX        INTEGER { unsupported(200) , supported(300) }
  MAX-ACCESS    read-write
  STATUS        current
  DESCRIPTION " UAS PRACK Support

                Determines the support of RFC 3262 (PRACK) when acting as a
                user agent server.

                  * Unsupported: The option tag '100rel' is ignored if present
                    in the Supported or Required headers of received initial
                    INVITEs and provisional responses are not sent reliably as
                    per RFC 3261.
                  * Supported: If the option tag '100rel' is present in the
                    Supported or Required header of initial received INVITEs,
                    provisional responses are sent reliably as per RFC 3262 by
                    adding the option tag '100rel' to the Require header.

                Receiving an UPDATE request to negotiate 'early media' is
                supported only if UasPrackSupport is set to 'Supported'.


                "
  DEFVAL        { unsupported }
  ::= { prackGroup 100 }

 -- Scalar:UAC PRACK Support

 uacPrackSupport OBJECT-TYPE
  SYNTAX        INTEGER { unsupported(200) , supported(300) , required(400) }
  MAX-ACCESS    read-write
  STATUS        current
  DESCRIPTION " UAC PRACK Support

                Determines the support of RFC 3262 (PRACK) when acting as a
                user agent client.

                  * Unsupported: The option tag '100rel' is not added in the
                    Supported or Required headers of sent INVITEs as per RFC
                    3261. If the provisional response contains a 'Require'
                    header field with the option tag '100rel', the indication
                    is ignored and no PRACK are sent.
                  * Supported: The option tag '100rel' is added to the
                    Supported header of sent initial INVITEs as per RFC 3262.
                    If the received provisional response contains a Require
                    header field with the option tag '100rel', the response is
                    to be sent reliably using the PRACK method.
                  * Required: The option tag '100rel' is added to the Require
                    header of sent initial INVITEs as per RFC 3262. If the
                    received provisional response contains a Require header
                    field with the option tag '100rel', the response is to be
                    sent reliably using the PRACK method.


                "
  DEFVAL        { unsupported }
  ::= { prackGroup 200 }

-- End of group:PRACK Group

-- ****************************************************************************

-- Group:Offer and Answer Group

-- ****************************************************************************

offerAnswerGroup OBJECT IDENTIFIER
 ::= { sipEpMIBObjects 1500 }
 -- Scalar:Answer Codec Negotiation

 answerCodecNegotiation OBJECT-TYPE
  SYNTAX        INTEGER { allCommonLocalPriority(100) ,
                firstCommonLocalPriority(200) , allCommonPeerPriority(300) ,
                firstCommonPeerPriority(400) }
  MAX-ACCESS    read-write
  STATUS        current
  DESCRIPTION " Answer Codec Negotiation

                Defines the codec negotiation rule when generating a SDP
                answer.

                  * AllCommonLocalPriority : When generating an answer to an
                    offered session, all common codecs are listed in the local
                    order of priority. The local priority is defined for each
                    codec in the Mipt service.
                  * FirstCommonLocalPriority : When generating an answer to an
                    offered session, only the first common codec with the
                    higher local priority is listed. The local priority is
                    defined for each codec in the Mipt service.
                  * AllCommonPeerPriority : When generating an answer to an
                    offered session, all common codecs are listed. The codecs
                    order is the same as in the peer offer.
                  * FirstCommonPeerPriority : When generating an answer to an
                    offered session, only the first common codec is listed.
                    The codecs order is the same as in the peer offer.


                "
  DEFVAL        { allCommonLocalPriority }
  ::= { offerAnswerGroup 100 }

-- End of group:Offer and Answer Group

-- ****************************************************************************

-- Group:Call Diversion Group

-- ****************************************************************************

diversionGroup OBJECT IDENTIFIER
 ::= { sipEpMIBObjects 1600 }
 -- ***************************************************************************
 
 -- Table:Diversion Configuration

 -- ***************************************************************************
 
 diversionConfigTable OBJECT-TYPE
  SYNTAX        SEQUENCE OF DiversionConfigEntry
  MAX-ACCESS    not-accessible
  STATUS        current
  DESCRIPTION " Diversion Configuration

                A table of the call diversion configuration indexed by the SIP
                gateway name.
                "
  ::= { diversionGroup 100 }
  diversionConfigEntry OBJECT-TYPE
   SYNTAX        DiversionConfigEntry
   MAX-ACCESS    not-accessible
   STATUS        current
   DESCRIPTION " A row in table Diversion Configuration. "
   INDEX         {
                   diversionConfigGatewayName
                 }

   ::= { diversionConfigTable 1 }

  DiversionConfigEntry ::= SEQUENCE
  {
    diversionConfigGatewayName OCTET STRING,
    diversionConfigMethod      INTEGER
  }

  -- Index:Gateway Name

  diversionConfigGatewayName OBJECT-TYPE
   SYNTAX        OCTET STRING
   MAX-ACCESS    read-only
   STATUS        current
   DESCRIPTION " Gateway Name

                 String that identifies a SIP gateway in other tables.
                 "
   ::= { diversionConfigEntry 100 }

  -- Columnar:Call Diversion Method

  diversionConfigMethod OBJECT-TYPE
   SYNTAX        INTEGER { none(100) , diversionHeader(200) }
   MAX-ACCESS    read-write
   STATUS        current
   DESCRIPTION " Call Diversion Method

                 Selects the SIP method used to receive/send call diversion
                 information in an INVITE.

                   * None: No diversion information is sent in SIP messages.
                   * DiversionHeader: The SIP gateway supports the SIP header
                     'Diversion' (RFC 5806) in received and sent INVITEs, as
                     well as in 302 messages.


                 "
   DEFVAL        { none }
   ::= { diversionConfigEntry 200 }


 -- End of table:Diversion Configuration

-- End of group:Call Diversion Group

-- ****************************************************************************

-- Group:DNS Group

-- ****************************************************************************

dnsGroup OBJECT IDENTIFIER
 ::= { sipEpMIBObjects 1700 }
 -- Scalar:Supported DNS Queries

 supportedDnsQueries OBJECT-TYPE
  SYNTAX        INTEGER { address(100) , srv(200) , naptr(300) }
  MAX-ACCESS    read-write
  STATUS        current
  DESCRIPTION " Supported DNS Queries

                Specify the type of DNS queries that the SipEp service
                supports and uses.

                  * Address: Sends only Address requests (type A).
                  * Srv: Sends a Service request (type SRV) first and then
                    Address requests (type A) if needed.
                  * Naptr: Sends a Naming Authority Pointer request (type
                    NAPTR) first and then Service requests (type SRV) or
                    Address requests (type A) as needed.


                "
  DEFVAL        { naptr }
  ::= { dnsGroup 100 }

-- End of group:DNS Group

-- ****************************************************************************

-- Group:Message Waiting Indication

-- ****************************************************************************

messageWaitingIndication OBJECT IDENTIFIER
 ::= { sipEpMIBObjects 1800 }
 -- Scalar:Default Static Messaging Host

 defaultStaticMessagingHost OBJECT-TYPE
  SYNTAX        MxIpHostNamePort
  MAX-ACCESS    read-write
  STATUS        current
  DESCRIPTION " Default Static Messaging Host

                Messaging server FQDN and port.

                A Messaging system host is a server that accepts MWI SUBSCRIBE
                requests and places the information it receives in those
                requests into the location service for the domain it handles.

                Note: If the host corresponds to a domain name that is bound
                to a SRV record, the port must be set to 0 for the unit to
                perform DNS SRV queries; otherwise only type A record lookups
                will be used.

                If a specific configuration is set in the
                GwSpecificMwi.MessagingHost variable and the
                GwSpecificMwi.EnableConfig variable is set to 'Enable', then
                it overrides the current default configuration.


                "
  DEFVAL        { "192.168.10.10:0" }
  ::= { messageWaitingIndication 100 }

 -- Scalar:Default Username in Request-URI Enable

 defaultUsernameInRequestUriEnable OBJECT-TYPE
  SYNTAX        MxEnableState
  MAX-ACCESS    read-write
  STATUS        current
  DESCRIPTION " Default Username in Request-URI Enable

                Indicates whether or not the unit adds the username in the
                request URI of MWI SUBSCRIBE requests.

                  * enable: The unit adds the username in the Request-URI of
                    sent MWI SUBSCRIBE requests.
                  * disable: No username in Request-URI of MWI SUBSCRIBE
                    requests sent by the unit.

                If a specific configuration is set in the
                GwSpecificMwi.UsernameInRequestUriEnable variable and the
                GwSpecificMwi.EnableConfig variable is set to 'Enable', then
                it overrides the current default configuration.


                "
  DEFVAL        { disable }
  ::= { messageWaitingIndication 110 }

 -- ***************************************************************************
 
 -- Table:SIP Gateway Specific MWI

 -- ***************************************************************************
 
 gwSpecificMwiTable OBJECT-TYPE
  SYNTAX        SEQUENCE OF GwSpecificMwiEntry
  MAX-ACCESS    not-accessible
  STATUS        current
  DESCRIPTION " SIP Gateway Specific MWI

                A table of the MWI subscription configuration indexed by the
                SIP gateway name. It is used to override the default value.
                "
  ::= { messageWaitingIndication 200 }
  gwSpecificMwiEntry OBJECT-TYPE
   SYNTAX        GwSpecificMwiEntry
   MAX-ACCESS    not-accessible
   STATUS        current
   DESCRIPTION " A row in table SIP Gateway Specific MWI. "
   INDEX         {
                   gwSpecificMwiGatewayName
                 }

   ::= { gwSpecificMwiTable 1 }

  GwSpecificMwiEntry ::= SEQUENCE
  {
    gwSpecificMwiGatewayName                OCTET STRING,
    gwSpecificMwiEnableConfig               MxEnableState,
    gwSpecificMwiMessagingHost              MxIpHostNamePort,
    gwSpecificMwiUsernameInRequestUriEnable MxEnableState
  }

  -- Index:Gateway Name

  gwSpecificMwiGatewayName OBJECT-TYPE
   SYNTAX        OCTET STRING
   MAX-ACCESS    read-only
   STATUS        current
   DESCRIPTION " Gateway Name

                 String that identifies a SIP gateway in other tables.
                 "
   ::= { gwSpecificMwiEntry 100 }

  -- Columnar:Enable Configuration

  gwSpecificMwiEnableConfig OBJECT-TYPE
   SYNTAX        MxEnableState
   MAX-ACCESS    read-write
   STATUS        current
   DESCRIPTION " Enable Configuration

                 Defines the configuration to use for a specific SIP gateway.

                   * Disable: The SIP gateway uses the default configuration
                     as defined in the DefaultStaticMessagingHost and
                     DefaultUsernameInRequestUriEnable.
                   * Enable: The endpoint uses the specific configuration as
                     defined in the GwSpecificMwi.MessagingHost and
                     GwSpecificMwi.UsernameInRequestUriEnable.


                 "
   DEFVAL        { disable }
   ::= { gwSpecificMwiEntry 200 }

  -- Columnar:Messaging Host

  gwSpecificMwiMessagingHost OBJECT-TYPE
   SYNTAX        MxIpHostNamePort
   MAX-ACCESS    read-write
   STATUS        current
   DESCRIPTION " Messaging Host

                 Messaging server FQDN and port.
                 "
   DEFVAL        { "192.168.10.10:0" }
   ::= { gwSpecificMwiEntry 300 }

  -- Columnar:Username in Request-URI Enable

  gwSpecificMwiUsernameInRequestUriEnable OBJECT-TYPE
   SYNTAX        MxEnableState
   MAX-ACCESS    read-write
   STATUS        current
   DESCRIPTION " Username in Request-URI Enable

                 Indicates whether or not the unit adds the username in the
                 request URI of MWI SUBSCRIBE requests.

                   * enable: The unit adds the username in the Request-URI of
                     sent MWI SUBSCRIBE requests.
                   * disable: No username in Request-URI of MWI SUBSCRIBE
                     requests sent by the unit.


                 "
   DEFVAL        { disable }
   ::= { gwSpecificMwiEntry 400 }


 -- End of table:SIP Gateway Specific MWI

 -- ***************************************************************************
 
 -- Table:MWI Status

 -- ***************************************************************************
 
 mwiStatusTable OBJECT-TYPE
  SYNTAX                      SEQUENCE OF MwiStatusEntry
  MAX-ACCESS                  not-accessible
  STATUS                      current
  DESCRIPTION              "  MWI Status

                              .
                              "
  ::= { messageWaitingIndication 300 }
  mwiStatusEntry OBJECT-TYPE
   SYNTAX        MwiStatusEntry
   MAX-ACCESS    not-accessible
   STATUS        current
   DESCRIPTION " A row in table MWI Status. "
   INDEX         {
                   mwiStatusIndex
                 }

   ::= { mwiStatusTable 1 }

  MwiStatusEntry ::= SEQUENCE
  {
    mwiStatusIndex             Unsigned32,
    mwiStatusGatewayName       OCTET STRING,
    mwiStatusSubscriptionState INTEGER,
    mwiStatusEndpoint          OCTET STRING,
    mwiStatusMessagingHost     OCTET STRING,
    mwiStatusUsername          OCTET STRING
  }

  -- Index:Index

  mwiStatusIndex OBJECT-TYPE
   SYNTAX        Unsigned32
   MAX-ACCESS    read-only
   STATUS        current
   DESCRIPTION " Index

                 Unique identifier of the row.
                 "
   ::= { mwiStatusEntry 100 }

  -- Columnar:Gateway Name

  mwiStatusGatewayName OBJECT-TYPE
   SYNTAX        OCTET STRING
   MAX-ACCESS    read-only
   STATUS        current
   DESCRIPTION " Gateway Name

                 The SIP gateway used for this subscription.
                 "
   ::= { mwiStatusEntry 200 }

  -- Columnar:State

  mwiStatusSubscriptionState OBJECT-TYPE
   SYNTAX        INTEGER { unsubscribed(100) , subscribing(200) , subscribed
                 (300) , refreshing(400) , unsubscribing(500) , unreachable
                 (600) , authFailed(700) , rejected(800) , configError(900) ,
                 invalidResponse (1000) }
   MAX-ACCESS    read-only
   STATUS        current
   DESCRIPTION " State

                 The current state of the subscription.

                   * Unsubscribed: The unit/endpoint is not subscribed and
                     never tries to subscribe. This case occurs if the network
                     interface used by the SIP gateway is not up or the unit/
                     endpoint is locked.
                   * Subscribing: The subscription is currently trying to
                     subscribe.
                   * Subscribed: The subscription is successfully subscribed.
                   * Refreshing: The subscription is trying to refresh.
                   * Unreachable: The last subscription attempt failed because
                     the messaging server is unreachable.
                   * AuthFailed: The last subscription attempt failed because
                     authentication was not successful.
                   * Rejected: The last subscription attempt failed because
                     the messaging server rejects the subscription.
                   * ConfigError: The last subscription attempt failed because
                     it was badly configured. Check if the username and the
                     messaging host are not empty.
                   * InvalidResponse: The received 200 OK response contact
                     does not match the contact of the messaging server, or
                     the 200 OK response for an un-subscribe contains a
                     contact.


                 "
   ::= { mwiStatusEntry 300 }

  -- Columnar:Endpoint

  mwiStatusEndpoint OBJECT-TYPE
   SYNTAX        OCTET STRING
   MAX-ACCESS    read-only
   STATUS        current
   DESCRIPTION " Endpoint

                 The endpoint related to this subscription.
                 "
   ::= { mwiStatusEntry 400 }

  -- Columnar:Messaging Host

  mwiStatusMessagingHost OBJECT-TYPE
   SYNTAX        OCTET STRING
   MAX-ACCESS    read-only
   STATUS        current
   DESCRIPTION " Messaging Host

                 Messaging server FQDN and port used to subscribe the event
                 state.
                 "
   ::= { mwiStatusEntry 500 }

  -- Columnar:Username

  mwiStatusUsername OBJECT-TYPE
   SYNTAX        OCTET STRING
   MAX-ACCESS    read-only
   STATUS        current
   DESCRIPTION " Username

                 The username currently used by the subscription.
                 "
   ::= { mwiStatusEntry 600 }


 -- End of table:MWI Status

-- End of group:Message Waiting Indication

-- ****************************************************************************

-- Group:Conference

-- ****************************************************************************

conferenceGroup OBJECT IDENTIFIER
 ::= { sipEpMIBObjects 1900 }
 -- Scalar:Default Static Conference Server URI

 defaultStaticConferenceServerUri OBJECT-TYPE
  SYNTAX        OCTET STRING ( SIZE(0..255) )
  MAX-ACCESS    read-write
  STATUS        current
  DESCRIPTION " Default Static Conference Server URI

                URI used in the request-URI of the INVITE sent to the
                conference server as defined in RFC 4579.

                This variable only has an effect when the conference type is
                'ConferenceServer'. See EpServ.DefaultConferenceType.

                Please refer to the documentation shipped with your device for
                more details regarding this variable's semantics.

                If a specific configuration is set in the
                GwSpecificConference.ServerHost variable and the
                GwSpecificConference.EnableConfig variable is set to 'Enable',
                then it overrides the current default configuration.


                "
  DEFVAL        { "" }
  ::= { conferenceGroup 100 }

 -- ***************************************************************************
 
 -- Table:SIP Gateway Specific Conference

 -- ***************************************************************************
 
 gwSpecificConferenceTable OBJECT-TYPE
  SYNTAX        SEQUENCE OF GwSpecificConferenceEntry
  MAX-ACCESS    not-accessible
  STATUS        current
  DESCRIPTION " SIP Gateway Specific Conference

                A table of the conference configuration indexed by the SIP
                gateway name. It is used to override the default value.
                "
  ::= { conferenceGroup 1000 }
  gwSpecificConferenceEntry OBJECT-TYPE
   SYNTAX        GwSpecificConferenceEntry
   MAX-ACCESS    not-accessible
   STATUS        current
   DESCRIPTION " A row in table SIP Gateway Specific Conference. "
   INDEX         {
                   gwSpecificConferenceGatewayName
                 }

   ::= { gwSpecificConferenceTable 1 }

  GwSpecificConferenceEntry ::= SEQUENCE
  {
    gwSpecificConferenceGatewayName  OCTET STRING,
    gwSpecificConferenceEnableConfig MxEnableState,
    gwSpecificConferenceServerUri    OCTET STRING
  }

  -- Index:Gateway Name

  gwSpecificConferenceGatewayName OBJECT-TYPE
   SYNTAX        OCTET STRING
   MAX-ACCESS    read-only
   STATUS        current
   DESCRIPTION " Gateway Name

                 String that identifies a SIP gateway in other tables.
                 "
   ::= { gwSpecificConferenceEntry 100 }

  -- Columnar:Enable Configuration

  gwSpecificConferenceEnableConfig OBJECT-TYPE
   SYNTAX        MxEnableState
   MAX-ACCESS    read-write
   STATUS        current
   DESCRIPTION " Enable Configuration

                 Defines the configuration to use for a specific SIP gateway.

                   * Disable: The SIP gateway uses the default configuration
                     as defined in the DefaultStaticConferenceServerUri
                     variable.
                   * Enable: The endpoint uses the specific configuration as
                     defined in the GwSpecificConference.ServerUri variable.


                 "
   DEFVAL        { disable }
   ::= { gwSpecificConferenceEntry 200 }

  -- Columnar:SIP Gateway Specific Conference Server URI

  gwSpecificConferenceServerUri OBJECT-TYPE
   SYNTAX        OCTET STRING ( SIZE(0..255) )
   MAX-ACCESS    read-write
   STATUS        current
   DESCRIPTION " SIP Gateway Specific Conference Server URI

                 URI used in the request-URI of the INVITE sent to the
                 conference server as defined in RFC 4579.

                 This variable only has an effect when the conference type is
                 'ConferenceServer'. See EpServ.DefaultConferenceType.

                 Please refer to the documentation shipped with your device
                 for more details regarding this variable's semantics.


                 "
   DEFVAL        { "" }
   ::= { gwSpecificConferenceEntry 300 }


 -- End of table:SIP Gateway Specific Conference

-- End of group:Conference

-- ****************************************************************************

-- Group:Priority Group

-- ****************************************************************************

priorityGroup OBJECT IDENTIFIER
 ::= { sipEpMIBObjects 2000 }
 -- Scalar:Default Outbound Priority Call Routing

 defaultOutboundPriorityCallRouting OBJECT-TYPE
  SYNTAX        INTEGER { normal(100) , skipOutboundProxy(200) }
  MAX-ACCESS    read-write
  STATUS        current
  DESCRIPTION " Default Outbound Priority Call Routing

                Describes how to route priority calls including emergency
                calls.

                  * Normal: Send call using normal SIP call routing to the
                    outbound proxy (if defined) and to the target host
                    (usually the SIP server).
                  * SkipOutboundProxy: Send call directly to the configured
                    server skipping the outbound proxy.


                "
  DEFVAL        { skipOutboundProxy }
  ::= { priorityGroup 100 }

-- End of group:Priority Group

-- ****************************************************************************

-- Group:EventHandling

-- ****************************************************************************

eventHandlingGroup OBJECT IDENTIFIER
 ::= { sipEpMIBObjects 2100 }
 -- ***************************************************************************
 
 -- Table:SIP Gateway Event Handling

 -- ***************************************************************************
 
 gwEventHandlingTable OBJECT-TYPE
  SYNTAX        SEQUENCE OF GwEventHandlingEntry
  MAX-ACCESS    not-accessible
  STATUS        current
  DESCRIPTION " SIP Gateway Event Handling

                A table of event handling configuration indexed by SIP
                gateway.
                "
  ::= { eventHandlingGroup 100 }
  gwEventHandlingEntry OBJECT-TYPE
   SYNTAX        GwEventHandlingEntry
   MAX-ACCESS    not-accessible
   STATUS        current
   DESCRIPTION " A row in table SIP Gateway Event Handling. "
   INDEX         {
                   gwEventHandlingGatewayName
                 }

   ::= { gwEventHandlingTable 1 }

  GwEventHandlingEntry ::= SEQUENCE
  {
    gwEventHandlingGatewayName OCTET STRING,
    gwEventHandlingReboot      INTEGER,
    gwEventHandlingCheckSync   INTEGER
  }

  -- Index:Gateway Name

  gwEventHandlingGatewayName OBJECT-TYPE
   SYNTAX        OCTET STRING
   MAX-ACCESS    read-only
   STATUS        current
   DESCRIPTION " Gateway Name

                 String that identifies a SIP gateway in other tables.
                 "
   ::= { gwEventHandlingEntry 100 }

  -- Columnar:SIP Gateway can start a remote reboot via a SIP NOTIFY Event.

  gwEventHandlingReboot OBJECT-TYPE
   SYNTAX        INTEGER { rejected(100) , restart(200) }
   MAX-ACCESS    read-write
   STATUS        current
   DESCRIPTION " SIP Gateway can start a remote reboot via a SIP NOTIFY Event.

                 Specifies whether a remote reboot via a SIP NOTIFY message
                 event is supported or not for a specific SIP gateway.

                   * Rejected: The 'reboot' notification is rejected on
                     reception.
                   * Restart: When receiving a 'reboot' notification, a
                     restart of the unit is done.


                 "
   DEFVAL        { rejected }
   ::= { gwEventHandlingEntry 200 }

  -- Columnar:SIP Gateway can transfer and run a configuration file via a SIP
  -- NOTIFY Event.

  gwEventHandlingCheckSync OBJECT-TYPE
   SYNTAX        INTEGER { rejected(100) , transferScript(200) }
   MAX-ACCESS    read-write
   STATUS        current
   DESCRIPTION " SIP Gateway can transfer and run a configuration file via a
                 SIP NOTIFY Event.

                 Specifies whether a transfer script via a SIP NOTIFY message
                 event is supported or not for a specific SIP gateway.

                   * Rejected: The 'check-sync' notification is rejected on
                     reception.
                   * TransferScript: When receiving a 'check-sync'
                     notification, the Conf.ConfiguredScriptsTransferAndRun
                     command is executed.


                 "
   DEFVAL        { rejected }
   ::= { gwEventHandlingEntry 300 }


 -- End of table:SIP Gateway Event Handling

-- End of group:EventHandling

-- ****************************************************************************

-- Group:Transfer Group

-- ****************************************************************************

transferGroup OBJECT IDENTIFIER
 ::= { sipEpMIBObjects 2200 }
 -- Scalar:Referred By Header

 referredByHeader OBJECT-TYPE
  SYNTAX        INTEGER { none(100) , headerOnly(200) }
  MAX-ACCESS    read-write
  STATUS        current
  DESCRIPTION " Referred By Header

                Indicates how the Referred-By header is used when
                participating in a transfer.

                  * None: When acting as the transferor (sending the REFER),
                    the REFER does not contain a Referred-By header. When
                    acting as the transferee (receiving the REFER and sending
                    the INVITE to the target), the Referred-By header is not
                    copied from the REFER to the INVITE.
                  * HeaderOnly: When acting as the transferor (sending the
                    REFER), the Referred-By header contains the SIP URI of the
                    transferor. When acting as the transferee (receiving the
                    REFER and sending the INVITE to the target), the
                    Referred-By header is copied from the REFER to the INVITE.


                "
  DEFVAL        { none }
  ::= { transferGroup 100 }

 -- Scalar:Blind Transfer Method

 blindTransferMethod OBJECT-TYPE
  SYNTAX        INTEGER { semiAttended(100) , semiAttendedConfirmed(200) ,
                semiAttendedCancelled(300) }
  MAX-ACCESS    read-write
  STATUS        current
  DESCRIPTION " Blind Transfer Method

                Indicates how the blind transfer is achieved when
                participating in a transfer as the transferor.

                  * SemiAttended: When blind transfer is invoked by the
                    transferor, the device does not wait for the 200 OK
                    response before sending the REFER request, causing the
                    call transfer to be executed before the transfer-target
                    answers. The transferee and the target are connected
                    together early and the transferee can hear the ringback
                    from the target until the target answers.
                  * SemiAttendedConfirmed: When blind transfer is invoked by
                    the transferor, the device waits for receiving the 200 OK
                    from the transfer-target before sending a REFER to the
                    transferee. This is as per RFC5589 section 7.6, figure 11.
                  * SemiAttendedCancelled: Similar to SemiAttended but the
                    INVITE to the transfer-target is cancelled when the blind
                    tranfer is invoked before receiving a 200 OK. This is as
                    per RFC5589 section 7.6, Figure 12.


                "
  DEFVAL        { semiAttended }
  ::= { transferGroup 200 }

-- End of group:Transfer Group

-- ****************************************************************************

-- Group:Aoc Group

-- ****************************************************************************

aocGroup OBJECT IDENTIFIER
 ::= { sipEpMIBObjects 2300 }
 -- ***************************************************************************
 
 -- Table:Aoc Configuration

 -- ***************************************************************************
 
 aocConfigTable OBJECT-TYPE
  SYNTAX        SEQUENCE OF AocConfigEntry
  MAX-ACCESS    not-accessible
  STATUS        current
  DESCRIPTION " Aoc Configuration

                A table of the Aoc configuration indexed by the SIP gateway
                name.
                "
  ::= { aocGroup 100 }
  aocConfigEntry OBJECT-TYPE
   SYNTAX        AocConfigEntry
   MAX-ACCESS    not-accessible
   STATUS        current
   DESCRIPTION " A row in table Aoc Configuration. "
   INDEX         {
                   aocConfigGatewayName
                 }

   ::= { aocConfigTable 1 }

  AocConfigEntry ::= SEQUENCE
  {
    aocConfigGatewayName OCTET STRING,
    aocConfigAocDSupport INTEGER,
    aocConfigAocESupport INTEGER
  }

  -- Index:Gateway Name

  aocConfigGatewayName OBJECT-TYPE
   SYNTAX        OCTET STRING
   MAX-ACCESS    read-only
   STATUS        current
   DESCRIPTION " Gateway Name

                 String that identifies a SIP gateway in other tables.
                 "
   ::= { aocConfigEntry 100 }

  -- Columnar:Advice of Charge AOC-D Support

  aocConfigAocDSupport OBJECT-TYPE
   SYNTAX        INTEGER { disabled(100) , transparent(200) }
   MAX-ACCESS    read-write
   STATUS        current
   DESCRIPTION " Advice of Charge AOC-D Support

                 Send/Receive the current charge (D)uring the call in AOC-D
                 messages.

                   * Disabled: No AOC information is sent. Received AOC
                     information is discarded.
                   * Transparent: AOC information is forwarded to the peer
                     interface if AOC messages are received from the network.


                 "
   DEFVAL        { disabled }
   ::= { aocConfigEntry 200 }

  -- Columnar:Advice of Charge AOC-E Support

  aocConfigAocESupport OBJECT-TYPE
   SYNTAX        INTEGER { disabled(100) , transparent(200) }
   MAX-ACCESS    read-write
   STATUS        current
   DESCRIPTION " Advice of Charge AOC-E Support

                 Send the total charge at the (E)nd of the call in AOC-E
                 messages.

                   * Disabled: No AOC information is sent. Received AOC
                     information is discarded.
                   * Transparent: AOC information is forwarded to the peer
                     interface if AOC messages are received from the network.


                 "
   DEFVAL        { transparent }
   ::= { aocConfigEntry 300 }


 -- End of table:Aoc Configuration

-- End of group:Aoc Group

-- ****************************************************************************

-- Group:Interop Group

-- ****************************************************************************

interopGroup OBJECT IDENTIFIER
 ::= { sipEpMIBObjects 50000 }
 -- Scalar:Transmission Timeout

 interopTransmissionTimeout OBJECT-TYPE
  SYNTAX        Unsigned32 ( 1..32 )
  MAX-ACCESS    read-write
  STATUS        current
  DESCRIPTION " Transmission Timeout

                Changes the time to wait for a response or an ACK before
                considering a transaction timed out. This corresponds to
                timers B, F and H for all transport protocols and timer J for
                UDP. These timers are defined in section A of RFC 3261.

                This timeout affects the number of retransmissions.
                Retransmissions continue to follow the timing guidelines
                described in RFC 3261.

                For example, if using DNS SRV and multiple entries are
                present, this value is the time spent waiting for answers from
                each entry.

                This value is expressed in seconds (s).


                "
  DEFVAL        { 32 }
  ::= { interopGroup 400 }

 -- Scalar:TCP Connect Timeout

 interopTcpConnectTimeout OBJECT-TYPE
  SYNTAX        Unsigned32 ( 1..189 )
  MAX-ACCESS    read-write
  STATUS        current
  DESCRIPTION " TCP Connect Timeout

                Defines the maximum time, in seconds, the unit should try to
                establish a TCP connection to SIP hosts. This timeout value is
                useful to have a faster detection of unreachable remote hosts.
                This timer can also affects the TLS connection establishment
                time.
                "
  DEFVAL        { 189 }
  ::= { interopGroup 450 }

 -- Scalar:Enable/Disable Symmetric UDP Source Port

 interopSymmetricUdpSourcePortEnable OBJECT-TYPE
  SYNTAX        MxEnableState
  MAX-ACCESS    read-write
  STATUS        current
  DESCRIPTION " Enable/Disable Symmetric UDP Source Port

                Indicates whether the unit always uses the same local port
                when sending SIP traffic over UDP.

                Symmetric UDP ports are sometimes needed to traverse NAT/
                Firewall devices.

                Note that when changing this setting, all destinations are
                automatically thrown out of the penalty box, when applicable.

                  * enable: SIP signaling sent over UDP originates from the
                    same port as the port on which the user agent is
                    listening. This is configured in the 'PortConfig'
                    variable. When enabled, ICMP messages are not processed,
                    which means that unreachable targets will take longer to
                    detect.
                  * disable: SIP signaling over UDP uses a randomly-generated
                    originating port. ICMP errors are processed correctly.


                "
  DEFVAL        { enable }
  ::= { interopGroup 600 }

 -- Scalar:Max Forwards Value

 interopMaxForwardsValue OBJECT-TYPE
  SYNTAX        Integer32 ( 0..200 )
  MAX-ACCESS    read-write
  STATUS        current
  DESCRIPTION " Max Forwards Value

                Sets the value used in the Max-Forwards header, in conformance
                with RFC 3261.
                "
  DEFVAL        { 70 }
  ::= { interopGroup 700 }

 -- Scalar:Enable/Disable Sending of User-Agent Header

 interopSendUaHeaderEnable OBJECT-TYPE
  SYNTAX        MxEnableState
  MAX-ACCESS    read-write
  STATUS        current
  DESCRIPTION " Enable/Disable Sending of User-Agent Header

                Enables/Disables sending of the SIP User-Agent header.
                "
  DEFVAL        { enable }
  ::= { interopGroup 800 }

 -- Scalar:Enable/Disable SDP Direction Attribute

 interopSdpDirectionAttributeEnable OBJECT-TYPE
  SYNTAX        MxEnableState
  MAX-ACCESS    read-write
  STATUS        current
  DESCRIPTION " Enable/Disable SDP Direction Attribute

                Indicates if the SDP direction attribute is supported by the
                unit.

                This variable is used only when the negotiated media uses an
                IPv4 address. The application always behaves as if this
                variable is set to 'Enable' for media using an IPv6 address.

                When disabled, the application uses the RFC 2543 method to put
                a session on hold:

                  * No direction attribute is present in the SDP sent by the
                    unit.
                  * Any direction attribute found in the SDP received from the
                    peer is ignored by the unit.

                When enabled, the application uses the RFC 3264 method to put
                a session on hold:

                  * The unit always sends the direction attribute in the SDP
                    of an initiated call. For all other SDP messages sent by
                    the unit, refer to the variable
                    InteropSdpDetectPeerDirectionAttributeSupportEnable.
                  * If present in the SDP, the direction attribute is
                    preferred over the connection address to transmit session
                    modification information.


                "
  DEFVAL        { enable }
  ::= { interopGroup 900 }

 -- Scalar:Enable/Disable SDP Detect Peer Direction Attribute Support

 interopSdpDetectPeerDirectionAttributeSupportEnable OBJECT-TYPE
  SYNTAX        MxEnableState
  MAX-ACCESS    read-write
  STATUS        current
  DESCRIPTION " Enable/Disable SDP Detect Peer Direction Attribute Support

                Indicates if the SDP direction attribute support should be
                autodetected in the SDP received from the peer.

                This variable is used only when the negotiated media uses an
                IPv4 address and when the InteropSdpDirectionAttributeEnable
                is enabled. The application always behaves as if this variable
                is set to 'Disable' for media using an IPv6 address.

                When disabled, the unit always sends the direction attribute
                in the SDP without autodetection of peer support.

                When enabled: the initial handshake determines if the peer
                supports the direction attribute. The direction attribute will
                be present when the peer supports it.


                "
  DEFVAL        { enable }
  ::= { interopGroup 950 }

 -- Scalar:On Hold SDP Connection Address

 interopOnHoldSdpConnectionAddress OBJECT-TYPE
  SYNTAX        INTEGER { holdAddress(100) , mediaAddress(200) }
  MAX-ACCESS    read-write
  STATUS        current
  DESCRIPTION " On Hold SDP Connection Address

                Indicates the value of the connection address sent in the SDP
                when an endpoint is on hold and no longer listening to media
                packets.

                This variable is used only when the negotiated media uses an
                IPv4 address. The application always behaves as if this
                variable is set to 'MediaAddress' for media using an IPv6
                address.

                  * HoldAddress: The connection address sent in the SDP is
                    '0.0.0.0' if the media uses an IPv4 address. This method
                    is described by RFC 2543.
                  * MediaAddress: The connection address sent in the SDP is
                    the listening address.


                "
  DEFVAL        { holdAddress }
  ::= { interopGroup 975 }

 -- Scalar:On Hold SDP Stream Direction

 interopOnHoldSdpStreamDirection OBJECT-TYPE
  SYNTAX        INTEGER { inactive(100) , sendonly(200) }
  MAX-ACCESS    read-write
  STATUS        current
  DESCRIPTION " On Hold SDP Stream Direction

                Indicates the direction attribute sent in the SDP when putting
                an endpoint on hold.

                  * Inactive: The stream is put on hold by marking it as
                    inactive.
                  * Sendonly: The stream is put on hold by marking it as
                    sendonly. This method is in conformance with RFC 3264.

                This configuration has no effect if the
                InteropSdpDirectionAttributeEnable variable is set to
                'Disable'.


                "
  DEFVAL        { inactive }
  ::= { interopGroup 1000 }

 -- Scalar:On Hold Answer SDP Stream Direction

 interopOnHoldAnswerSdpStreamDirection OBJECT-TYPE
  SYNTAX        INTEGER { inactive(100) , recvonly(200) }
  MAX-ACCESS    read-write
  STATUS        current
  DESCRIPTION " On Hold Answer SDP Stream Direction

                Indicates how to set the direction attribute in the SDP when
                answering a hold offer with the direction attribute
                'sendonly'.

                  * Inactive: The stream is marked as inactive. If the stream
                    uses an IPv4 address, the connection address is set
                    according to the InteropOnHoldSdpConnectionAddress
                    variable.
                  * Recvonly: If the stream is currently active or receive
                    only, the stream is marked as recvonly and the connection
                    address is set to the IP address of the unit. If the
                    stream is currently send only or inactive, the stream is
                    marked as inactive and the connection address is set
                    according to the InteropOnHoldSdpConnectionAddress
                    variable.

                In both cases, no direction attribute is present in the SDP if
                the InteropSdpDirectionAttributeEnable variable is set to
                'Disable'.


                "
  DEFVAL        { recvonly }
  ::= { interopGroup 1025 }

 -- Scalar:SDP Stream Direction Attribute Level

 interopSdpDirectionAttributeLevel OBJECT-TYPE
  SYNTAX        INTEGER { mediaOrSessionLevel(100) , mediaAndSessionLevel(200)
                }
  MAX-ACCESS    read-write
  STATUS        current
  DESCRIPTION " SDP Stream Direction Attribute Level

                Preferred location where the stream direction attribute is
                set.

                  * MediaOrSessionLevel: If every media have the same
                    direction, the stream direction attribute is only present
                    at session level. Otherwise, the stream direction
                    attribute is only present at media level.
                  * MediaAndSessionLevel: If every media have the same
                    direction, the stream direction attribute is present both
                    at session level and media level. Otherwise, the stream
                    direction attribute is only present at media level.


                "
  DEFVAL        { mediaOrSessionLevel }
  ::= { interopGroup 1050 }

 -- Scalar:Local Ring on Provisional Response

 interopLocalRingOnProvisionalResponse OBJECT-TYPE
  SYNTAX        INTEGER { disable(0) , localRingWhenNoEstablishedMediaStream
                (1) , localRingAlways(2) }
  MAX-ACCESS    read-write
  STATUS        current
  DESCRIPTION " Local Ring on Provisional Response

                Specifies if the local ring should be started upon receiving a
                '18x Provisional' response without SDP.

                  * Disable: The local ring is not started on a '18x
                    Provisional' response without SDP, with one exception: the
                    '180 Ringing' without SDP will start the local ring if the
                    media stream is not already established.
                  * LocalRingWhenNoEstablishedMediaStream: The local ring is
                    started on any '18x Provisional' response without SDP if
                    the media stream is not already established.
                  * LocalRingAlways: The local ring is always started on any
                    '18x Provisional' response without SDP.

                Note: This variable does not affect the behaviour in case the
                '18x Provisional' response contains SDP in which case the
                media stream, if present, is played.'


                "
  DEFVAL        { disable }
  ::= { interopGroup 1100 }

 -- Scalar:SDP Origin Line Session ID and Version Max Length

 interopSdpOriginLineSessionIdAndVersionMaxLength OBJECT-TYPE
  SYNTAX        INTEGER { max32bits(100) , max64bits(200) }
  MAX-ACCESS    read-write
  STATUS        current
  DESCRIPTION " SDP Origin Line Session ID and Version Max Length

                The maximum length of the session ID and the session version
                number in the origin line (o=) of the SDP.

                  * Max-32bits: The session ID and the session version number
                    are represented with a 32 bit integer. They have a maximum
                    length of 10 digits.
                  * Max-64bits: The session ID and the session version number
                    are represented with a 64 bit integer. They have a maximum
                    length of 20 digits.


                "
  DEFVAL        { max64bits }
  ::= { interopGroup 1200 }

 -- Scalar:Enable/Disable Lock DNS SRV Record Per Call

 interopLockDnsSrvRecordPerCallEnable OBJECT-TYPE
  SYNTAX        MxEnableState
  MAX-ACCESS    read-write
  STATUS        current
  DESCRIPTION " Enable/Disable Lock DNS SRV Record Per Call

                Configures the behavior of the DNS SRV feature.

                  * Disable: The behavior follows RFC 3263.
                  * Enable: All messages during a call or registration use the
                    same SRV record.


                "
  DEFVAL        { disable }
  ::= { interopGroup 1400 }

 -- Scalar:Ringing Response Code

 interopRingingResponseCode OBJECT-TYPE
  SYNTAX        INTEGER { send180Ringing(100) , send183WithSdp(200) }
  MAX-ACCESS    read-write
  STATUS        current
  DESCRIPTION " Ringing Response Code

                Configures the response code sent back when the endpoint
                starts ringing.

                  * Send180Ringing: Send out a '180 Ringing' response without
                    a body.
                  * Send183WithSdp: Return a '183 Session Progress' packet
                    with SDP (needed if the endpoint is required to generate
                    ringback on connection).


                "
  DEFVAL        { send180Ringing }
  ::= { interopGroup 1600 }

 -- Scalar:Reject Code For No Ressource

 interopRejectCodeForNoRessource OBJECT-TYPE
  SYNTAX        INTEGER { temporarilyUnavailable(100) , busyHere(200) }
  MAX-ACCESS    read-write
  STATUS        current
  DESCRIPTION " Reject Code For No Ressource

                Configures the rejection code used when all lines of the group
                are unavailable.

                  * TemporarilyUnavailable: The '480 Temporarily Unavailable'
                    rejection code is used.
                  * BusyHere: The '486 Busy Here' rejection code is used.


                "
  DEFVAL        { temporarilyUnavailable }
  ::= { interopGroup 1700 }

 -- Scalar:Reject Code For Unsupported SDP Offer

 interopRejectCodeForUnsupportedSdpOffer OBJECT-TYPE
  SYNTAX        INTEGER { unsupportedMediaType(415) , notAcceptableHere(488) }
  MAX-ACCESS    read-write
  STATUS        current
  DESCRIPTION " Reject Code For Unsupported SDP Offer

                Configures the rejection code used when an offer is received
                with invalid or unsupported SDP Offer.

                  * UnsupportedMediaType: The SIP error code 415 'Unsupported
                    Media Type' is returned if the Content-Type is invalid;
                    the payload is missing or the SDP content is invalid.
                  * NotAcceptableHere: The SIP error code 488 'Not Acceptable
                    Here' is returned if the SDP content is invalid.

                RFC 3261 recommends using the error code 488 'Not Acceptable
                Here'.


                "
  DEFVAL        { unsupportedMediaType }
  ::= { interopGroup 1750 }

 -- Scalar:Enable/Disable Use DTMF Payload Type Found In Answer

 interopUseDtmfPayloadTypeFoundInAnswer OBJECT-TYPE
  SYNTAX        MxEnableState
  MAX-ACCESS    read-write
  STATUS        current
  DESCRIPTION " Enable/Disable Use DTMF Payload Type Found In Answer

                The default behavior when sending an initial offer that
                contains an RFC 2833 payload type is to keep using that
                payload type even if the response comes back with a different
                one. When this variable is enabled, the unit rather uses the
                payload type found in the answer. The variable does not affect
                the behavior when receiving an offer.

                  * Disable: Keep using the initial payload type.
                  * Enable: Use the RFC 2833 payload type found in the
                    received answer.

                This variable only has an effect when the
                DefaultDtmfTransportMethod variable is set to
                'OutOfBandUsingRtp'.


                "
  DEFVAL        { disable }
  ::= { interopGroup 2200 }

 -- Scalar:Register Home Domain Override

 interopRegisterHomeDomainOverride OBJECT-TYPE
  SYNTAX        OCTET STRING ( SIZE(0..255) )
  MAX-ACCESS    read-write
  STATUS        current
  DESCRIPTION " Register Home Domain Override

                Home domain override configuration. If not empty, the address
                of record in the register uses this string instead of the home
                domain proxy (refer to the variable
                'DefaultStaticProxyHomeDomainHost').
                "
  DEFVAL        { "" }
  ::= { interopGroup 2400 }

 -- Scalar:Enforce Offer Answer Model

 interopEnforceOfferAnswerModel OBJECT-TYPE
  SYNTAX        MxEnableState
  MAX-ACCESS    read-write
  STATUS        current
  DESCRIPTION " Enforce Offer Answer Model

                Determines whether or not the unit requires strict adherence
                to RFC 3264 when receiving an answer from the peer when
                negotiating capabilities for the establishment of a media
                session.

                When enabled, the following guidelines from the Offer-Answer
                Model must be strictly followed. An answer must:

                  * Include at least one codec from the list that the unit
                    sent in the offer;
                  * Contain the same number of media lines that the unit put
                    in its offer.

                Otherwise, the answer is rejected and the unit ends the call.

                When disabled, then the peer can freely:

                  * Send back a brand new list of codecs;
                  * Add new media lines.

                As long as at least one codec sent back was present in the
                initial offer, the call is allowed to go on. Any media line
                added by the peer is simply ignored.

                The variable InteropAllowLessMediaInResponse allows to enable/
                disable other deviations from the Offer/Answer model.


                "
  DEFVAL        { enable }
  ::= { interopGroup 2600 }

 -- Scalar:Map Plus To TON International

 interopMapPlusToTonInternational OBJECT-TYPE
  SYNTAX        MxEnableState
  MAX-ACCESS    read-write
  STATUS        current
  DESCRIPTION " Map Plus To TON International

                When enabled, the service has the following behavior:

                  * For a call to SIP, prefixes the username with '+' if the
                    call has the call property 'type of number' set to
                    'international'. Also adds the 'user' parameter with value
                    'phone' to the SIP URI. e.g.: 'sip:1234@domain.com;user=
                    phone'
                  * For a call from SIP, sets the call property 'type of
                    number' to 'international' if the username has the prefix
                    '+'.


                "
  DEFVAL        { enable }
  ::= { interopGroup 2700 }

 -- Scalar:Allow Less Media In Response

 interopAllowLessMediaInResponse OBJECT-TYPE
  SYNTAX        MxEnableState
  MAX-ACCESS    read-write
  STATUS        current
  DESCRIPTION " Allow Less Media In Response

                Determines the behavior of the device when receiving less
                medias announcement in the response than in the offer.

                  * Enable: Tries to find matching media when the response
                    contains less media announcement than in the offer.
                  * Disable: Rejects the response with less media announcement
                    than in the offer.

                The variable InteropEnforceOfferAnswerModel allows to enable/
                disable other deviations from the Offer/Answer model.


                "
  DEFVAL        { disable }
  ::= { interopGroup 2800 }

 -- Scalar:Default Username Value

 interopDefaultUsernameValue OBJECT-TYPE
  SYNTAX        INTEGER { anonymous(100) , host(200) }
  MAX-ACCESS    read-write
  STATUS        current
  DESCRIPTION " Default Username Value

                Determines the username to use when the username is empty or
                undefined.

                  * Anonymous: Set the username to 'anonymous'.
                  * Host: Set the username to the same value as the host.


                "
  DEFVAL        { anonymous }
  ::= { interopGroup 3000 }

 -- Scalar:Call Waiting Private Number Criteria for SIP INFO

 interopCallWaitingSipInfoPrivateNumberCriteria OBJECT-TYPE
  SYNTAX        OCTET STRING ( SIZE(0..255) )
  MAX-ACCESS    read-write
  STATUS        current
  DESCRIPTION " Call Waiting Private Number Criteria for SIP INFO

                Specify the call waiting criteria, in the form of a regular
                expression, that defines a private number received in a SIP
                INFO.

                For example, the value '(Anonymous|anonymous)' would define a
                calling number that is either 'Anonymous' or 'anonymous' as
                private. The regular expression symbols to match the beginning
                and end of the number are implicit and do not need to be
                specified.

                The variable is effective only if the
                EpServ.DefaultCallHookFlashProcessing or
                EpServ.EpSpecificCall.HookFlashProcessing variables are set to
                'TransmitUsingSignalingProtocol'.


                "
  DEFVAL        { "" }
  ::= { interopGroup 3250 }

 -- Scalar:T.38 Capabilities Format

 interopSdpT38ParametersEncoding OBJECT-TYPE
  SYNTAX        INTEGER { ituT38AnnexD(100) ,
                sippingRealTimeFax00InternetDraft(200) }
  MAX-ACCESS    read-write
  STATUS        current
  DESCRIPTION " T.38 Capabilities Format

                Determines the format in which the unit's T.38 capabilities
                are advertised. This format is used in the SDP portion of SIP
                packets.

                  * SippingRealTimeFax00InternetDraft : Support for the
                    boolean T.38 parameters T38FaxFillBitRemoval,
                    T38FaxTranscodingMMR and T38FaxTranscodingJBIG is
                    advertised by associating a value of 0 (unsupported) or 1
                    (supported) with the parameter in the following manner: 'a
                    =T38FaxFillBitRemoval:0', 'a=T38FaxTranscodingMMR:0' and
                    'a=T38FaxTranscodingJBIG:0'. This is compliant with the
                    draft-ietf-sipping-realtimefax-00.txt internet draft.
                  * ItuT38AnnexD : Support for the above T.38 parameters is
                    advertised in conformance with ITU-T Recommendation T.38,
                    section D.2.3. The presence of the parameter in the SDP
                    indicates support for it (without the need for an
                    associated value), while its absence means that it is not
                    supported.


                "
  DEFVAL        { sippingRealTimeFax00InternetDraft }
  ::= { interopGroup 3300 }

 -- Scalar:ReInvite For Voice On 606 Not Acceptable

 interopReInviteForVoiceOn606NotAcceptable OBJECT-TYPE
  SYNTAX        MxEnableState
  MAX-ACCESS    read-write
  STATUS        current
  DESCRIPTION " ReInvite For Voice On 606 Not Acceptable

                Determines the behavior of the device when receiving a 606 Not
                Acceptable in response to an INVITE for T.38 fax.

                  * Enable: Fallback to voice is done by sending an INVITE for
                    voice codec negotiation. Also, fax detection is disabled
                    for the remainder of the call.
                  * Disable: The call is released.


                "
  DEFVAL        { disable }
  ::= { interopGroup 3400 }

 -- Scalar:Allow Multiple Active Media In Answer

 interopAllowMultipleActiveMediaInAnswer OBJECT-TYPE
  SYNTAX        MxEnableState
  MAX-ACCESS    read-write
  STATUS        current
  DESCRIPTION " Allow Multiple Active Media In Answer

                Determines the behavior of the device when answering a request
                offering more than one active media.

                  * Enable: Each matching active media in the offer is
                    specified as active in the answer. Other medias are set to
                    inactive.
                  * Disable: The answer contains only one active media. The
                    media specified as active in the answer is the top-most
                    matching one in the offer. Other medias are set to
                    inactive.


                "
  DEFVAL        { enable }
  ::= { interopGroup 3500 }

 -- Scalar:Ignore SIP OPTIONS On No Usuable Endpoints

 interopIgnoreSipOptionsOnNoUsuableEndpoints OBJECT-TYPE
  SYNTAX        MxEnableState
  MAX-ACCESS    read-write
  STATUS        current
  DESCRIPTION " Ignore SIP OPTIONS On No Usuable Endpoints

                Determines whether or not the SIP OPTIONS requests should be
                ignored when all endpoints are unusable.

                Enable: The unit ignores SIP OPTIONS request when all
                endpoints are unusable. When at least one endpoint is usable,
                then the SIP OPTIONS requests are answered as configured in
                the variable InteropSipOptionsMethodSupport.

                Disable: The SIP OPTIONS requests are answered as configured
                in the variable InteropSipOptionsMethodSupport regardless of
                the state of the endpoints.


                "
  DEFVAL        { disable }
  ::= { interopGroup 3550 }

 -- Scalar:SIP OPTIONS Method Support

 interopSipOptionsMethodSupport OBJECT-TYPE
  SYNTAX        INTEGER { none(100) , alwaysOk(200) }
  MAX-ACCESS    read-write
  STATUS        current
  DESCRIPTION " SIP OPTIONS Method Support

                Determines the behavior of the device when answering a SIP
                OPTIONS request.

                  * None: The unit responds with an error 405 Method not
                    allowed.
                  * AlwaysOk: The unit responds with a 200 OK regardless of
                    the content of the OPTIONS request.


                "
  DEFVAL        { none }
  ::= { interopGroup 3600 }

 -- Scalar:Allow Media Reactivation in SDP Answer

 interopAllowMediaReactivationInAnswer OBJECT-TYPE
  SYNTAX        MxEnableState
  MAX-ACCESS    read-write
  STATUS        current
  DESCRIPTION " Allow Media Reactivation in SDP Answer

                Determines the unit behavior when receiving a SDP answer
                activating a media that had been previously deactivated in the
                offer.

                  * Enable: A media reactivated in an incoming answer is
                    ignored. This behavior goes against the SDP Offer/Answer
                    model described by IETF RFC 3264.
                  * Disable: A media reactivated in an incoming answer ends
                    the current media negotiation and the call. This behavior
                    follows the SDP Offer/Answer model described by IETF RFC
                    3264.

                The InteropEnforceOfferAnswerModel,
                InteropAllowLessMediaInResponse and
                InteropAllowMultipleActiveMediaInAnswer variables allow to
                enable or disable other deviations from the Offer/Answer
                model.


                "
  DEFVAL        { disable }
  ::= { interopGroup 3700 }

 -- Scalar:Allow Simultaneous Audio and Image Media Negotiation

 interopAllowAudioAndImageNegotiation OBJECT-TYPE
  SYNTAX        MxEnableState
  MAX-ACCESS    read-write
  STATUS        current
  DESCRIPTION " Allow Simultaneous Audio and Image Media Negotiation

                Determines the unit behavior when offering media or answering
                to a media offer with audio and image negotiation.

                  * Enable: The unit offers audio and image media
                    simultaneously in outgoing SDP offers and transits to T.38
                    mode upon reception of a T.38 packet. Also, when the unit
                    answers positively to a SDP offer with audio and image, it
                    transits to T.38 mode upon reception of a T.38 packet.
                  * Disable: Outgoing offers never include image and audio
                    simultaneously. Incoming offers with audio and image
                    medias with a non-zero port are considered as offering
                    only audio.


                "
  DEFVAL        { disable }
  ::= { interopGroup 3800 }

 -- Scalar:Escape Pound in SIP URI Username

 interopEscapePoundInSipUriUsername OBJECT-TYPE
  SYNTAX        MxEnableState
  MAX-ACCESS    read-write
  STATUS        current
  DESCRIPTION " Escape Pound in SIP URI Username

                Determines whether or not the pound character (#) must be
                escaped in the username part of a SIP URI.

                  * Enable: Pound character (#) is escaped in the username
                    part of a SIP URI.
                  * Disable: Pound character (#) is not escaped in the
                    username part of a SIP URI.

                Note: RFC 3261 specifies that the pound character (#) needs to
                be escaped in the username part of a SIP URI.


                "
  DEFVAL        { enable }
  ::= { interopGroup 4000 }

 -- Scalar:Add the 'x-Siemens-Call-Type' header to the SIP packets

 interopSiemensTransportHeaderEnable OBJECT-TYPE
  SYNTAX        MxEnableState
  MAX-ACCESS    read-write
  STATUS        current
  DESCRIPTION " Add the 'x-Siemens-Call-Type' header to the SIP packets

                Triggers the addition of the 'x-Siemens-Call-Type' header to
                the SIP packets sent by the unit. When enabled, the header is
                added, and assigned the value 'ST-secure', as soon as secure
                transport and secure payload are being used. If secure
                transport or secure payload are not used, the header is not
                added.
                "
  DEFVAL        { disable }
  ::= { interopGroup 4100 }

 -- Scalar:Request client authentication when acting as TLS server

 interopTlsClientAuthenticationEnable OBJECT-TYPE
  SYNTAX        MxEnableState
  MAX-ACCESS    read-write
  STATUS        current
  DESCRIPTION " Request client authentication when acting as TLS server

                Specifies whether mutual authentication is enforced when the
                gateway is acting as a TLS server.

                  * Enable: The TLS clients have to provide their host
                    certificate in order for the connection to be allowed. In
                    this case, the level of security used to validate the host
                    certificate is TrustedCertificate, whatever the value set
                    in the variable SipEp.InteropTlsCertificateValidation.
                  * Disable: The unit does not require to TLS client to
                    provide their host certificate in order for the connection
                    to be allowed.


                "
  DEFVAL        { disable }
  ::= { interopGroup 4200 }

 -- Scalar:Level of security used to validate the peer TLS certificate

 interopTlsCertificateValidation OBJECT-TYPE
  SYNTAX        INTEGER { noValidation(100) , trustedCertificate(200) ,
                dnsSrvResponse(300) , hostName(400) }
  MAX-ACCESS    read-write
  STATUS        current
  DESCRIPTION " Level of security used to validate the peer TLS certificate

                When the unit is acting as a TLS client, this variable
                specifies which level of security is used to validate a TLS
                server certificate.

                NOTE: This variable has no effect on the TLS client
                authentication when the unit is acting as a TLS server (See
                the variable InteropTlsClientAuthenticationEnable).

                  * NoValidation: No validation of the peer certificate is
                    performed. All TLS connections are accepted without any
                    verification. Note that at least one certificate must be
                    returned by the peer even if no validation is made. This
                    option provides no security and should be restricted to a
                    lab use only.
                  * TrustedCertificate: Allow a TLS connection only if the
                    peer certificate is trusted. A certificate is considered
                    trusted when the certificate authority (CA) that signed
                    the peer certificate is present in the certMIB/
                    othersCertificatesInfoTable. This option provides a
                    minimum level of security and should be restricted to a
                    lab use only.
                  * DnsSrvResponse: Allow a TLS connection if the peer
                    certificate is trusted and contains a known host name. A
                    known host name can be the FQDN or IP address configured
                    as the SIP server, or can also be returned by a DNS SRV
                    request. In this case, the match is performed against the
                    DNS response name. If it matches either one of the Subject
                    Alternate Name (SAN) or Common Name (CN) in the peer
                    certificate, the connection is allowed. This option
                    provides an acceptable level of security, but not as good
                    as HostName.
                  * HostName: Allow a TLS connection if the peer certificate
                    is trusted and contains a known host name. A known host
                    name can only be the FQDN or IP address configured as the
                    SIP server. If it matches either one of the Subject
                    Alternate Name (SAN) or Common Name (CN) in the peer
                    certificate, the connection is allowed. This option
                    provides the highest level of security.


                "
  DEFVAL        { hostName }
  ::= { interopGroup 4250 }

 -- Scalar:Ignore Plus in Username

 interopIgnorePlusInUsername OBJECT-TYPE
  SYNTAX        MxEnableState
  MAX-ACCESS    read-write
  STATUS        current
  DESCRIPTION " Ignore Plus in Username

                Determines whether or not the plus character (+) is ignored
                when attempting to match a challenge username with usernames
                in the Authentication table.

                  * Enable: Plus character (+) is ignored when attempting to
                    match a username in the authentication table.
                  * Disable: Plus character (+) is not ignored when attempting
                    to match a username in the authentication table.

                Note that the plus character is ignored in both the challenge
                username and the Authentication table username.


                "
  DEFVAL        { disable }
  ::= { interopGroup 4300 }

 -- ***************************************************************************
 
 -- Table:Behavior On T.38 Invite Not Accepted

 -- ***************************************************************************
 
 behaviorOnT38InviteNotAcceptedTable OBJECT-TYPE
  SYNTAX        SEQUENCE OF BehaviorOnT38InviteNotAcceptedEntry
  MAX-ACCESS    not-accessible
  STATUS        current
  DESCRIPTION " Behavior On T.38 Invite Not Accepted

                This table defines the device behavior after receiving an
                error to a SIP INVITE for T.38 fax.
                "
  ::= { interopGroup 4600 }
  behaviorOnT38InviteNotAcceptedEntry OBJECT-TYPE
   SYNTAX        BehaviorOnT38InviteNotAcceptedEntry
   MAX-ACCESS    not-accessible
   STATUS        current
   DESCRIPTION " A row in table Behavior On T.38 Invite Not Accepted. "
   INDEX         {
                   behaviorOnT38InviteNotAcceptedSipErrorCode
                 }

   ::= { behaviorOnT38InviteNotAcceptedTable 1 }

  BehaviorOnT38InviteNotAcceptedEntry ::= SEQUENCE
  {
    behaviorOnT38InviteNotAcceptedSipErrorCode Unsigned32,
    behaviorOnT38InviteNotAcceptedBehavior     INTEGER
  }

  -- Index:SIP Error Code

  behaviorOnT38InviteNotAcceptedSipErrorCode OBJECT-TYPE
   SYNTAX        Unsigned32 ( 406..406 | 415..415 | 488..488 | 606..606 )
   MAX-ACCESS    read-only
   STATUS        current
   DESCRIPTION " SIP Error Code

                 SIP code in the error response to an INVITE for T.38 fax.
                 "
   ::= { behaviorOnT38InviteNotAcceptedEntry 100 }

  -- Columnar:Behavior

  behaviorOnT38InviteNotAcceptedBehavior OBJECT-TYPE
   SYNTAX        INTEGER { dropCall(100) , reInviteForClearChannelOnly(200) ,
                 reEstablishAudio(300) , usePreviousMediaNegotiation(400) }
   MAX-ACCESS    read-write
   STATUS        current
   DESCRIPTION " Behavior

                 Behavior of the device when receiving a SIP error response to
                 an INVITE for T.38 fax.

                   * DropCall: The call is dropped by sending a BYE.
                   * ReInviteForClearChannelOnly: A re-INVITE is sent with
                     enabled clear channel codecs only.
                   * ReEstablishAudio: A re-INVITE is sent to re-establish the
                     audio path. Also, fax detection is disabled for the
                     remainder of the call.
                   * UsePreviousMediaNegotiation: No re-INVITE is sent and the
                     audio codec from the last successful negotiation is used.
                     For the remainder of the call, T.38 is disabled and fax
                     detection may trigger a switch to a clear channel codec
                     that was available in the last successful negotiation.


                 "
   DEFVAL        { reInviteForClearChannelOnly }
   ::= { behaviorOnT38InviteNotAcceptedEntry 200 }


 -- End of table:Behavior On T.38 Invite Not Accepted

 -- Scalar:Behavior On Machine Detection

 interopBehaviorOnMachineDetection OBJECT-TYPE
  SYNTAX        INTEGER { reInviteOnFaxT38Only(100) ,
                reInviteOnNoNegotiatedDataCodec(200) , reInviteUnconditional
                (300) }
  MAX-ACCESS    read-write
  STATUS        current
  DESCRIPTION " Behavior On Machine Detection

                Specifies the SIP device behavior when a machine is detected
                during a call.

                  * ReInviteOnFaxT38Only: A SIP re-INVITE is sent only on a
                    fax detection and T.38 is enabled.
                  * ReInviteOnNoNegotiatedDataCodec: A SIP re-INVITE is sent
                    on a fax or modem detection if no data codec was
                    previously negotiated in the original SDP negotiation. In
                    the case where at least one data codec was previously
                    negotiated in the SDP negotiation, the device switches
                    silently to a data codec without sending a SIP re-INVITE.
                    Note that if there is no data codec enabled on the device,
                    no SIP re-INVITE is sent and the call is dropped by
                    sending a BYE.
                  * ReInviteUnconditional : A SIP re-INVITE is sent with data
                    codecs upon detection of a fax or modem even if a data
                    codec was negotiated in the initial offer-answer. The T.38
                    codec is offered if it is enabled and a fax is detected.


                "
  DEFVAL        { reInviteOnFaxT38Only }
  ::= { interopGroup 4650 }

 -- Scalar:Codec vs Beareer Capabilities Mapping Preferred Codec Choice

 interopCodecVsBearerCapabilitiesMappingPreferredCodecChoice OBJECT-TYPE
  SYNTAX        INTEGER { firstCodec(100) , prioritizeClearChannel(200) }
  MAX-ACCESS    read-write
  STATUS        current
  DESCRIPTION " Codec vs Beareer Capabilities Mapping Preferred Codec Choice

                Configures the behavior of the
                CodecVsBearerCapabilitiesMapping table by modifying the
                selection of the preferred codec in the incoming SDP.

                  * FirstCodec: The first valid codec in the incoming SDP is
                    considered the preferred one and is used when looking up
                    the CodecVsBearerCapabilitiesMapping table.
                  * PrioritizeClearChannel: When a clear channel codec is in
                    the incoming SDP, it is always considered as the preferred
                    one, no matter where it stands in the codec list, and is
                    used when looking up the CodecVsBearerCapabilitiesMapping
                    table.


                "
  DEFVAL        { firstCodec }
  ::= { interopGroup 4700 }

 -- Scalar:SIP URI User Parameter Value

 interopSipUriUserParameterValue OBJECT-TYPE
  SYNTAX        OCTET STRING ( SIZE(0..255) )
  MAX-ACCESS    read-write
  STATUS        current
  DESCRIPTION " SIP URI User Parameter Value

                Determines the value of the user parameter in SIP URIs sent by
                the unit. If empty, the parameter is not added.

                ex: 'sip:1234@domain.com;user=InteropSipUriUserParameterValue'

                Note that when the variable InteropMapPlusToTonInternational
                is enabled, the parameter's value might be overwritten.


                "
  DEFVAL        { "" }
  ::= { interopGroup 4800 }

 -- Scalar:Listen for early RTP

 interopListenForEarlyRtpEnable OBJECT-TYPE
  SYNTAX        MxEnableState
  MAX-ACCESS    read-write
  STATUS        current
  DESCRIPTION " Listen for early RTP

                Listen for RTP even before the reception of a response with
                SDP.

                  * Enable: The RTP port is opened after the initial INVITE
                    has been sent, without waiting for a provisional or final
                    response with SDP to be received. No local ring is
                    generated. This conforms to section 5.1 of RFC 3264.
                  * Disable: The RTP port is opened only after a response with
                    SDP is received.

                This variable only applies to calls initiated from analog
                endpoints (FXS/FXO) with non-secure RTP.


                "
  DEFVAL        { disable }
  ::= { interopGroup 4900 }

 -- Scalar:Registration Contact Matching

 interopRegistrationContactMatching OBJECT-TYPE
  SYNTAX        INTEGER { strict(100) , ignoreUriParams(200) }
  MAX-ACCESS    read-write
  STATUS        current
  DESCRIPTION " Registration Contact Matching

                Configures the matching behavior for the contact header
                received in positive responses to REGISTER requests sent by
                the unit.

                  * Strict: Match the complete contact's SIP URI including any
                    URI parameters, if any, as per RFC 3261 sections '10.2.4
                    Refreshing Bindings' and '19.1.4 URI Comparison'. The
                    contact's SIP URI of a 2XX positive response MUST match
                    the contact's SIP URI of the REGISTER request.
                  * IgnoreUriParams: Match the username and the host port part
                    of the contact's SIP URI. All URI parameters are ignored.


                "
  DEFVAL        { strict }
  ::= { interopGroup 5000 }

 -- Scalar:Interop Resolve Route Header

 interopResolveRouteHeaderEnable OBJECT-TYPE
  SYNTAX        MxEnableState
  MAX-ACCESS    read-write
  STATUS        current
  DESCRIPTION " Interop Resolve Route Header

                Allows to resolve the FQDN in the top-most route header of
                outgoing packets.

                  * Enable: The FQDN in the top-most route header is replaced
                    by the IP address of the packet's destination if the FQDN
                    matches the gateway's configured outbound proxy.
                  * Disable: The route header is not modified.


                "
  DEFVAL        { disable }
  ::= { interopGroup 5100 }

 -- Scalar:Force DNS NAPTR In TLS

 interopForceDnsNaptrInTls OBJECT-TYPE
  SYNTAX        MxEnableState
  MAX-ACCESS    read-write
  STATUS        current
  DESCRIPTION " Force DNS NAPTR In TLS

                Force DNS NAPTR request when SIP transport is TLS.

                  * Enable: A DNS NAPTR request is sent to obtain the DNS
                    record associated with SIP over TLS. An SRV request is
                    performed afterward. If no SIP over TLS entry is returned,
                    the call fails.
                  * Disable: The DNS SRV request is sent directly with the SIP
                    transport in SIP URI as recommended in RFC 3263, section
                    4.1.

                This variable only applies to calls over TLS when the
                SupportedDnsQueries variable is set to Naptr.


                "
  DEFVAL        { disable }
  ::= { interopGroup 5200 }

 -- Scalar:ACK Branch Matching

 interopAckBranchMatching OBJECT-TYPE
  SYNTAX        INTEGER { rfc3261(100) , rfc3261WithoutAck(200) }
  MAX-ACCESS    read-write
  STATUS        current
  DESCRIPTION " ACK Branch Matching

                Configures the method used to match incoming ACK SIP packets.

                  * Rfc3261: Follow the method described in RFC 3261 (section
                    8.1.1.7). The branch value in the topmost via of the ACK
                    request to a 2XX response MUST be different than the one
                    of the INVITE.
                  * Rfc3261WithoutAck: Follow the method described in RFC 3261
                    (section 8.1.1.7) but enable the handling of ACK requests
                    (for 2XX responses) that have the same branch value in the
                    topmost via as the INVITE.


                "
  DEFVAL        { rfc3261 }
  ::= { interopGroup 5300 }

 -- Scalar:Ignore Require Header

 interopIgnoreRequireHeaderEnable OBJECT-TYPE
  SYNTAX        MxEnableState
  MAX-ACCESS    read-write
  STATUS        current
  DESCRIPTION " Ignore Require Header

                Indicates if the Require Header must be ignored when
                processing the incoming SIP Client requests (Invite,
                re-Invite, Bye, etc.).

                  * Enable: The Require Header is ignored and no validation
                    about these options-tags is performed.
                  * Disable: The Require Header options-tags are validated
                    and, when an option-tag is not supported, a 420 (Bad
                    Extension) response is sent.

                    The supported options-tags are:
                      + * 100rel
                      + * replaces
                      + * timer


                "
  DEFVAL        { enable }
  ::= { interopGroup 5400 }

 -- Scalar:User-Agent Header Format

 interopUaHeaderFormat OBJECT-TYPE
  SYNTAX        OCTET STRING
  MAX-ACCESS    read-write
  STATUS        current
  DESCRIPTION " User-Agent Header Format

                The text to display in the User-Agent Header. Macros can be
                used to include information specific to the unit.

                The supported macros are:

                  * %version% - Application version.
                  * %mac% - MAC address.
                  * %product% - Product name.
                  * %profile% - Profile.
                  * %% - Insert % character.


                "
  DEFVAL        { "%product%/v%version% %profile%" }
  ::= { interopGroup 5500 }

 -- Scalar:SIP INFO Without Content Answer

 interopSipInfoWithoutContentAnswer OBJECT-TYPE
  SYNTAX        INTEGER { ok(200) , unsupportedMediaType(415) }
  MAX-ACCESS    read-write
  STATUS        current
  DESCRIPTION " SIP INFO Without Content Answer

                Determines the response of the device to a received SIP INFO
                with no message body for an existing call.

                  * UnsupportedMediaType: The unit responds with the SIP error
                    code 415 'Unsupported Media Type'.
                  * Ok: The unit responds with a 200 OK.

                RFC 2976 recommends that a 200 OK response MUST be sent for an
                INFO request with no message body if the INFO request was
                successfully received for an existing call.


                "
  DEFVAL        { unsupportedMediaType }
  ::= { interopGroup 5600 }

 -- Scalar:Registration Delay Value

 interopRegistrationDelayValue OBJECT-TYPE
  SYNTAX        Unsigned32 ( 0..600 )
  MAX-ACCESS    read-write
  STATUS        current
  DESCRIPTION " Registration Delay Value

                The maximum number of seconds that the system uses to apply a
                random algorithm, which is used to determine a delay before
                requesting a user registration or an endpoint registration.
                When the value is 0, the request registration is done
                immediately.

                Note: The random algorithm applies individually to all
                registrations meaning registrations order may not follow their
                corresponding index.

                This value is expressed in second(s).


                "
  DEFVAL        { 0 }
  ::= { interopGroup 5700 }

 -- Scalar:Unsupported Content-Type

 interopUnsupportedContentType OBJECT-TYPE
  SYNTAX        INTEGER { reject(100) , allow(200) , ignore(300) }
  MAX-ACCESS    read-write
  STATUS        current
  DESCRIPTION " Unsupported Content-Type

                Determines the behaviour of the device upon reception of a SIP
                packet containing multiple unsupported Content-Type in the
                payload.

                  * Reject: Unsupported Content-Type are rejected.
                  * Allow: Unsupported Content-Type are allowed and ignored if
                    at least one Content-Type is supported.
                  * Ignore: Unsupported Content-Type are ignored.

                Note: When ignored, unsupported Content-Type are treated as if
                they were not present in the packet.
                "
  DEFVAL        { reject }
  ::= { interopGroup 5800 }

 -- Scalar:Wait for Confirmed Dialog in Blind Transfers

 interopWaitConfirmedDialogForBlindTransfer OBJECT-TYPE
  SYNTAX        MxEnableState
  MAX-ACCESS    read-write
  STATUS        deprecated
  DESCRIPTION " Wait for Confirmed Dialog in Blind Transfers

                Deprecated: The use of the TransferGroup.BlindTransferMethod
                instead of
                InteropGroup.InteropWaitConfirmedDialogForBlindTransfer is
                recommended. Determines whether the application waits for a
                confirmed dialog (i.e. waits until receiving a 200 OK
                response) before sending the REFER request when acting as a
                transferor in a blind transfer.

                  * Disable: The application does not wait for the 200 OK
                    response before sending the REFER request, causing the
                    call transfer to be executed before the target answers.
                    The transferee and the target are connected together early
                    and the transferee can hear the ringback from the target
                    until the target answers.
                  * Enable: The application waits for the 200 OK response
                    before sending the REFER request. The call transfer is
                    thus compatible with devices that strictly comply to the
                    following clause from RFC 3891 section 3, which states
                    that a User Agent Server shall refuse a Replaces Header
                    received while still in an early dialog that was not
                    initiated by the UA itself: 'If the Replaces header field
                    matches an early dialog that was not initiated by this UA,
                    it returns a 481 (Call/Transaction Does Not Exist)
                    response to the new INVITE, and leaves the matched dialog
                    unchanged.' Using this configuration, the transfer target
                    must answer the call before the transferee can get out of
                    the hold state.


                "
  DEFVAL        { disable }
  ::= { interopGroup 5900 }

 -- Scalar:Maximum Waiting Time for a Pending Blind Transfer

 interopPendingBlindTransferTimeout OBJECT-TYPE
  SYNTAX        Unsigned32 ( 5..600 )
  MAX-ACCESS    read-write
  STATUS        current
  DESCRIPTION " Maximum Waiting Time for a Pending Blind Transfer

                The maximum number of seconds that the system keeps a blind
                transfer pending (waiting for a 200 OK response) when the
                variable InteropWaitConfirmedDialogForBlindTransfer is set to
                Enable. If the timeout expires, the call transfer is
                cancelled.
                "
  DEFVAL        { 30 }
  ::= { interopGroup 6000 }

 -- Scalar:Forked Provisional Reponses Behavior

 interopForkedProvisionalResponsesBehavior OBJECT-TYPE
  SYNTAX        INTEGER { interpretFirst(100) , interpretAll(200) }
  MAX-ACCESS    read-write
  STATUS        current
  DESCRIPTION " Forked Provisional Reponses Behavior

                Configure the unit's behavior when receiving forked
                provisional answers.

                  * InterpretFirst: Only the first provisional answer is
                    interpreted. Following responses do not change the state
                    of the call and the SDP is ignored if present.
                  * InterpretAll: Each forked provisional response received by
                    the unit is interpreted replacing the previous one. If the
                    response contains SDP, it replaces previous answers if
                    any.

                This configuration has no effect if the UACPrackSupport
                variable is set to a value other than 'Unsupported'.


                "
  DEFVAL        { interpretFirst }
  ::= { interopGroup 6100 }

 -- Scalar:Interop SIP Contact Display Name Presence

 interopSipContactDisplayNamePresence OBJECT-TYPE
  SYNTAX        MxEnableState
  MAX-ACCESS    read-write
  STATUS        current
  DESCRIPTION " Interop SIP Contact Display Name Presence

                Determines if the display name appears in the SIP Contact
                header sent by the unit.

                  * Enable : The display name parameter appears in the SIP
                    Contact header of sent SIP request.
                  * Disable : The display name does not appear.


                "
  DEFVAL        { enable }
  ::= { interopGroup 6200 }

 -- Scalar:Interop Escaped Display Format

 interopEscapeFormat OBJECT-TYPE
  SYNTAX        INTEGER { lowercaseHex(100) , uppercaseHex(200) }
  MAX-ACCESS    read-write
  STATUS        current
  DESCRIPTION " Interop Escaped Display Format

                Configures the format of the escaped characters in all SIP
                header.

                  * LowercaseHex: Escaped characters are displayed in a
                    lowercase hexadecimals format.
                  * UppercaseHex: Escaped characters are displayed in a
                    uppercase hexadecimals format.


                "
  DEFVAL        { lowercaseHex }
  ::= { interopGroup 6300 }

 -- ***************************************************************************
 
 -- Group:DTMF Group

 -- ***************************************************************************
 
 interopDtmfGroup OBJECT IDENTIFIER
  ::= { interopGroup 50000 }
  -- Scalar:DTMF Transport Method With SIP

  interopDtmfTransportMethod OBJECT-TYPE
   SYNTAX        INTEGER { draftChoudhuriSipInfoDigit00(100) , infoDtmfRelay
                 (200) }
   MAX-ACCESS    read-write
   STATUS        current
   DESCRIPTION " DTMF Transport Method With SIP

                 Configures the method used to transmit DTMFs over the SIP
                 protocol.

                 This variable is effective only if the endpoint is configured
                 to use the DTMF out-of-band by protocol transport method
                 ('OutOfBandUsingSignalingProtocol'; refer to the variable
                 DefaultDtmfTransportMethod).

                   * DraftChoudhuriSipInfoDigit00: Transmit DTMFs by using the
                     method defined in the draft
                     'draft-choudhuri-sip-info-digit-00'.
                   * InfoDtmfRelay: Transmit DTMFs by using a custom method.

                 This custom method requires no SDP negotiation and uses a SIP
                 INFO message with a content of type 'application/dtmf-relay'.


                 "
   DEFVAL        { draftChoudhuriSipInfoDigit00 }
   ::= { interopDtmfGroup 100 }

  -- Scalar:DTMF Duration

  interopDtmfTransportDuration OBJECT-TYPE
   SYNTAX        Integer32 ( 50..2000 )
   MAX-ACCESS    read-write
   STATUS        current
   DESCRIPTION " DTMF Duration

                 Configures the DTMF duration sent in the INFO message when
                 using the 'InfoDtmfRelay' method (refer to the
                 InteropDtmfTransportMethod variable).

                 This value is expressed in milliseconds (ms).


                 "
   DEFVAL        { 100 }
   ::= { interopDtmfGroup 200 }

 -- End of group:DTMF Group

-- End of group:Interop Group

-- ****************************************************************************

-- Group:Monitoring Group

-- ****************************************************************************

monitoringGroup OBJECT IDENTIFIER
 ::= { sipEpMIBObjects 50500 }
 -- Scalar:Sip Notifications Gateway

 sipNotificationsGateway OBJECT-TYPE
  SYNTAX        OCTET STRING
  MAX-ACCESS    read-write
  STATUS        current
  DESCRIPTION " Sip Notifications Gateway

                Defines the SIP gateway used to send SIP NOTIFY containing the
                notification events. Notification events are configured in the
                Nlm.Events table.
                "
  DEFVAL        { "default" }
  ::= { monitoringGroup 100 }

 -- Scalar:Maximal Number of Notifications Per Notify

 maxNotificationsPerNotify OBJECT-TYPE
  SYNTAX        Unsigned32 ( 1..25 )
  MAX-ACCESS    read-write
  STATUS        current
  DESCRIPTION " Maximal Number of Notifications Per Notify

                Defines the maximal number of notification events the device
                may have to send in one SIP NOTIFY request. Notifications are
                sent in XML elements through the SIP NOTIFY's body request.
                "
  DEFVAL        { 5 }
  ::= { monitoringGroup 200 }

-- End of group:Monitoring Group

-- ****************************************************************************

-- Group:Debug Group

-- ****************************************************************************

debugGroup OBJECT IDENTIFIER
 ::= { sipEpMIBObjects 51000 }
 -- Scalar:Enable/Disable Debug Signaling Log

 debugSignalingLogEnable OBJECT-TYPE
  SYNTAX        MxEnableState
  MAX-ACCESS    read-write
  STATUS        current
  DESCRIPTION " Enable/Disable Debug Signaling Log

                Enables the logging client debugging tool for IP telephony
                signaling.
                "
  DEFVAL        { disable }
  ::= { debugGroup 100 }

 -- Scalar:Debug Signaling Log Host

 debugSignalingLogHost OBJECT-TYPE
  SYNTAX        MxIpHostNamePort
  MAX-ACCESS    read-write
  STATUS        current
  DESCRIPTION " Debug Signaling Log Host

                Logging client FQDN and port.

                The default port is 6000.


                "
  DEFVAL        { "192.168.10.10:0" }
  ::= { debugGroup 200 }

 -- Scalar:Debug Snapshot Time

 debugContextSnapshotTime OBJECT-TYPE
  SYNTAX        Unsigned32 ( 0..10080 )
  MAX-ACCESS    read-write
  STATUS        current
  DESCRIPTION " Debug Snapshot Time

                Sets the time between snapshots.

                The list of contexts currently in use in the sipFramework and
                sipApplication are periodically output as debug-level syslog
                messages.

                Note that for this feature to work, the system log severity
                level must be set to 'debug', and the syslog feature must be
                properly configured.

                Note that enabling this feature also triggers an instant
                snapshot.

                To disable this feature, set this variable to zero (0).

                This value is expressed in minutes (min).


                "
  DEFVAL        { 0 }
  ::= { debugGroup 300 }

-- End of group:Debug Group

-- ****************************************************************************

-- Group:Notification Messages Configuration

-- ****************************************************************************

notificationsGroup OBJECT IDENTIFIER
 ::= { sipEpMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { sipEpMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
