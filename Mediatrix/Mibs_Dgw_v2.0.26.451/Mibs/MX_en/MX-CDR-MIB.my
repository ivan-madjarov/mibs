-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


MX-CDR-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpAddress,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

cdrMIB MODULE-IDENTITY
 LAST-UPDATED   "1104190000Z"
 ORGANIZATION " Mediatrix Telecom, Inc. "
 CONTACT-INFO " Mediatrix Telecom, Inc.
                4229, Garlock Street
                Sherbrooke (Quebec)
                Canada
                Phone: (819) 829-8749
                "
 DESCRIPTION  " Call Detail Record

                Call detail record (CDR) in voice over IP (VoIP) contains
                information about recent system usage such as the identities of
                sources (points of origin), the identities of destinations
                (endpoints), the duration of each call, the total usage time in
                the billing period and many others.
                "
 -- ****************************************************************************
 
 -- Revision history
 -- ****************************************************************************
 REVISION       "1104190000Z"
 DESCRIPTION  " Initial Revision "
 REVISION       "1105310000Z"
 DESCRIPTION  " Variable SyslogFormat : corrected typo with %ocdnum and
                description with %id. "
 REVISION       "1106220000Z"
 DESCRIPTION  " Added new supported macros %sipdr and %pdd in variable
                SyslogFormat. "
 ::= { mediatrixServices 4200 }

cdrMIBObjects OBJECT IDENTIFIER ::= { cdrMIB 1 }

-- ****************************************************************************

-- Group:Syslog Group

-- ****************************************************************************

syslogGroup OBJECT IDENTIFIER
 ::= { cdrMIBObjects 400 }
 -- Scalar:Syslog CDR Remote Host

 syslogRemoteHost OBJECT-TYPE
  SYNTAX        MxIpHostNamePort
  MAX-ACCESS    read-write
  STATUS        current
  DESCRIPTION " Syslog CDR Remote Host

                Host name and port number of the device that archives CDR log
                entries. Specifying no port (or port 0) sends notifications to
                port 514.
                "
  DEFVAL        { "" }
  ::= { syslogGroup 100 }

 -- Scalar:Syslog CDR Format

 syslogFormat OBJECT-TYPE
  SYNTAX        OCTET STRING ( SIZE(0..1024) )
  MAX-ACCESS    read-write
  STATUS        current
  DESCRIPTION " Syslog CDR Format

                Specifies the format of the syslog Call Detail Record.

                Formal Syntax Description of the Protocol

                  * Precision=DIGIT
                  * Width=DIGIT
                  * MacroId=(ALPHA / '_')
                  * Macro=%[Width]|[.Precision]|[Width.Precision]MacroId

                The Width field is the minimum width of the converted
                argument. If the converted argument has fewer characters than
                the specified field width, then it is padded with spaces. If
                the converted argument has more characters than the specified
                field width, the field width is extended to whatever is
                required.

                The Precision field specifies the maximum number of characters
                to be printed from a string.

                Examples : sipid=SipUser001

                  * CDR Log : %sipid --> CDR Log : SipUser001
                  * CDR Log : %15sipid --> CDR Log : SipUser001
                  * CDR Log : %15.5sipid --> CDR Log : SipUs
                  * CDR Log : %.5sipid --> CDR Log : SipUs

                Call Detail Record predefined macros

                Control characters

                  * %% : %
                  * \n : Split message

                Call detail record macros

                  * %id : CDR Id. The CDR ID is unique. The ID is incremented
                    by one each time it is represented in a CDR record.
                  * %sipid : SIP call ID. Blank if no SIP interface was used
                    during the call.
                  * %ocgnum : Original calling number. Calling number as
                    received by the unit.
                  * %cgnum : Calling number. Calling number after manipulation
                    by the call router.
                  * %ocdnum : Original called number. Called number as
                    received by the unit.
                  * %cdnum : Called number. Called number after manipulation
                    by the call router.
                  * %oiname : Origin interface name. Interface on which the
                    call was received. Ex. isdn-Slot2/Pri1.
                  * %diname : Destination interface name. Interface on which
                    the call was relayed. Ex. SIP-Default.
                  * %chan : Channel number. Blank if no PRI/BRI interface was
                    used during the call. If 2 PRI/BRI interfaces were
                    involved, display the originating interface.
                  * %sipla : SIP local IP address.
                  * %sipra : SIP remote IP address or FQDN (next hop).
                  * %siprp : SIP remote port (next hop).
                  * %mra : Media remote IP address. Source IP address of the
                    incoming media stream. If the stream was modified during
                    the call, display the last stream.
                  * %mrsp : Media remote source port. Source port of the
                    incoming media stream. If the stream was modified during
                    the call, display the last stream.
                  * %mrp : Media remote port. Destination port of the outgoing
                    media stream. If the stream was modified during the call,
                    display the last stream.
                  * %tz : Local time zone
                  * %cd : Call duration (in seconds) (connect/disconnect).
                  * %sd : Call duration (in seconds) (setup/connect).
                  * %pdd : Post dial delay (in seconds) (setup/progress).
                  * %css : Call setup second (local time)
                  * %csm : Call setup minute (local time)
                  * %csh : Call setup hour (local time)
                  * %csd : Call setup day (local time)
                  * %csmm : Call setup month (local time)
                  * %csy : Call setup year (local time)
                  * %ccs : Call connect second (local time)
                  * %ccm : Call connect minute (local time)
                  * %cch : Call connect hour (local time)
                  * %ccd : Call connect day (local time)
                  * %ccmm : Call connect month (local time)
                  * %ccy : Call connect year (local time)
                  * %cds : Call disconnect second (local time)
                  * %cdm : Call disconnect minute (local time)
                  * %cdh : Call disconnect hour (local time)
                  * %cdd : Call disconnect day (local time)
                  * %cdmm : Call disconnect month (local time)
                  * %cdy : Call disconnect year (local time)
                  * %miptxc : IP Media last transmitted codec
                  * %miptxp : IP Media last transmitted p-time
                  * %dr : Disconnect reason (ISDN reason codes with ISUP SIP
                    mapping)
                  * %rxp : Received media packets. Excluding T.38.
                  * %txp : Transmitted media packets. Excluding T.38.
                  * %rxpl : Received media packets lost. Excluding T.38.
                  * %rxmd : Received packets mean playout delay (ms, 2
                    decimals). Excluding T.38.
                  * %rxaj : Received packets average jitter (ms, 2 decimals).
                    Excluding T.38.
                  * %sipdr : SIP disconnect or rejection reason.


                "
  DEFVAL        { "" }
  ::= { syslogGroup 200 }

 -- Scalar:Syslog CDR Facility

 syslogFacility OBJECT-TYPE
  SYNTAX        INTEGER { local0(100) , local1(200) , local2(300) , local3
                (400) , local4(500) , local5(600) , local6(700) , local7(800)
                }
  MAX-ACCESS    read-write
  STATUS        current
  DESCRIPTION " Syslog CDR Facility

                Syslog facility used by the unit to route the Call Detail
                Record messages. The application can use local0 through
                local7.
                "
  DEFVAL        { local0 }
  ::= { syslogGroup 300 }

-- End of group:Syslog Group

-- ****************************************************************************

-- Group:Notification Messages Configuration

-- ****************************************************************************

notificationsGroup OBJECT IDENTIFIER
 ::= { cdrMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { cdrMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
