-- ****************************************************************************
-- ****************************************************************************
--             Copyright(c) 2005 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************

SEC10-MX-SNMPEX-MIB
DEFINITIONS ::= BEGIN

IMPORTS
        MODULE-IDENTITY,
        OBJECT-TYPE,
        Unsigned32
    FROM SNMPv2-SMI
        snmpMIBObjects
    FROM SEC10-MX-SNMP-MIB;

snmpExMIB MODULE-IDENTITY
    LAST-UPDATED   "0411150000Z"
    ORGANIZATION " Mediatrix Telecom, Inc. "
    CONTACT-INFO " Mediatrix Telecom, Inc.
                   4229, Garlock Street
                   Sherbrooke (Quebec)
                   Canada
                   Phone: (819) 829-8749
                   "
    DESCRIPTION  " SNMP service

                   This service allows accesses to internal variables through
                   an SNMP client.
                   "
    -- *************************************************************************

    -- Revision history

    -- *************************************************************************
    REVISION       "0411150000Z"
    DESCRIPTION  " Initial Revision "
    ::= { snmpMIBObjects 100 }

snmpExMIBObjects OBJECT IDENTIFIER ::= { snmpExMIB 1 }

-- *****************************************************************************

-- Group:  Access

-- *****************************************************************************

access OBJECT IDENTIFIER
    ::= { snmpExMIBObjects 100 }


    -- Scalar:  Last result

    lastResult OBJECT-TYPE
        SYNTAX         OCTET STRING
        MAX-ACCESS     read-only
        STATUS         current
        DESCRIPTION  " Last result

                       Allow retreiving the last snmp request result.
                       "
        ::= { access 100 }

    -- Scalar:  Command

    command OBJECT-TYPE
        SYNTAX         OCTET STRING
        MAX-ACCESS     read-write
        STATUS         current
        DESCRIPTION  " Command

                       Allows executing a command.
                       "
        ::= { access 200 }

-- End of group:  Access

END
