-- ****************************************************************************
-- ****************************************************************************
--
--             Copyright(c) 2001-2002 Mediatrix Telecom, Inc.
--
--  NOTICE:
--   This document contains information that is confidential and proprietary
--   to Mediatrix Telecom, Inc.
--
--   Mediatrix Telecom, Inc. reserves all rights to this document as well as
--   to the Intellectual Property of the document and the technology and
--   know-how that it includes and represents.
--
--   This publication cannot be reproduced, neither in whole nor in part in
--   any form whatsoever without written prior approval by
--   Mediatrix Telecom, Inc.
--
--   Mediatrix Telecom, Inc. reserves the right to revise this publication
--   and make changes at any time and without the obligation to notify any
--   person and/or entity of such revisions and/or changes.
--
-- ****************************************************************************
-- ****************************************************************************

SIP43-MX-TELEPHONY-SERVICES-MIB
DEFINITIONS ::= BEGIN

IMPORTS
        MODULE-IDENTITY,
        OBJECT-TYPE,
        Unsigned32
    FROM SNMPv2-SMI
        MODULE-COMPLIANCE,
        OBJECT-GROUP
    FROM SNMPv2-CONF
        ifIndex
    FROM RFC1213-MIB
        mediatrixConfig
    FROM MX-SMI;

telephonyServicesMIB MODULE-IDENTITY
    LAST-UPDATED "0311030000Z"
    ORGANIZATION "Mediatrix Telecom, Inc."
    CONTACT-INFO "Mediatrix Telecom, Inc.
                  4229, Garlock Street
                  Sherbrooke (Quebec)
                  Canada
                  Phone: (819) 829-8749
                  "
    DESCRIPTION  "This MIB is used to configure the availability of the different
                  basic telephony services, such as call hold and conference,
                  as well as more advanced services, such as call waiting and
                  call forwarding preferences."


    -- ************************************************************************
    -- Revision history
    -- ************************************************************************
    REVISION    "0311030000Z"
    DESCRIPTION "November 3rd, 2003
                    Amended description of the telephonyServicesConferenceEnable
                    variable to specify the enabling of at least one PCM codec
                    as a prerequisite to the enabling of the service.
                 October 04, 2002
                    Fixed an error in the description of
                    telephonyServicesIfAutoSpeedDialTable
                 July 02, 2002
                    Added range for no answer timeout
                 May 28, 2002
                    Reordered status table for basic services
                 May 23, 2002
                    Added new status variables
                 January 18, 2002
                    Creation"
    ::= { mediatrixConfig 60 }

telephonyServicesMIBObjects OBJECT IDENTIFIER ::= { telephonyServicesMIB 1 }
telephonyServicesConformance OBJECT IDENTIFIER ::= { telephonyServicesMIB 2 }


    -- ************************************************************************
    -- Enable/Disable Telephone Service table parameters
    -- ************************************************************************
    telephonyServicesIfActivationTable OBJECT-TYPE
        SYNTAX      SEQUENCE OF TelephonyServicesIfActivationEntry
        MAX-ACCESS  not-accessible
        STATUS      current
        DESCRIPTION "A table of the basic telephony services configuration for
                     the interface, indexed by the interface number."
        ::= { telephonyServicesMIBObjects 10 }

        telephonyServicesIfActivationEntry OBJECT-TYPE
            SYNTAX      TelephonyServicesIfActivationEntry
            MAX-ACCESS  not-accessible
            STATUS      current
            DESCRIPTION "A row in the telephonyServicesIfActivationTable table.
                         It contains the configuration of the basic telephony
                         services for this interface."
            INDEX       {
                            ifIndex
                        }
            ::= { telephonyServicesIfActivationTable 1 }

            TelephonyServicesIfActivationEntry ::= SEQUENCE
                {
                    telephonyServicesHoldEnable             INTEGER,
                    telephonyServicesCallWaitingEnable      INTEGER,
                    telephonyServicesSecondCallEnable       INTEGER,
                    telephonyServicesBlindTransferEnable    INTEGER,
                    telephonyServicesAttendedTransferEnable INTEGER,
                    telephonyServicesConferenceEnable       INTEGER
                }

            telephonyServicesHoldEnable OBJECT-TYPE
                SYNTAX  INTEGER {
                                  disable(0),
                                  enable(1)
                                }
                MAX-ACCESS  read-write
                STATUS      current
                DESCRIPTION "Enable/Disable the holding service.

                             With this service enabled, an active call can be
                             temporarily put on hold, usually by using the 'flash'
                             button of the telephone. The user can resume the
                             call in the same way.

                             This service has no dependencies on other services
                             being enabled."
                DEFVAL      { enable }
                ::= { telephonyServicesIfActivationEntry 5 }

            telephonyServicesCallWaitingEnable OBJECT-TYPE
                SYNTAX  INTEGER {
                                  disable(0),
                                  enable(1)
                                }
                MAX-ACCESS  read-write
                STATUS      current
                DESCRIPTION "Enable/Disable the call waiting service.

                             With this service enabled, new calls received by an
                             endpoint during an already active call on that
                             endpoint will result in the endpoint hearing a
                             special tone indicating that a call is waiting on
                             the second line. The user can then answer that
                             call by using the 'flash' button of the telephone.
			     The user will then be able to switch between the two
			     active calls by using the 'flash' button.

                             For this service to be enabled, the call hold
                             service must be enabled as well.

                             See telephonyServicesHoldEnable."
                DEFVAL      { enable }
                ::= { telephonyServicesIfActivationEntry 10 }

            telephonyServicesSecondCallEnable OBJECT-TYPE
                SYNTAX  INTEGER {
                                  disable(0),
                                  enable(1)
                                }
                MAX-ACCESS  read-write
                STATUS      current
                DESCRIPTION "Enable/Disable the second call service.

                             With this service enabled, a user with an active
                             call can put the call on hold, and initiate a new
			     call on the second line.

                             This service is most useful in cunjunction with the
                             transfer and conference services.

                             For this service to be enabled, the call hold
                             service must be enabled as well.

                             See telephonyServicesHoldEnable."
                DEFVAL      { enable }
                ::= { telephonyServicesIfActivationEntry 15 }

            telephonyServicesBlindTransferEnable OBJECT-TYPE
                SYNTAX  INTEGER {
                                  disable(0),
                                  enable(1)
                                }
                MAX-ACCESS  read-write
                STATUS      current
                DESCRIPTION "Enable/Disable the blind call transfer service,
                             sometimes called Transfer without Consultation, or
                             Unattended Transfer.

                             With this service enabled, a user can transfer
                             a call on hold to a still ringing (unanswered) call.

                             Starting with an active call, a user can put the
                             call on hold, initiate a call to a third party,
                             then transfer the participant that is currently
                             on hold to the third party. This must be done
                             before the third party has answered. In case the
                             third party anwsers, the transfer becomes an
                             Attended Transfer.

                             The transfer is triggerred by the user hanging up
                             his/her handset.

                             The remaining calls (held call and ringing call
                             with third party) are then connected together. The
                             held call will be automatically unheld and will
                             hear the ringback tone provided by the third
                             party's ringing.

                             For this service to be enabled, the call hold AND
                             second call services must be enabled as well.

                             See telephonyServicesHoldEnable and
                             telephonyServicesSecondCallEnable.

                             Also see telephonyServicesAttendedTransferEnable
                             for a variation of the transfer method."
                DEFVAL      { enable }
                ::= { telephonyServicesIfActivationEntry 20 }

            telephonyServicesAttendedTransferEnable OBJECT-TYPE
                SYNTAX  INTEGER {
                                  disable(0),
                                  enable(1)
                                }
                MAX-ACCESS  read-write
                STATUS      current
                DESCRIPTION "Enable/Disable the attented call transfer service,
                             sometimes called Transfer with Consultation.

                             With this service enabled, a user can transfer a
                             call on hold to an active call.

                             Starting with an active call, a user can put the
                             call on hold, initiate a call to a third party,
                             wait for the third party to answer, then transfer
                             the participant that is currently on hold to the
                             third party.

                             The transfer is triggerred by the user hanging up
                             his/her handset. The remaining calls (held call and
                             active call with third party) are then connected
                             together.

                             For this service to be enabled, the call hold AND
                             second call services must be enabled as well.

                             See telephonyServicesHoldEnable and
                             telephonyServicesSecondCallEnable."
                DEFVAL      { enable }
                ::= { telephonyServicesIfActivationEntry 25 }

            telephonyServicesConferenceEnable OBJECT-TYPE
                SYNTAX  INTEGER {
                                  disable(0),
                                  enable(1)
                                }
                MAX-ACCESS  read-write
                STATUS      current
                DESCRIPTION "Enable/Disable the call conference service.

                             With this service enabled, a user can link two
                             or more calls together to form a single
                             conversation, called a conference.

                             Starting with an active call, a user can put the
                             call on hold, initiate a call to a third party,
                             wait for the third party to answer, and then use the
                             'flash' button of the telephone to start the conference
                             with the call that is already on hold.

                             * Currently, only 3-way conferences are supported.

                             * Currently, a participant of the conference can put
			       the conference on hold and attempt other calls. This
			       participant may then rejoin the conference at a later
			       time by unholding it. The endpoint that has initiated
			       the conference is NOT able to put the conference on hold.

                             For this service to be enabled, the call hold AND
                             second call services must be enabled, ALONG with at
                             least one PCM codec.

                             See telephonyServicesHoldEnable,
                             telephonyServicesSecondCallEnable,
                             voiceIfCodecPcmuEnable and voiceIfCodecPcmaEnable."
                DEFVAL      { enable }
                ::= { telephonyServicesIfActivationEntry 30 }


    -- ************************************************************************
    --  Telephone Service Status table parameters
    -- ************************************************************************
    telephonyServicesIfStatusTable OBJECT-TYPE
        SYNTAX      SEQUENCE OF TelephonyServicesIfStatusEntry
        MAX-ACCESS  not-accessible
        STATUS      current
        DESCRIPTION "A table of the basic telephony services statuses for
                     the interface, indexed by the interface number."
        ::= { telephonyServicesMIBObjects 15 }

        telephonyServicesIfStatusEntry OBJECT-TYPE
            SYNTAX      TelephonyServicesIfStatusEntry
            MAX-ACCESS  not-accessible
            STATUS      current
            DESCRIPTION "A row in the telephonyServicesIfStatusTable table.
                         It contains the status of the basic telephony
                         services for this interface."
            INDEX       {
                            ifIndex
                        }
            ::= { telephonyServicesIfStatusTable 1 }

            TelephonyServicesIfStatusEntry ::= SEQUENCE
                {
                    telephonyServicesHoldStatus             INTEGER,
                    telephonyServicesCallWaitingStatus      INTEGER,
                    telephonyServicesSecondCallStatus       INTEGER,
                    telephonyServicesBlindTransferStatus    INTEGER,
                    telephonyServicesAttendedTransferStatus INTEGER,
                    telephonyServicesConferenceStatus       INTEGER
                }


            telephonyServicesHoldStatus OBJECT-TYPE
                SYNTAX  INTEGER {
                                  inactive(0),
                                  active(1)
                                }
                MAX-ACCESS  read-only
                STATUS      current
                DESCRIPTION "Status of the holding service.

                             See telephonyServicesHoldEnable."
                DEFVAL      { active }
                ::= { telephonyServicesIfStatusEntry 5 }

            telephonyServicesCallWaitingStatus OBJECT-TYPE
                SYNTAX  INTEGER {
                                  inactive(0),
                                  active(1)
                                }
                MAX-ACCESS  read-only
                STATUS      current
                DESCRIPTION "Status of the call waiting service.

                             See telephonyServicesCallWaitingEnable."
                DEFVAL      { active }
                ::= { telephonyServicesIfStatusEntry 10 }

            telephonyServicesSecondCallStatus OBJECT-TYPE
                SYNTAX  INTEGER {
                                  inactive(0),
                                  active(1)
                                }
                MAX-ACCESS  read-only
                STATUS      current
                DESCRIPTION "Status of the second call service.

                             See telephonyServicesSecondCallEnable."
                DEFVAL      { active }
                ::= { telephonyServicesIfStatusEntry 15 }

            telephonyServicesBlindTransferStatus OBJECT-TYPE
                SYNTAX  INTEGER {
                                  inactive(0),
                                  active(1)
                                }
                MAX-ACCESS  read-only
                STATUS      current
                DESCRIPTION "Status of the blind transfer service.

                             See telephonyServicesBlindTransferEnable."
                DEFVAL      { active }
                ::= { telephonyServicesIfStatusEntry 20 }

            telephonyServicesAttendedTransferStatus OBJECT-TYPE
                SYNTAX  INTEGER {
                                  inactive(0),
                                  active(1)
                                }
                MAX-ACCESS  read-only
                STATUS      current
                DESCRIPTION "Status of the attended transfer service.

                             See telephonyServicesAttendedTransferEnable."
                DEFVAL      { active }
                ::= { telephonyServicesIfStatusEntry 25 }

            telephonyServicesConferenceStatus OBJECT-TYPE
                SYNTAX  INTEGER {
                                  inactive(0),
                                  active(1)
                                }
                MAX-ACCESS  read-only
                STATUS      current
                DESCRIPTION "Status of the conference service.

                             See telephonyServicesConferenceEnable."
                DEFVAL      { active }
                ::= { telephonyServicesIfStatusEntry 30 }


    -- ************************************************************************
    -- Special Features
    -- ************************************************************************
    telephonyServicesCustomization OBJECT IDENTIFIER ::= { telephonyServicesMIBObjects 20 }

    -- ************************************************************************
    -- AutoSpeedDial
    -- ************************************************************************
    telephonyServicesAutoSpeedDial OBJECT IDENTIFIER ::= { telephonyServicesCustomization 10 }

    -- ************************************************************************
    -- Auto Speed Dial Table
    -- ************************************************************************
    telephonyServicesIfAutoSpeedDialTable OBJECT-TYPE
        SYNTAX      SEQUENCE OF TelephonyServicesIfAutoSpeedDialEntry
        MAX-ACCESS  not-accessible
        STATUS      current
        DESCRIPTION "A table of the auto speed dial service
                     customization for each interface, indexed by the interface
                     number."
        ::= { telephonyServicesAutoSpeedDial 10 }

        telephonyServicesIfAutoSpeedDialEntry OBJECT-TYPE
            SYNTAX      TelephonyServicesIfAutoSpeedDialEntry
            MAX-ACCESS  not-accessible
            STATUS      current
            DESCRIPTION "A row in the telephonyServicesIfAutoSpeedDialTable
                         table. It contains all the informations required to
                         customize the auto speed dial service for this
                         interface."
            INDEX       {
                            ifIndex
                        }
            ::= { telephonyServicesIfAutoSpeedDialTable 1 }

            TelephonyServicesIfAutoSpeedDialEntry ::= SEQUENCE
                {
                    telephonyServicesAutoSpeedDialEnable            INTEGER,
                    telephonyServicesAutoSpeedDialTargetAddress     OCTET STRING
                }

            telephonyServicesAutoSpeedDialEnable OBJECT-TYPE
                SYNTAX  INTEGER {
                                  disable(0),
                                  enable(1)
                                }
                MAX-ACCESS  read-write
                STATUS      current
                DESCRIPTION "Enable/Disable the auto speed dial service.
                             This service provides a 'redphone'-like experience.

                             If enabled, the target address is automatically
                             called when the user picks up the phone.

                             When this service is enabled, the second line service
                             will be disabled but the call waiting feature will
                             still be functionnal. The user can still accept
                             incoming calls.

                             See telephonyServicesAutoSpeedDialTargetAddress."
                DEFVAL      { disable }
                ::= { telephonyServicesIfAutoSpeedDialEntry 5 }

            telephonyServicesAutoSpeedDialTargetAddress OBJECT-TYPE
                SYNTAX  OCTET STRING (SIZE(0..127))
                MAX-ACCESS  read-write
                STATUS      current
                DESCRIPTION "A string that represents the address or telephone
                             number that the user wants to automatically call.

                             Accepted formats are phone numbers (5551111) or
                             'scheme:user@host' type strings (such as SipUrls).

                             For example, 'sip:user@foo.com'.

                             This string will be used literally, so cosmetic
                             symbols (such as the dash in '555-xxxx') should not
                             be present."
                DEFVAL      { "" }
                ::= { telephonyServicesIfAutoSpeedDialEntry 10 }

    -- ************************************************************************
    -- Call forwarding Customization group
    -- ************************************************************************
    telephonyServicesCallForwardCustomization OBJECT IDENTIFIER ::= { telephonyServicesCustomization 20 }

    -- ************************************************************************
    -- Call forwarding Unconditional
    -- ************************************************************************
    telephonyServicesCallForwardUnconditionnal OBJECT IDENTIFIER ::= { telephonyServicesCallForwardCustomization 5 }

    telephonyServicesCallForwardUnconditionnalEnableDigitMap OBJECT-TYPE
        SYNTAX  OCTET STRING (SIZE(2..10))
        MAX-ACCESS  read-write
        STATUS      current
        DESCRIPTION "Digit map the user can dial to enable the
                     application of the service.

                     This digit map must respect the syntax for digit
                     maps as declared in the digit maps MIB.

                     Note that dialing this digit map will not have any
                     effect unless the service's status is 'enabled'.

                     See
                     telephonyServicesCallForwardUnconditionnalEnable."
        DEFVAL      { "  " }
        ::= { telephonyServicesCallForwardUnconditionnal 5 }

    telephonyServicesCallForwardUnconditionnalDisableDigitMap OBJECT-TYPE
        SYNTAX  OCTET STRING (SIZE(2..10))
        MAX-ACCESS  read-write
        STATUS      current
        DESCRIPTION "Digit map the user can dial to disable the
                     application of the service.

                     This digit map must respect the syntax for digit
                     maps as declared in the digit maps MIB.

                     Note that dialing this digit map will not have any
                     effect unless the service's status is 'enabled'.

                     See telephonyServicesCallForwardUnconditionnalEnable."
        DEFVAL      { "  " }
        ::= { telephonyServicesCallForwardUnconditionnal 10 }


    -- ************************************************************************
    -- Call forwarding Unconditional Config Table
    -- ************************************************************************
    telephonyServicesIfCallForwardUnconditionnalTable OBJECT-TYPE
        SYNTAX      SEQUENCE OF TelephonyServicesIfCallForwardUnconditionnalEntry
        MAX-ACCESS  not-accessible
        STATUS      current
        DESCRIPTION "A table of the unconditional call forward service
                     customization for each interface, indexed by the interface
                     number."
        ::= { telephonyServicesCallForwardUnconditionnal 15 }

        telephonyServicesIfCallForwardUnconditionnalEntry OBJECT-TYPE
            SYNTAX      TelephonyServicesIfCallForwardUnconditionnalEntry
            MAX-ACCESS  not-accessible
            STATUS      current
            DESCRIPTION "A row in the
                         telephonyServicesIfCallForwardUnconditionnalTable
                         table. It contains all the informations required to
                         customize the unconditional call forwarding service
                         for this interface."
            INDEX       {
                            ifIndex
                        }
            ::= { telephonyServicesIfCallForwardUnconditionnalTable 1 }

            TelephonyServicesIfCallForwardUnconditionnalEntry ::= SEQUENCE
                {
                    telephonyServicesCallForwardUnconditionnalEnable            INTEGER,
                    telephonyServicesCallForwardUnconditionnalForwardingAddress OCTET STRING
                }

            telephonyServicesCallForwardUnconditionnalEnable OBJECT-TYPE
                SYNTAX  INTEGER {
                                  disable(0),
                                  enable(1)
                                }
                MAX-ACCESS  read-write
                STATUS      current
                DESCRIPTION "Enable/Disable the unconditional call forward
                             service.

                             This service allows a user to forward ALL incoming
                             calls to a specified target.  A short sound will be
                             emitted to alert the user that the call has been
                             forwarded, but the user will not be able to pick
                             up the call from that location.

                             If enabled, the user can dial the digit maps for
			     enabling and disabling this service.

                             See
                             telephonyServicesCallForwardUnconditionnalForwardingAddress."
                DEFVAL      { disable }
                ::= { telephonyServicesIfCallForwardUnconditionnalEntry 5 }

            telephonyServicesCallForwardUnconditionnalForwardingAddress OBJECT-TYPE
                SYNTAX  OCTET STRING (SIZE(0..127))
                MAX-ACCESS  read-write
                STATUS      current
                DESCRIPTION "A string that represents the address or telephone
                             number that the user wants to forward calls to.

                             Accepted formats are phone numbers (5551111) or
                             'scheme:user@host' type strings (such as SipUrls).

                             For example, 'sip:user@foo.com'.

                             This string will be used literally, so cosmetic
                             symbols (such as the dash in '555-xxxx') should not
                             be present."
                DEFVAL      { "" }
                ::= { telephonyServicesIfCallForwardUnconditionnalEntry 10 }


    -- ************************************************************************
    -- Call forwarding Unconditional Status Table
    -- ************************************************************************
    telephonyServicesIfCallForwardUnconditionnalStatusTable OBJECT-TYPE
        SYNTAX      SEQUENCE OF TelephonyServicesIfCallForwardUnconditionnalStatusEntry
        MAX-ACCESS  not-accessible
        STATUS      current
        DESCRIPTION "A table of the unconditional call forward service
                     customization for each interface, indexed by the interface
                     number."
        ::= { telephonyServicesCallForwardUnconditionnal 20 }

        telephonyServicesIfCallForwardUnconditionnalStatusEntry OBJECT-TYPE
            SYNTAX      TelephonyServicesIfCallForwardUnconditionnalStatusEntry
            MAX-ACCESS  not-accessible
            STATUS      current
            DESCRIPTION "A row in the
                         telephonyServicesIfCallForwardUnconditionnalStatusTable
                         table. It contains the status of the unconditional
                         call forwarding service for this interface."
            INDEX       {
                            ifIndex
                        }
            ::= { telephonyServicesIfCallForwardUnconditionnalStatusTable 1 }

            TelephonyServicesIfCallForwardUnconditionnalStatusEntry ::= SEQUENCE
                {
                    telephonyServicesCallForwardUnconditionnalStatus    INTEGER
                }

            telephonyServicesCallForwardUnconditionnalStatus OBJECT-TYPE
                SYNTAX  INTEGER {
                                  inactive(0),
                                  active(1)
                                }
                MAX-ACCESS  read-only
                STATUS      current
                DESCRIPTION "Status of the unconditional call forward service.

                             Using the digit maps configured for this service,
                             the user can use his/her handset to activate or
                             deactivate this service.

                             This variable will reflect the last command entered
                             by the user."
                DEFVAL      { inactive }
                ::= { telephonyServicesIfCallForwardUnconditionnalStatusEntry 5 }



    -- ************************************************************************
    -- Call forwarding On Busy
    -- ************************************************************************
    telephonyServicesCallForwardBusy OBJECT IDENTIFIER ::= { telephonyServicesCallForwardCustomization 10 }

    telephonyServicesCallForwardBusyEnableDigitMap OBJECT-TYPE
        SYNTAX  OCTET STRING (SIZE(2..10))
        MAX-ACCESS  read-write
        STATUS      current
        DESCRIPTION "Digit map the user can dial to enable the
                     application of the service.

                     This digit map must respect the syntax for digit
                     maps as declared in the digit maps MIB.

                     Note that dialing this digit map will not have any
                     effect unless the service's status is 'enabled'.

                     See telephonyServicesCallForwardBusyEnable."
        DEFVAL      { "  " }
        ::= { telephonyServicesCallForwardBusy 5 }

    telephonyServicesCallForwardBusyDisableDigitMap OBJECT-TYPE
        SYNTAX  OCTET STRING (SIZE(2..10))
        MAX-ACCESS  read-write
        STATUS      current
        DESCRIPTION "Digit map the user can dial to disable the
                     application of the service.

                     This digit map must respect the syntax for digit
                     maps as declared in the digit maps MIB.

                     Note that dialing this digit map will not have any
                     effect unless the service's status is 'enabled'.

                     See telephonyServicesCallForwardBusyEnable."
        DEFVAL      { "  " }
        ::= { telephonyServicesCallForwardBusy 10 }


    -- ************************************************************************
    -- Call forwarding On Busy Config Table
    -- ************************************************************************
    telephonyServicesIfCallForwardBusyTable OBJECT-TYPE
        SYNTAX      SEQUENCE OF TelephonyServicesIfCallForwardBusyEntry
        MAX-ACCESS  not-accessible
        STATUS      current
        DESCRIPTION "A table of the call forward busy service customization
                     for each interface, indexed by the interface number."
        ::= { telephonyServicesCallForwardBusy 15 }

        telephonyServicesIfCallForwardBusyEntry OBJECT-TYPE
            SYNTAX      TelephonyServicesIfCallForwardBusyEntry
            MAX-ACCESS  not-accessible
            STATUS      current
            DESCRIPTION "A row in the
                         telephonyServicesIfCallForwardBusyTable table. It
                         contains all the informations required to customize the
                         call forwarding busy service for this interface."
            INDEX       {
                            ifIndex
                        }
            ::= { telephonyServicesIfCallForwardBusyTable 1 }

            TelephonyServicesIfCallForwardBusyEntry ::= SEQUENCE
                {
                    telephonyServicesCallForwardBusyEnable            INTEGER,
                    telephonyServicesCallForwardBusyForwardingAddress OCTET STRING
                }

            telephonyServicesCallForwardBusyEnable OBJECT-TYPE
                SYNTAX  INTEGER {
                                  disable(0),
                                  enable(1)
                                }
                MAX-ACCESS  read-write
                STATUS      current
                DESCRIPTION "Enable/Disable the call forward busy service.

                             This service allows a user to forward incoming
                             calls to a specified target when the user is already
                             participating in another call.

                             The user will not have any feedback that a call was
                             forwarded.

                             If enabled, the user can dial the digit maps for
			     enabling and disabling this service.

                             See
                             telephonyServicesCallForwardBusyForwardingAddress."
                DEFVAL      { disable }
                ::= { telephonyServicesIfCallForwardBusyEntry 5 }

            telephonyServicesCallForwardBusyForwardingAddress OBJECT-TYPE
                SYNTAX  OCTET STRING (SIZE(0..127))
                MAX-ACCESS  read-write
                STATUS      current
                DESCRIPTION "A string that represents the address or telephone
                             number that the user wants to forward calls to.

                             Accepted formats are phone numbers (5551111) or
                             'scheme:user@host' type strings (such as SipUrls).

                             For example, 'sip:user@foo.com'.

                             This string will be used literally, so cosmetic
                             symbols (such as the dash in '555-xxxx') should not
                             be present."
                DEFVAL      { "" }
                ::= { telephonyServicesIfCallForwardBusyEntry 10 }


    -- ************************************************************************
    -- Call forwarding On Busy Status Table
    -- ************************************************************************
    telephonyServicesIfCallForwardBusyStatusTable OBJECT-TYPE
        SYNTAX      SEQUENCE OF TelephonyServicesIfCallForwardBusyStatusEntry
        MAX-ACCESS  not-accessible
        STATUS      current
        DESCRIPTION "A table of the call forward busy service status
                     for each interface, indexed by the interface number."
        ::= { telephonyServicesCallForwardBusy 20 }

        telephonyServicesIfCallForwardBusyStatusEntry OBJECT-TYPE
            SYNTAX      TelephonyServicesIfCallForwardBusyStatusEntry
            MAX-ACCESS  not-accessible
            STATUS      current
            DESCRIPTION "A row in the
                         telephonyServicesIfCallForwardBusyStatusTable table. It
                         contains the status of the call forwarding busy service
                         for this interface."
            INDEX       {
                            ifIndex
                        }
            ::= { telephonyServicesIfCallForwardBusyStatusTable 1 }

            TelephonyServicesIfCallForwardBusyStatusEntry ::= SEQUENCE
                {
                    telephonyServicesCallForwardBusyStatus            INTEGER
                }

            telephonyServicesCallForwardBusyStatus OBJECT-TYPE
                SYNTAX  INTEGER {
                                  inactive(0),
                                  active(1)
                                }
                MAX-ACCESS  read-only
                STATUS      current
                DESCRIPTION "Status of the call forward busy service.

                             Using the digit maps configured for this service,
                             the user can use his/her handset to activate or
                             deactivate this service.

                             This variable will reflect the last command entered
                             by the user."
                DEFVAL      { inactive }
                ::= { telephonyServicesIfCallForwardBusyStatusEntry 5 }


    -- ************************************************************************
    -- Call forwarding On No Answer
    -- ************************************************************************
    telephonyServicesCallForwardDontAnswer OBJECT IDENTIFIER ::= { telephonyServicesCallForwardCustomization 15 }

    telephonyServicesCallForwardDontAnswerEnableDigitMap OBJECT-TYPE
        SYNTAX  OCTET STRING (SIZE(2..10))
        MAX-ACCESS  read-write
        STATUS      current
        DESCRIPTION "Digit map the user can dial to enable the
                     application of the service.

                     This digit map must respect the syntax for digit
                     maps as declared in the digit maps MIB.

                     Note that dialing this digit map will not have any
                     effect unless the service's status is 'enabled'.

                     See telephonyServicesCallForwardDontAnswerEnable."
        DEFVAL      { "  " }
        ::= { telephonyServicesCallForwardDontAnswer 5 }

    telephonyServicesCallForwardDontAnswerDisableDigitMap OBJECT-TYPE
        SYNTAX  OCTET STRING (SIZE(2..10))
        MAX-ACCESS  read-write
        STATUS      current
        DESCRIPTION "Digit map the user can dial to disable the
                     application of the service.

                     This digit map must respect the syntax for digit
                     maps as declared in the digit maps MIB.

                     Note that dialing this digit map will not have any
                     effect unless the service's status is 'enabled'.

                     See telephonyServicesCallForwardDontAnswerEnable."
        DEFVAL      { "  " }
        ::= { telephonyServicesCallForwardDontAnswer 10 }


    -- ************************************************************************
    -- Call forwarding On No Answer Config Table
    -- ************************************************************************
    telephonyServicesIfCallForwardDontAnswerTable OBJECT-TYPE
        SYNTAX      SEQUENCE OF TelephonyServicesIfCallForwardDontAnswerEntry
        MAX-ACCESS  not-accessible
        STATUS      current
        DESCRIPTION "A table of the call forward don't answer service
                     customization for each interface, indexed by the interface
                     number."
        ::= { telephonyServicesCallForwardDontAnswer 15 }

        telephonyServicesIfCallForwardDontAnswerEntry OBJECT-TYPE
            SYNTAX      TelephonyServicesIfCallForwardDontAnswerEntry
            MAX-ACCESS  not-accessible
            STATUS      current
            DESCRIPTION "A row in the
                         telephonyServicesIfCallForwardDontAnswerTable
                         table. It contains all the informations required to
                         customize the call forwarding don't answer service
                         for this interface."
            INDEX       {
                            ifIndex
                        }
            ::= { telephonyServicesIfCallForwardDontAnswerTable 1 }

            TelephonyServicesIfCallForwardDontAnswerEntry ::= SEQUENCE
                {
                    telephonyServicesCallForwardDontAnswerEnable            INTEGER,
                    telephonyServicesCallForwardDontAnswerForwardingAddress OCTET STRING,
                    telephonyServicesCallForwardDontAnswerTimeout           Unsigned32
                }

            telephonyServicesCallForwardDontAnswerEnable OBJECT-TYPE
                SYNTAX  INTEGER {
                                  disable(0),
                                  enable(1)
                                }
                MAX-ACCESS  read-write
                STATUS      current
                DESCRIPTION "Enable/Disable the call forward don't answer
                             service.

                             This service allows a user to forward incoming
                             calls to a specified target when the user is unable
                             to pick up the call before a specified amount of
                             rings have been heard.

                             The user will not have any feedback that a call was
                             forwarded.

                             If enabled, the user can dial the digit maps for
			     enabling and disabling this service.

                             See
                             telephonyServicesCallForwardDontAnswerForwardingAddress
                             and
                             telephonyServicesCallForwardDontAnswerTimeout."
                DEFVAL      { disable }
                ::= { telephonyServicesIfCallForwardDontAnswerEntry 5 }

            telephonyServicesCallForwardDontAnswerForwardingAddress OBJECT-TYPE
                SYNTAX  OCTET STRING (SIZE(0..127))
                MAX-ACCESS  read-write
                STATUS      current
                DESCRIPTION "A string that represents the address or telephone
                             number that the user wants to forward calls to.

                             Accepted formats are phone numbers (5551111) or
                             'scheme:user@host' type strings (such as SipUrls).

                             For example, 'sip:user@foo.com'.

                             This string will be used literally, so cosmetic
                             symbols (such as the dash in '555-xxxx') should not
                             be present."
                DEFVAL      { "" }
                ::= { telephonyServicesIfCallForwardDontAnswerEntry 10 }

            telephonyServicesCallForwardDontAnswerTimeout OBJECT-TYPE
                SYNTAX  Unsigned32(200..120000)
                MAX-ACCESS  read-write
                STATUS      current
                DESCRIPTION "Time the telephone will keep ringing before the call
                             forwarding activates, in milliseconds."
                DEFVAL      { 5000 }
                ::= { telephonyServicesIfCallForwardDontAnswerEntry 15 }


    -- ************************************************************************
    -- Call forwarding On No Answer Status Table
    -- ************************************************************************
    telephonyServicesIfCallForwardDontAnswerStatusTable OBJECT-TYPE
        SYNTAX      SEQUENCE OF TelephonyServicesIfCallForwardDontAnswerStatusEntry
        MAX-ACCESS  not-accessible
        STATUS      current
        DESCRIPTION "A table of the call forward don't answer service
                     status for each interface, indexed by the interface
                     number."
        ::= { telephonyServicesCallForwardDontAnswer 20 }

        telephonyServicesIfCallForwardDontAnswerStatusEntry OBJECT-TYPE
            SYNTAX      TelephonyServicesIfCallForwardDontAnswerStatusEntry
            MAX-ACCESS  not-accessible
            STATUS      current
            DESCRIPTION "A row in the
                         telephonyServicesIfCallForwardDontAnswerStatusTable
                         table. It contains the status of the call forwarding
                         don't answer service for this interface."
            INDEX       {
                            ifIndex
                        }
            ::= { telephonyServicesIfCallForwardDontAnswerStatusTable 1 }

            TelephonyServicesIfCallForwardDontAnswerStatusEntry ::= SEQUENCE
                {
                    telephonyServicesCallForwardDontAnswerStatus            INTEGER
                }

            telephonyServicesCallForwardDontAnswerStatus OBJECT-TYPE
                SYNTAX  INTEGER {
                                  inactive(0),
                                  active(1)
                                }
                MAX-ACCESS  read-only
                STATUS      current
                DESCRIPTION "Status of the call forward don't answer service.

                             Using the digit maps configured for this service,
                             the user can use his/her handset to activate or
                             deactivate this service.

                             This variable will reflect the last command entered
                             by the user."
                DEFVAL      { inactive }
                ::= { telephonyServicesIfCallForwardDontAnswerStatusEntry 5 }


    -- ************************************************************************
    -- Call Waiting Customization group
    -- ************************************************************************
    telephonyServicesCallWaitingCustomization OBJECT IDENTIFIER ::= { telephonyServicesCustomization 30 }

    -- ************************************************************************
    -- Call Waiting Cancel
    -- ************************************************************************
    telephonyServicesCallWaitingCancel OBJECT IDENTIFIER ::= { telephonyServicesCallWaitingCustomization 5 }

    telephonyServicesCallWaitingCancelDigitMap OBJECT-TYPE
        SYNTAX  OCTET STRING (SIZE(2..10))
        MAX-ACCESS  read-write
        STATUS      current
        DESCRIPTION "Digit map the user can dial to enable the
                     application of the service.

                     This digit map must respect the syntax for digit
                     maps as declared in the digit maps MIB.

                     Note that dialing this digit map will not have any
                     effect unless the service's status is 'enabled'.

                     See telephonyServicesCallWaitingCancelEnable."
        DEFVAL      { "  " }
        ::= { telephonyServicesCallWaitingCancel 5 }

    -- ************************************************************************
    -- Call Waiting Cancel Table
    -- ************************************************************************
    telephonyServicesIfCallWaitingCancelTable OBJECT-TYPE
        SYNTAX      SEQUENCE OF TelephonyServicesIfCallWaitingCancelEntry
        MAX-ACCESS  not-accessible
        STATUS      current
        DESCRIPTION "A table of the call waiting cancel service
                     customization for each interface, indexed by the interface
                     number."
        ::= { telephonyServicesCallWaitingCancel 10 }

        telephonyServicesIfCallWaitingCancelEntry OBJECT-TYPE
            SYNTAX      TelephonyServicesIfCallWaitingCancelEntry
            MAX-ACCESS  not-accessible
            STATUS      current
            DESCRIPTION "A row in the
                         telephonyServicesIfCallWaitingCancelTable
                         table. It contains all the informations required to
                         customize the call waiting cancel service for this
                         interface."
            INDEX       {
                            ifIndex
                        }
            ::= { telephonyServicesIfCallWaitingCancelTable 1 }

            TelephonyServicesIfCallWaitingCancelEntry ::= SEQUENCE
                {
                    telephonyServicesCallWaitingCancelEnable            INTEGER
                }

            telephonyServicesCallWaitingCancelEnable OBJECT-TYPE
                SYNTAX  INTEGER {
                                  disable(0),
                                  enable(1)
                                }
                MAX-ACCESS  read-write
                STATUS      current
                DESCRIPTION "Enable/Disable the call waiting cancel service.

                             This service allows a user who has call waiting
                             enabled to disable that service on a per-call basis.

                             Dialing the 'enable' digit map for this service
                             will disable call waiting on the next call only. If,
                             for any reason, the user wishes to undo the cancel,
                             simply unhook and re-hook the telephone to reset
                             the service.

                             If enabled, the user can dial the digit maps for
			     enabling and disabling this service.

                             For this service to be enabled, the call hold
                             AND call waiting services must be enabled as well.

                             See telephonyServicesHoldEnable and
                             telephonyServicesCallWaitingEnable.

                             See telephonyServicesCallWaitingCancelDigitMap."
                DEFVAL      { disable }
                ::= { telephonyServicesIfCallWaitingCancelEntry 5 }


    -- ************************************************************************
    -- Urgent Gateway group
    -- ************************************************************************
    telephonyServicesUrgentGatewayCustomization OBJECT IDENTIFIER ::= { telephonyServicesCustomization 35 }

    telephonyServicesUrgentGatewayEnable OBJECT-TYPE
        SYNTAX  INTEGER {
                          disable(0),
                          enable(1)
                        }
        MAX-ACCESS  read-write
        STATUS      current
        DESCRIPTION "Enable/Disable the urgent gateway service.

                     This service allows a user to dial a special digit map
                     resulting in a message being sent to a specified urgent
                     gateway, bypassing any other intermediaries.

                     If enabled, whenever the user dials the specified digit map,
                     a message will be sent to the target address.

                     See telephonyServicesUrgentGatewayDigitMap and
                     telephonyServicesUrgentGatewayTargetAddress."
        DEFVAL      { disable }
        ::= { telephonyServicesUrgentGatewayCustomization 5 }

    telephonyServicesUrgentGatewayDigitMap OBJECT-TYPE
        SYNTAX  OCTET STRING (SIZE(2..10))
        MAX-ACCESS  read-write
        STATUS      current
        DESCRIPTION "Digit map the user must dial to initiate a call in urgent
                     mode.

                     This digit map must respect the syntax for digit
                     maps as declared in the digit maps MIB.

                     Note that dialing this digit map will not have any
                     effect unless the service's status is 'enabled'.

                     See telephonyServicesUrgentGatewayEnable."
        DEFVAL      { "  " }
        ::= { telephonyServicesUrgentGatewayCustomization 10 }

    telephonyServicesUrgentGatewayTargetAddress OBJECT-TYPE
        SYNTAX  OCTET STRING (SIZE(0..127))
        MAX-ACCESS  read-write
        STATUS      current
        DESCRIPTION "A string that represents the address or telephone
                     number that the user wants to automatically call when
                     he/she dials the emergency number.

                     Accepted formats are phone numbers (5551111) or
                     'scheme:user@host' type strings (such as SipUrls).

                     For example, 'sip:user@foo.com'.

                     This string will be used literally, so cosmetic
                     symbols (such as the dash in '555-xxxx') should not
                     be present."
        DEFVAL      { "" }
        ::= { telephonyServicesUrgentGatewayCustomization 15 }

    -- ************************************************************************
    -- IP Address Call group
    -- ************************************************************************
    telephonyServicesIpAddressCallCustomization OBJECT IDENTIFIER ::= { telephonyServicesCustomization 99 }

    telephonyServicesIpAddressCallEnable OBJECT-TYPE
        SYNTAX  INTEGER {
                          disable(0),
                          enable(1)
                        }
        MAX-ACCESS  read-write
        STATUS      current
        DESCRIPTION "Enable/Disable the direct IP address call service.
                     This service allows, for example, a user to make a SIP call
                     without the help of a SIP server.

                     If enabled, whenever the user dials an IP address
                     concatenated with a phone number, a message is sent to
                     the phone or fax connected to the target address.

                     To make an IP address call:
                        1. Dial '**'
                        2. Dial the numerical digits of the IP address and use
                           '*' for the '.' of the IP address.
                        3. Dial '#' to terminate the IP address.
                        4. Dial the phone number.

		     For instance, to reach the phone number '3330001' of the
                     unit with local IP address '192.168.0.23', the user dials
                     the following digits: **192*168*0*23#3330001 ."
        DEFVAL      { disable }
        ::= { telephonyServicesIpAddressCallCustomization 5 }

    -- ************************************************************************
    -- Conformance information
    -- ************************************************************************
    telephonyServicesCompliances OBJECT IDENTIFIER ::= { telephonyServicesConformance 1 }

    telephonyServicesComplVer1 MODULE-COMPLIANCE
        STATUS      current
        DESCRIPTION
            "List of groups required to support telephony services."
        MODULE  -- This Module
            MANDATORY-GROUPS {
                                telephonyServicesStatusVer1,
                                telephonyServicesActivationVer1,
                                telephonyServicesAutoSpeedDialVer1,
                                telephonyServicesCallForwardUnconditionnalStatusVer1,
                                telephonyServicesCallForwardUnconditionnalVer1,
                                telephonyServicesCallForwardBusyStatusVer1,
                                telephonyServicesCallForwardBusyVer1,
                                telephonyServicesCallForwardOnNoAnswerStatusVer1,
                                telephonyServicesCallForwardOnNoAnswerVer1,
                                telephonyServicesCallWaitingCancelVer1,
                                telephonyServicesUrgentGatewayVer1,
                                telephonyServicesIpAddressCallVer1
                             }
        ::= { telephonyServicesCompliances 1 }

    -- ************************************************************************
    --  MIB variable grouping
    -- ************************************************************************
    telephonyServicesGroups OBJECT IDENTIFIER ::= { telephonyServicesConformance 5 }

    telephonyServicesStatusVer1 OBJECT-GROUP
        OBJECTS {
                    telephonyServicesHoldStatus,
                    telephonyServicesCallWaitingStatus,
                    telephonyServicesSecondCallStatus,
                    telephonyServicesBlindTransferStatus,
                    telephonyServicesAttendedTransferStatus,
                    telephonyServicesConferenceStatus
                }
        STATUS current
        DESCRIPTION
            "A collection of objects that defines the characteristics of telephony services."
        ::= { telephonyServicesGroups 3 }

    telephonyServicesActivationVer1 OBJECT-GROUP
        OBJECTS {
                    telephonyServicesHoldEnable,
                    telephonyServicesCallWaitingEnable,
                    telephonyServicesSecondCallEnable,
                    telephonyServicesBlindTransferEnable,
                    telephonyServicesAttendedTransferEnable,
                    telephonyServicesConferenceEnable
                }
        STATUS current
        DESCRIPTION
            "A collection of objects that defines the characteristics of telephony services."
        ::= { telephonyServicesGroups 5 }


    telephonyServicesAutoSpeedDialVer1 OBJECT-GROUP
        OBJECTS {
                    telephonyServicesAutoSpeedDialEnable,
                    telephonyServicesAutoSpeedDialTargetAddress
                }
        STATUS current
        DESCRIPTION
            "A collection of objects that defines the characteristics of telephony services."
        ::= { telephonyServicesGroups 10 }


    telephonyServicesCallForwardUnconditionnalStatusVer1 OBJECT-GROUP
        OBJECTS {
                    telephonyServicesCallForwardUnconditionnalStatus
                }
        STATUS current
        DESCRIPTION
            "A collection of objects that defines the characteristics of telephony services."
        ::= { telephonyServicesGroups 12 }


    telephonyServicesCallForwardUnconditionnalVer1 OBJECT-GROUP
        OBJECTS {
                    telephonyServicesCallForwardUnconditionnalEnable,
                    telephonyServicesCallForwardUnconditionnalForwardingAddress,
                    telephonyServicesCallForwardUnconditionnalEnableDigitMap,
                    telephonyServicesCallForwardUnconditionnalDisableDigitMap
                }
        STATUS current
        DESCRIPTION
            "A collection of objects that defines the characteristics of telephony services."
        ::= { telephonyServicesGroups 15 }


    telephonyServicesCallForwardBusyStatusVer1 OBJECT-GROUP
        OBJECTS {
                    telephonyServicesCallForwardBusyStatus
                }
        STATUS current
        DESCRIPTION
            "A collection of objects that defines the characteristics of telephony services."
        ::= { telephonyServicesGroups 17 }


    telephonyServicesCallForwardBusyVer1 OBJECT-GROUP
        OBJECTS {
                    telephonyServicesCallForwardBusyEnable,
                    telephonyServicesCallForwardBusyForwardingAddress,
                    telephonyServicesCallForwardBusyEnableDigitMap,
                    telephonyServicesCallForwardBusyDisableDigitMap
                }
        STATUS current
        DESCRIPTION
            "A collection of objects that defines the characteristics of telephony services."
        ::= { telephonyServicesGroups 20 }


    telephonyServicesCallForwardOnNoAnswerStatusVer1 OBJECT-GROUP
        OBJECTS {
                    telephonyServicesCallForwardDontAnswerStatus
                }
        STATUS current
        DESCRIPTION
            "A collection of objects that defines the characteristics of telephony services."
        ::= { telephonyServicesGroups 22 }


    telephonyServicesCallForwardOnNoAnswerVer1 OBJECT-GROUP
        OBJECTS {
                    telephonyServicesCallForwardDontAnswerEnable,
                    telephonyServicesCallForwardDontAnswerForwardingAddress,
                    telephonyServicesCallForwardDontAnswerEnableDigitMap,
                    telephonyServicesCallForwardDontAnswerDisableDigitMap,
                    telephonyServicesCallForwardDontAnswerTimeout
                }
        STATUS current
        DESCRIPTION
            "A collection of objects that defines the characteristics of telephony services."
        ::= { telephonyServicesGroups 25 }


    telephonyServicesCallWaitingCancelVer1 OBJECT-GROUP
        OBJECTS {
                    telephonyServicesCallWaitingCancelEnable,
                    telephonyServicesCallWaitingCancelDigitMap
                }
        STATUS current
        DESCRIPTION
            "A collection of objects that defines the characteristics of telephony services."
        ::= { telephonyServicesGroups 30 }


    telephonyServicesUrgentGatewayVer1 OBJECT-GROUP
        OBJECTS {
                    telephonyServicesUrgentGatewayEnable,
                    telephonyServicesUrgentGatewayDigitMap,
                    telephonyServicesUrgentGatewayTargetAddress
                }
        STATUS current
        DESCRIPTION
            "A collection of objects that defines the characteristics of telephony services."
        ::= { telephonyServicesGroups 35 }

    telephonyServicesIpAddressCallVer1 OBJECT-GROUP
        OBJECTS {
                    telephonyServicesIpAddressCallEnable
                }
        STATUS current
        DESCRIPTION
            "A collection of objects that defines the characteristics of telephony services."
        ::= { telephonyServicesGroups 99 }
END
