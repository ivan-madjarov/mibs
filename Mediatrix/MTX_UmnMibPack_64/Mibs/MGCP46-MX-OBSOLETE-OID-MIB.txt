-- ****************************************************************************
-- ****************************************************************************
--
--             Copyright(c) 2003 Mediatrix Telecom, Inc.
--
--  NOTICE:
--   This document contains information that is confidential and proprietary
--   to Mediatrix Telecom, Inc.
--
--   Mediatrix Telecom, Inc. reserves all rights to this document as well as
--   to the Intellectual Property of the document and the technology and
--   know how that it includes and represents.
--
--   This publication cannot be reproduced, neither in whole nor in part in
--   any form whatsoever without written prior approval by
--   Mediatrix Telecom, Inc.
--
--   Mediatrix Telecom, Inc. reserves the right to revise this publication
--   and make changes at any time and without the obligation to notify any
--   person and/or entity of such revisions and/or changes.
--
-- ****************************************************************************
-- ****************************************************************************

MX-OBSOLETE-MIB
DEFINITIONS ::= BEGIN

IMPORTS
        MODULE-IDENTITY,
        OBJECT-TYPE,
        NOTIFICATION-TYPE,
        Unsigned32,
        Integer32
    FROM SNMPv2-SMI
        OBJECT-GROUP,
        NOTIFICATION-GROUP,
        MODULE-COMPLIANCE
    FROM SNMPv2-CONF
        MxIpHostName,
        MxIpConfigSource,
        MxIpPort,
        MxIpAddress,
        MxIpSelectConfigSource,
        MxIpDhcpSiteSpecificCode,
        MxActivationState,
        MxEnableState
    FROM MX-TC
        mediatrixExperimental
    FROM MX-SMI
        sipMIBObjects
    FROM MX-SIP-MIB
        subscriberServicesMIBObjects
    FROM MX-SUBSCRIBER-SERVICES-MIB
        h323RegistrationSingleRegistration,
        h323RegistrationMIBObjects
    FROM MX-H323-REGISTRATION-MIB
        ipAddressStatusH323,
        ipAddressConfigH323Static,
        ipAddressConfigH323Dhcp
    FROM MX-H323-MIB
        telephonyServicesMIBObjects,
        telephonyServicesIfStatusEntry,
        telephonyServicesIfActivationEntry
    FROM MX-TELEPHONY-SERVICES-MIB;

    -- ************************************************************************
    -- Obsoleted from MX-SIP-MIB
    -- ************************************************************************
    sipReplacesConfig OBJECT-TYPE
        SYNTAX      INTEGER {
                             doNotUseReplaces(0),
                             useReplacesWithRequire(1),
                             useReplacesNoRequire(2)
                            }
        MAX-ACCESS  read-write
        STATUS      obsolete
        DESCRIPTION "This object has been obsoleted and replaced by another object.
                     Please refer to the documentation shipped with your device for
                     more details."
        DEFVAL      { useReplacesWithRequire }
        ::= { sipMIBObjects  7 }

    -- ************************************************************************
    -- Obsoleted from MX-H323-TERMINAL-MIB
    -- ************************************************************************

        h323TermSingleRegAsGateway OBJECT-TYPE
            SYNTAX      INTEGER {
                                  disable(0),
                                  enable(1)
                                }
            MAX-ACCESS  read-write
            STATUS      current
            DESCRIPTION "This object has been obsoleted and replaced by another object.
                         Please refer to the documentation shipped with your device for
                         more details."
            DEFVAL { disable }
            ::=  {  h323RegistrationSingleRegistration 25 }

    h323TerminalAliasesIfTable OBJECT-TYPE
        SYNTAX      SEQUENCE OF H323TerminalAliasesIfEntry
        MAX-ACCESS  not-accessible
        STATUS      current
        DESCRIPTION "This object has been obsoleted and replaced by another object.
                     Please refer to the documentation shipped with your device for
                     more details."
        ::= { h323RegistrationMIBObjects 20 }

        h323TerminalAliasesIfEntry OBJECT-TYPE
            SYNTAX      H323TerminalAliasesIfEntry
            MAX-ACCESS  not-accessible
            STATUS      current
            DESCRIPTION "This object has been obsoleted and replaced by another object.
                         Please refer to the documentation shipped with your device for
                         more details."
            INDEX       { ifIndex }
            ::= { h323TerminalAliasesIfTable 1 }

            H323TerminalAliasesIfEntry ::= SEQUENCE
                {
                    h323TermAliasesConfigured OCTET STRING,
                    h323TermAliasesCurrent    OCTET STRING
                }

        h323TermAliasesConfigured OBJECT-TYPE
            SYNTAX      OCTET STRING (SIZE (0..63))
            MAX-ACCESS  read-write
            STATUS      current
            DESCRIPTION "This object has been obsoleted and replaced by another object.
                         Please refer to the documentation shipped with your device for
                         more details."
            DEFVAL { "" }
            ::=  {  h323TerminalAliasesIfEntry 5 }

        h323TermAliasesCurrent OBJECT-TYPE
            SYNTAX      OCTET STRING (SIZE (0..255))
            MAX-ACCESS  read-only
            STATUS      current
            DESCRIPTION "This object has been obsoleted and replaced by another object.
                         Please refer to the documentation shipped with your device for
                         more details."
            DEFVAL { "" }
            ::=  {  h323TerminalAliasesIfEntry 10 }


    h323TerminalProcedureIfTable OBJECT-TYPE
        SYNTAX      SEQUENCE OF H323TerminalProcedureIfEntry
        MAX-ACCESS  not-accessible
        STATUS      current
        DESCRIPTION "This object has been obsoleted and replaced by another object.
                     Please refer to the documentation shipped with your device for
                     more details."
        ::= { h323RegistrationMIBObjects 25 }

        h323TerminalProcedureIfEntry OBJECT-TYPE
            SYNTAX      H323TerminalProcedureIfEntry
            MAX-ACCESS  not-accessible
            STATUS      current
            DESCRIPTION "This object has been obsoleted and replaced by another object.
                         Please refer to the documentation shipped with your device for
                         more details."
            INDEX       { ifIndex }
            ::= { h323TerminalProcedureIfTable 1 }

            H323TerminalProcedureIfEntry ::= SEQUENCE
                {
                    h323TermProcedureEarlyH245Enable         INTEGER,
                    h323TermProcedureH245TunnelingEnable     INTEGER,
                    h323TermProcedureFastConnectEnable       INTEGER,
                    h323TermProcedureDirectGatewayCallEnable INTEGER
                }

        h323TermProcedureEarlyH245Enable OBJECT-TYPE
            SYNTAX      INTEGER {
                                  disable(0),
                                  enable(1)
                                }
            MAX-ACCESS  read-write
            STATUS      current
            DESCRIPTION "This object has been obsoleted and replaced by another object.
                         Please refer to the documentation shipped with your device for
                         more details."
            DEFVAL { enable }
            ::=  {  h323TerminalProcedureIfEntry 5 }

        h323TermProcedureH245TunnelingEnable OBJECT-TYPE
            SYNTAX      INTEGER {
                                  disable(0),
                                  enable(1)
                                }
            MAX-ACCESS  read-write
            STATUS      current
            DESCRIPTION "This object has been obsoleted and replaced by another object.
                         Please refer to the documentation shipped with your device for
                         more details."
            DEFVAL { disable }
            ::=  {  h323TerminalProcedureIfEntry 10 }

        h323TermProcedureFastConnectEnable OBJECT-TYPE
            SYNTAX      INTEGER {
                                  disable(0),
                                  enable(1)
                                }
            MAX-ACCESS  read-write
            STATUS      current
            DESCRIPTION "This object has been obsoleted and replaced by another object.
                         Please refer to the documentation shipped with your device for
                         more details."
            DEFVAL { enable }
            ::=  {  h323TerminalProcedureIfEntry 15 }

        h323TermProcedureDirectGatewayCallEnable OBJECT-TYPE
            SYNTAX      INTEGER {
                                  disable(0),
                                  enable(1)
                                }
            MAX-ACCESS  read-write
            STATUS      current
            DESCRIPTION "This object has been obsoleted and replaced by another object.
                         Please refer to the documentation shipped with your device for
                         more details."
            DEFVAL { disable }
            ::=  {  h323TerminalProcedureIfEntry 20 }

    -- *************************************************************************
    -- Obsoleted from MX-H323-ATTRIBUTES-MIB
    -- *************************************************************************

    h323DirectGatewayCallHost OBJECT-TYPE
        SYNTAX      MxIpAddress
        MAX-ACCESS  read-only
        STATUS      current
        DESCRIPTION "This object has been obsoleted and replaced by another object.
                     Please refer to the documentation shipped with your device for
                     more details."
        DEFVAL { "" }
        ::=  {  ipAddressStatusH323 10 }

    h323DirectGatewayCallPort OBJECT-TYPE
        SYNTAX      MxIpPort
        MAX-ACCESS  read-only
        STATUS      current
        DESCRIPTION "This object has been obsoleted and replaced by another object.
                     Please refer to the documentation shipped with your device for
                     more details."
        DEFVAL { 1720 }
        ::=  {  ipAddressStatusH323 15 }

    h323DirectGatewayCallStaticHost OBJECT-TYPE
        SYNTAX      MxIpAddress
        MAX-ACCESS  read-write
        STATUS      current
        DESCRIPTION "This object has been obsoleted and replaced by another object.
                     Please refer to the documentation shipped with your device for
                     more details."
        DEFVAL { "" }
        ::=  {  ipAddressConfigH323Static 5 }

    h323DirectGatewayCallStaticPort OBJECT-TYPE
        SYNTAX      MxIpPort
        MAX-ACCESS  read-only
        STATUS      current
        DESCRIPTION "This object has been obsoleted and replaced by another object.
                     Please refer to the documentation shipped with your device for
                     more details."
        DEFVAL { 1720 }
        ::=  {  ipAddressConfigH323Static 10 }

    h323DirectGatewayCallDhcpSiteSpecificCode OBJECT-TYPE
        SYNTAX      MxIpDhcpSiteSpecificCode
        MAX-ACCESS  read-write
        STATUS      current
        DESCRIPTION "This object has been obsoleted and replaced by another object.
                     Please refer to the documentation shipped with your device for
                     more details."
        DEFVAL { 0 }
        ::= { ipAddressConfigH323Dhcp 5 }

    -- *************************************************************************
    -- Moved within MX-SUBSCRIBER-SERVICES-MIB (Base OID changed from 60 to 62)
    -- telephonyServicesMIB is based at 60
    -- *************************************************************************

    subscriberServicesCallForwardUnconditionnalEnable OBJECT-TYPE
        SYNTAX  MxEnableState
        MAX-ACCESS  read-write
        STATUS      current
        DESCRIPTION "This object has been obsoleted and replaced by another object.
                     Please refer to the documentation shipped with your device for
                     more details."
        DEFVAL      { disable }
        ::= { telephonyServicesIfActivationEntry 35 }

    subscriberServicesCallForwardOnBusyEnable OBJECT-TYPE
        SYNTAX  MxEnableState
        MAX-ACCESS  read-write
        STATUS      current
        DESCRIPTION "This object has been obsoleted and replaced by another object.
                     Please refer to the documentation shipped with your device for
                     more details."
        DEFVAL      { disable }
        ::= { telephonyServicesIfActivationEntry 40 }

    subscriberServicesCallForwardOnNoAnswerEnable OBJECT-TYPE
        SYNTAX  MxEnableState
        MAX-ACCESS  read-write
        STATUS      current
        DESCRIPTION "This object has been obsoleted and replaced by another object.
                     Please refer to the documentation shipped with your device for
                     more details."
        DEFVAL      { disable }
        ::= { telephonyServicesIfActivationEntry 45 }

    subscriberServicesIfCallForwardActivationTable OBJECT-TYPE
        SYNTAX      SEQUENCE OF SubscriberServicesIfCallForwardActivationEntry
        MAX-ACCESS  not-accessible
        STATUS      current
        DESCRIPTION "This object has been obsoleted and replaced by another object.
                     Please refer to the documentation shipped with your device for
                     more details."
        ::= { telephonyServicesMIBObjects 21 }

        subscriberServicesIfCallForwardActivationEntry OBJECT-TYPE
            SYNTAX      SubscriberServicesIfCallForwardActivationEntry
            MAX-ACCESS  not-accessible
            STATUS      current
            DESCRIPTION "This object has been obsoleted and replaced by another object.
                         Please refer to the documentation shipped with your device for
                         more details."
            INDEX       {
                            ifIndex
                        }
            ::= { subscriberServicesIfCallForwardActivationTable 1 }

            SubscriberServicesIfCallForwardActivationEntry ::= SEQUENCE
                {
                    subscriberServicesCallForwardUnconditionnalActivation           MxActivationState,
                    subscriberServicesCallForwardUnconditionnalForwardingAddress    OCTET STRING,
                    subscriberServicesCallForwardOnBusyActivation                   MxActivationState,
                    subscriberServicesCallForwardOnBusyForwardingAddress            OCTET STRING,
                    subscriberServicesCallForwardOnNoAnswerActivation               MxActivationState,
                    subscriberServicesCallForwardOnNoAnswerForwardingAddress        OCTET STRING,
                    subscriberServicesCallForwardOnNoAnswerTimeout                  Unsigned32
                }

            subscriberServicesCallForwardUnconditionnalActivation OBJECT-TYPE
                SYNTAX  MxActivationState
                MAX-ACCESS  read-write
                STATUS      current
                DESCRIPTION "This object has been obsoleted and replaced by another object.
                             Please refer to the documentation shipped with your device for
                             more details."
                DEFVAL      { inactive }
                ::= { subscriberServicesIfCallForwardActivationEntry 5 }

            subscriberServicesCallForwardUnconditionnalForwardingAddress OBJECT-TYPE
                SYNTAX  OCTET STRING (SIZE(0..127))
                MAX-ACCESS  read-write
                STATUS      current
                DESCRIPTION "This object has been obsoleted and replaced by another object.
                             Please refer to the documentation shipped with your device for
                             more details."
                DEFVAL      { "" }
                ::= { subscriberServicesIfCallForwardActivationEntry 10 }

            subscriberServicesCallForwardOnBusyActivation OBJECT-TYPE
                SYNTAX  MxActivationState
                MAX-ACCESS  read-write
                STATUS      current
                DESCRIPTION "This object has been obsoleted and replaced by another object.
                             Please refer to the documentation shipped with your device for
                             more details."
                DEFVAL      { inactive }
                ::= { subscriberServicesIfCallForwardActivationEntry 15 }

            subscriberServicesCallForwardOnBusyForwardingAddress OBJECT-TYPE
                SYNTAX  OCTET STRING (SIZE(0..127))
                MAX-ACCESS  read-write
                STATUS      current
                DESCRIPTION "This object has been obsoleted and replaced by another object.
                             Please refer to the documentation shipped with your device for
                             more details."
                DEFVAL      { "" }
                ::= { subscriberServicesIfCallForwardActivationEntry 20 }

            subscriberServicesCallForwardOnNoAnswerActivation OBJECT-TYPE
                SYNTAX  MxActivationState
                MAX-ACCESS  read-write
                STATUS      current
                DESCRIPTION "This object has been obsoleted and replaced by another object.
                             Please refer to the documentation shipped with your device for
                             more details."
                DEFVAL      { inactive }
                ::= { subscriberServicesIfCallForwardActivationEntry 25 }

            subscriberServicesCallForwardOnNoAnswerForwardingAddress OBJECT-TYPE
                SYNTAX  OCTET STRING (SIZE(0..127))
                MAX-ACCESS  read-write
                STATUS      current
                DESCRIPTION "This object has been obsoleted and replaced by another object.
                             Please refer to the documentation shipped with your device for
                             more details."
                DEFVAL      { "" }
                ::= { subscriberServicesIfCallForwardActivationEntry 30 }

            subscriberServicesCallForwardOnNoAnswerTimeout OBJECT-TYPE
                SYNTAX  Unsigned32(200..120000)
                MAX-ACCESS  read-write
                STATUS      current
                DESCRIPTION "This object has been obsoleted and replaced by another object.
                             Please refer to the documentation shipped with your device for
                             more details."
                DEFVAL      { 5000 }
                ::= { subscriberServicesIfCallForwardActivationEntry 35 }

    subscriberServicesActivationDigitmaps OBJECT IDENTIFIER ::= { telephonyServicesMIBObjects 25 }

    subscriberServicesCallForwardUnconditionnalEnableDigitMap OBJECT-TYPE
        SYNTAX  OCTET STRING (SIZE(0..63))
        MAX-ACCESS  read-write
        STATUS      current
        DESCRIPTION "This object has been obsoleted and replaced by another object.
                     Please refer to the documentation shipped with your device for
                     more details."
        DEFVAL      { "" }
        ::= { subscriberServicesActivationDigitmaps 5 }

    subscriberServicesCallForwardUnconditionnalDisableDigitMap OBJECT-TYPE
        SYNTAX  OCTET STRING (SIZE(0..63))
        MAX-ACCESS  read-write
        STATUS      current
        DESCRIPTION "This object has been obsoleted and replaced by another object.
                     Please refer to the documentation shipped with your device for
                     more details."
        DEFVAL      { "" }
        ::= { subscriberServicesActivationDigitmaps 10 }

    subscriberServicesCallForwardOnBusyEnableDigitMap OBJECT-TYPE
        SYNTAX  OCTET STRING (SIZE(0..63))
        MAX-ACCESS  read-write
        STATUS      current
        DESCRIPTION "This object has been obsoleted and replaced by another object.
                     Please refer to the documentation shipped with your device for
                     more details."
        DEFVAL      { "" }
        ::= { subscriberServicesActivationDigitmaps 15 }

    subscriberServicesCallForwardOnBusyDisableDigitMap OBJECT-TYPE
        SYNTAX  OCTET STRING (SIZE(0..63))
        MAX-ACCESS  read-write
        STATUS      current
        DESCRIPTION "This object has been obsoleted and replaced by another object.
                     Please refer to the documentation shipped with your device for
                     more details."
        DEFVAL      { "" }
        ::= { subscriberServicesActivationDigitmaps 20 }

    subscriberServicesCallForwardOnNoAnswerEnableDigitMap OBJECT-TYPE
        SYNTAX  OCTET STRING (SIZE(0..63))
        MAX-ACCESS  read-write
        STATUS      current
        DESCRIPTION "This object has been obsoleted and replaced by another object.
                     Please refer to the documentation shipped with your device for
                     more details."
        DEFVAL      { "" }
        ::= { subscriberServicesActivationDigitmaps 25 }

    subscriberServicesCallForwardOnNoAnswerDisableDigitMap OBJECT-TYPE
        SYNTAX  OCTET STRING (SIZE(0..63))
        MAX-ACCESS  read-write
        STATUS      current
        DESCRIPTION "This object has been obsoleted and replaced by another object.
                     Please refer to the documentation shipped with your device for
                     more details."
        DEFVAL      { "" }
        ::= { subscriberServicesActivationDigitmaps 30 }

    subscriberServicesCallWaitingCancelDigitMap OBJECT-TYPE
        SYNTAX  OCTET STRING (SIZE(0..63))
        MAX-ACCESS  read-write
        STATUS      current
        DESCRIPTION "This object has been obsoleted and replaced by another object.
                     Please refer to the documentation shipped with your device for
                     more details."
        DEFVAL      { "" }
        ::= { subscriberServicesActivationDigitmaps 35 }

END
