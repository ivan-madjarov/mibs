-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


DGW11-MX-CONF-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

confMIB MODULE-IDENTITY
 LAST-UPDATED   "0510310000Z"
 ORGANIZATION " Mediatrix Telecom, Inc. "
 CONTACT-INFO " Mediatrix Telecom, Inc.
                4229, Garlock Street
                Sherbrooke (Quebec)
                Canada
                Phone: (819) 829-8749
                "
 DESCRIPTION  " Configuration Manager

                The Configuration Manager allows configuration scripts
                transfers and backup/restore of the unit's configuration.
                "
 -- ****************************************************************************
 
 -- Revision history
 -- ****************************************************************************
 REVISION       "0510310000Z"
 DESCRIPTION  " Initial Revision "
 REVISION       "0606060000Z"
 DESCRIPTION  " Updated ImagePrivacyAlgo and ImageSecretKey documentation "
 REVISION       "0607240000Z"
 DESCRIPTION  " Updated ScriptsSecretKey documentation "
 REVISION       "0803280000Z"
 DESCRIPTION  " Updated ScriptsSecretKey range and documentation "
 REVISION       "0804210000Z"
 DESCRIPTION  " Updated ScriptSpecificFileName description with %mac% "
 REVISION       "0809120000Z"
 DESCRIPTION  " New ImageBackupContent scalar "
 REVISION       "0809150000Z"
 DESCRIPTION  " Remove FILE protocol option for configuration script and update
                documentations "
 REVISION       "0809160000Z"
 DESCRIPTION  " Add new scalar ScriptsTransferRetriesNumber in
                AutomaticScriptsTransferGroup "
 REVISION       "0901070000Z"
 DESCRIPTION  " Add FILE protocol option for configuration script and update
                documentations "
 REVISION       "0902040000Z"
 DESCRIPTION  " Add information about using the %mac% macro in the
                ImageFileName variable. "
 REVISION       "0903130000Z"
 DESCRIPTION  " Add information about the ScriptsTransferRetriesNumber
                variable. "
 REVISION       "0904170000Z"
 DESCRIPTION  " Add some variables in a new group ScriptExportGroup. Add the
                RebootIfNeeded and ScriptExport command. Add some new stats in
                the group ScriptsStatsGroup. Improve some other descriptions. "
 REVISION       "0910080000Z"
 DESCRIPTION  " Add the variables ScriptsDhcpDownloadEnable. Add the variable
                ScriptsAllowRepeatedExecution Add the
                ScriptsTransferAndRun.AllowRepeatedExecution parameter. Add
                %version% macro information. "
 REVISION       "0910270000Z"
 DESCRIPTION  " Added ScriptsTransferCertificateValidation variable. Added
                ScriptsTransferAndRun.CertificateValidation parameter "
 REVISION       "0911170000Z"
 DESCRIPTION  " Updated RebootIfNeeded description. "
 ::= { mediatrixServices 800 }

confMIBObjects OBJECT IDENTIFIER ::= { confMIB 1 }

-- ****************************************************************************

-- Group:Configuration Scripts

-- ****************************************************************************

scriptsGroup OBJECT IDENTIFIER
 ::= { confMIBObjects 100 }
 -- Scalar:Generic Configuration Script Filename

 scriptGenericFileName OBJECT-TYPE
  SYNTAX        OCTET STRING ( SIZE(0..255) )
  MAX-ACCESS    read-write
  STATUS        current
  DESCRIPTION " Generic Configuration Script Filename

                Name of the generic configuration script to run. Using a
                generic configuration script but no specific configuration
                script or vice-versa is allowed. Using both generic and
                specific configuration scripts is also allowed.

                This field may contain some macros that are substituted by the
                actual value at the moment of fetching the configuration
                script.

                The supported macros are:

                  * %mac% - the MAC address of the unit.
                  * %version% - the MFP version of the unit.


                "
  DEFVAL        { "" }
  ::= { scriptsGroup 100 }

 -- Scalar:Specific Configuration Script Filename

 scriptSpecificFileName OBJECT-TYPE
  SYNTAX        OCTET STRING ( SIZE(0..255) )
  MAX-ACCESS    read-write
  STATUS        current
  DESCRIPTION " Specific Configuration Script Filename

                Name of the specific configuration script to run. Using a
                specific configuration script but no generic configuration
                script or vice-versa is allowed. Using both generic and
                specific configuration scripts is also allowed. When using a
                specific configuration script and a generic configuration
                script, commands from the specific configuration script
                override commands from the generic configuration script.

                This field may contain some macros that are substituted by the
                actual value at the moment of fetching the configuration
                script.

                The supported macros are:

                  * %mac% - the MAC address of the unit.
                  * %version% - the MFP version of the unit.


                "
  DEFVAL        { "" }
  ::= { scriptsGroup 200 }

 -- Scalar:Location (Path)

 scriptsLocation OBJECT-TYPE
  SYNTAX        OCTET STRING ( SIZE(0..255) )
  MAX-ACCESS    read-write
  STATUS        current
  DESCRIPTION " Location (Path)

                Path to the location of the configuration files. The path is
                relative to the root of the configuration scripts server
                referenced by the variable ScriptsTransfer/
                ScriptsTransferSrvHostname. Use '/' to separate
                subdirectories.
                "
  DEFVAL        { "" }
  ::= { scriptsGroup 300 }

 -- ***************************************************************************
 
 -- Group:Configuration Scripts Transfer

 -- ***************************************************************************
 
 scriptsTransferGroup OBJECT IDENTIFIER
  ::= { scriptsGroup 400 }
  -- Scalar:Transfer Protocol

  scriptsTransferProtocol OBJECT-TYPE
   SYNTAX        INTEGER { http(100) , https(200) , tftp(300) , ftp(400) , file
                 (500) }
   MAX-ACCESS    read-write
   STATUS        current
   DESCRIPTION " Transfer Protocol

                 Protocol used to transfer the configuration script files.

                   * HTTP: Hypertext Transfer Protocol.
                   * HTTPS: Hypertext Transfer Protocol over Transport Layer
                     Security.
                   * TFTP: Trivial File Transfer Protocol.
                   * FTP: File Transfer Protocol.
                   * File: Complete path to a configuration script in an
                     onboard storage.


                 "
   DEFVAL        { https }
   ::= { scriptsTransferGroup 100 }

  -- Scalar:User Name

  scriptsTransferUsername OBJECT-TYPE
   SYNTAX        OCTET STRING ( SIZE(0..63) )
   MAX-ACCESS    read-write
   STATUS        current
   DESCRIPTION " User Name

                 User name used to transfer the configuration script, if the
                 protocol selected by the variable ScriptsTransferProtocol
                 requires it.
                 "
   DEFVAL        { "" }
   ::= { scriptsTransferGroup 200 }

  -- Scalar:Password

  scriptsTransferPassword OBJECT-TYPE
   SYNTAX        OCTET STRING ( SIZE(0..63) )
   MAX-ACCESS    read-write
   STATUS        current
   DESCRIPTION " Password

                 Password used to transfer the configuration script, if the
                 protocol selected by the variable ScriptsTransferProtocol
                 requires it.
                 "
   DEFVAL        { "" }
   ::= { scriptsTransferGroup 300 }

  -- Scalar:Server Hostname and port

  scriptsTransferSrvHostname OBJECT-TYPE
   SYNTAX        MxIpHostNamePort
   MAX-ACCESS    read-write
   STATUS        current
   DESCRIPTION " Server Hostname and port

                 Configuration scripts server hostname and port. Use the
                 special port value zero to indicate the protocol default.
                 "
   DEFVAL        { "0.0.0.0:0" }
   ::= { scriptsTransferGroup 400 }

  -- Scalar:Level of security for HTTPS certificate validation.

  scriptsTransferCertificateValidation OBJECT-TYPE
   SYNTAX        INTEGER { noValidation(100) , hostName(200) }
   MAX-ACCESS    read-write
   STATUS        current
   DESCRIPTION " Level of security for HTTPS certificate validation.

                 When downloading a script from an HTTPS server, this variable
                 defines the level of security to use when validating the
                 server's certificate.

                   * NoValidation: Allow a connection to the server without
                     validating its certificate. The only condition is to
                     receive a certificate from the server. This option
                     provides partial security and should be selected with
                     care.
                   * HostName: Allow a connection to the server by validating
                     its certificate is trusted and valid. The validations
                     performed on the certificate include the expiration date
                     and that the Subject Alternate Name (SAN) or Common Name
                     (CN) matches the FQDN or IP address of the server.


                 "
   DEFVAL        { hostName }
   ::= { scriptsTransferGroup 500 }

 -- End of group:Configuration Scripts Transfer

 -- ***************************************************************************
 
 -- Group:Automatic Transfer

 -- ***************************************************************************
 
 automaticScriptsTransferGroup OBJECT IDENTIFIER
  ::= { scriptsGroup 500 }
  -- Scalar:Transfer On Restart

  scriptsTransferOnRestartEnable OBJECT-TYPE
   SYNTAX        MxEnableState
   MAX-ACCESS    read-write
   STATUS        current
   DESCRIPTION " Transfer On Restart

                 Enables the automatic configuration scripts transfer upon
                 restart.

                   * Enable: Configuration scripts are automatically
                     transferred upon restart.
                   * Disable: Configuration scripts are not automatically
                     transferred upon restart.


                 "
   DEFVAL        { disable }
   ::= { automaticScriptsTransferGroup 100 }

  -- Scalar:Scripts Transfer Number of Retries

  scriptsTransferRetriesNumber OBJECT-TYPE
   SYNTAX        Integer32 ( -1..100 )
   MAX-ACCESS    read-write
   STATUS        current
   DESCRIPTION " Scripts Transfer Number of Retries

                 Maximum attempts to retry a scripts transfer until its success
                 when it fails upon an automatic transfer on restart or
                 automatic periodic transfer. The retries are only attempted if
                 the server is unreachable. Unreachable port or file not found
                 errors don't trigger the retry mechanism. The time interval
                 between retries is 30 seconds.

                   * -1 means a retry to infinity.
                   * 0 means no retry.


                 "
   DEFVAL        { -1 }
   ::= { automaticScriptsTransferGroup 150 }

  -- Scalar:Periodic Transfer

  scriptsTransferPeriodicEnable OBJECT-TYPE
   SYNTAX        MxEnableState
   MAX-ACCESS    read-write
   STATUS        current
   DESCRIPTION " Periodic Transfer

                 Enables the automatic periodic configuration scripts transfer.
                 This requires that the device time is correctly set, which can
                 be done with the HOC service.

                   * Enable: Configuration scripts are automatically
                     transferred periodically.
                   * Disable: Configuration scripts transfer is not periodic.


                 "
   DEFVAL        { disable }
   ::= { automaticScriptsTransferGroup 200 }

  -- Scalar:Time Unit

  scriptsTransferPeriodicTimeUnit OBJECT-TYPE
   SYNTAX        INTEGER { minutes(100) , hours(200) , days(300) }
   MAX-ACCESS    read-write
   STATUS        current
   DESCRIPTION " Time Unit

                 Time unit for the variable ScriptsTransferPeriod.

                   * Minutes: Automatic configuration scripts transfer is
                     performed every x minutes.
                   * Hours: Automatic configuration scripts transfer is
                     performed every x hours.
                   * Days: Automatic configuration scripts transfer is
                     performed every x days at the time specified by the
                     ScriptsTransferTimeOfDay variable.


                 "
   DEFVAL        { hours }
   ::= { automaticScriptsTransferGroup 300 }

  -- Scalar:Time Interval

  scriptsTransferInterval OBJECT-TYPE
   SYNTAX        Unsigned32 ( 1..60 )
   MAX-ACCESS    read-write
   STATUS        current
   DESCRIPTION " Time Interval

                 Time interval between automatic configuration scripts
                 transfer. The time unit is selected by the
                 ScriptsTransferPeriodicTimeUnit variable.
                 "
   DEFVAL        { 1 }
   ::= { automaticScriptsTransferGroup 400 }

  -- Scalar:Daily Transfer Time

  scriptsTransferTimeOfDay OBJECT-TYPE
   SYNTAX        Integer32 ( -1..23 )
   MAX-ACCESS    read-write
   STATUS        current
   DESCRIPTION " Daily Transfer Time

                 Time when the automatic configuration scripts transfer occurs.
                 The time unit selected by the ScriptsTransferPeriodicTimeUnit
                 variable must be Days. -1 means random.
                 "
   DEFVAL        { -1 }
   ::= { automaticScriptsTransferGroup 500 }

  -- Scalar:DHCP Triggered Script Support.

  scriptsDhcpDownloadEnable OBJECT-TYPE
   SYNTAX        MxEnableState
   MAX-ACCESS    read-write
   STATUS        current
   DESCRIPTION " DHCP Triggered Script Support.

                 When enabled, DHCP options tftp-server (option 66) and
                 bootfile (option 67) are used to download a configuration
                 script. If this configuration script is identical to the last
                 executed script, it will not be run twice. The script retry
                 mechanism is not enabled for the DHCP triggered scripts.

                 If the two options are received, both scripts are executed
                 independently. The script defined by the tftp-server (option
                 66) option is executed first.


                 "
   DEFVAL        { enable }
   ::= { automaticScriptsTransferGroup 600 }

 -- End of group:Automatic Transfer

 -- Scalar:Decryption Key

 scriptsSecretKey OBJECT-TYPE
  SYNTAX        OCTET STRING ( SIZE(0..112) )
  MAX-ACCESS    read-write
  STATUS        current
  DESCRIPTION " Decryption Key

                Key used to decrypt configuration scripts when they are
                encrypted (auto-detected). The key is encoded in hexadecimal
                notation, meaning only characters in the range 0-9, A-F, and
                a-f can be used. Each character encodes 4 bits and the maximum
                key length is 112 characters, which gives a binary key of 56
                bytes. It is the maximum accepted by BlowFish.

                For example, a 32 bits key could look like: A36CB299.


                "
  DEFVAL        { "" }
  ::= { scriptsGroup 600 }

 -- Scalar:Allow Repeated Execution

 scriptsAllowRepeatedExecution OBJECT-TYPE
  SYNTAX        MxEnableState
  MAX-ACCESS    read-write
  STATUS        current
  DESCRIPTION " Allow Repeated Execution

                Allows the execution of a script even if it is identical to
                the last executed script.
                "
  DEFVAL        { enable }
  ::= { scriptsGroup 650 }

 -- ***************************************************************************
 
 -- Group:Configuration Script Exportation

 -- ***************************************************************************
 
 scriptExportGroup OBJECT IDENTIFIER
  ::= { scriptsGroup 1000 }
  -- Scalar:Export Content

  scriptExportContent OBJECT-TYPE
   SYNTAX        INTEGER { allConfig(100) , modifiedConfig(200) }
   MAX-ACCESS    read-write
   STATUS        current
   DESCRIPTION " Export Content

                 Content to export in generated configuration script.

                   * AllConfig: Export everything.
                   * ModifiedConfig: Export only the configuration that has
                     been modified (differs from the default values).


                 "
   DEFVAL        { modifiedConfig }
   ::= { scriptExportGroup 100 }

  -- Scalar:Export Script Destination URL

  scriptExportUrl OBJECT-TYPE
   SYNTAX        OCTET STRING ( SIZE(0..512) )
   MAX-ACCESS    read-write
   STATUS        current
   DESCRIPTION " Export Script Destination URL

                 URL where to send the exported configuration script. The URL
                 should follow this format:

                 protocol://[user[:password]@]hostname[:port]/[path/]filename

                 The brackets [] denote an optional parameter.

                 The filename may contain macros that are substituted at the
                 moment of sending the configuration script.

                 The supported macros are:

                   * %mac% - the MAC address of the unit.
                   * %version% - the MFP version of the unit.

                 The transfer protocols supported are:

                   * TFTP
                   * FTP
                   * FILE

                 Examples of valid URLs:

                   * tftp://tftpserver.com:69/folder/script.cfg
                   * ftp://guest@ftpserver.com/script.cfg
                   * ftp://username:password@ftpserver.com/script.cfg
                   * file://script.cfg

                 The protocol default port is used if none is specified.


                 "
   DEFVAL        { "" }
   ::= { scriptExportGroup 200 }

  -- Scalar:Encryption Key

  scriptExportSecretKey OBJECT-TYPE
   SYNTAX        OCTET STRING ( SIZE(0..64) )
   MAX-ACCESS    read-write
   STATUS        current
   DESCRIPTION " Encryption Key

                 Key used to encrypt the exported configuration script.

                 The key is encoded in hexadecimal notation, meaning only
                 characters in the range 0-9 and A-F can be used. The maximum
                 key length is 64 characters, which gives a binary key of 32
                 bytes (256 bits). It is the maximum key size accepted by the
                 MxCryptFile external tool.

                 For example, a 32 bits key could look like: A36CB299.


                 "
   DEFVAL        { "" }
   ::= { scriptExportGroup 300 }

 -- End of group:Configuration Script Exportation

 -- ***************************************************************************
 
 -- Group:Configuration Script Statistics

 -- ***************************************************************************
 
 scriptsStatsGroup OBJECT IDENTIFIER
  ::= { scriptsGroup 10000 }
  -- Scalar:Current Script Transfer State

  scriptsStatsCurrentTransferState OBJECT-TYPE
   SYNTAX        INTEGER { idle(100) , transfering(200) , running(300) }
   MAX-ACCESS    read-only
   STATUS        current
   DESCRIPTION " Current Script Transfer State

                 The current state of the configuration script transfer and
                 execution.

                   * Idle: No configuration script is currently running.
                   * Transfering: A configuration script is currently being
                     transferred.
                   * Running: The transferred configuration script is currently
                     running.


                 "
   DEFVAL        { idle }
   ::= { scriptsStatsGroup 700 }

  -- Scalar:Last Transfer Result

  scriptsStatsLastTransferResult OBJECT-TYPE
   SYNTAX        INTEGER { none(100) , success(200) , executionFailed(300) ,
                 transferFailed(400) }
   MAX-ACCESS    read-only
   STATUS        current
   DESCRIPTION " Last Transfer Result

                 Result of the last configuration scripts transfer and run
                 command.

                   * None: No configuration scripts transfer performed since
                     the last reset to default settings.
                   * Success: The last configuration scripts transfer succeeded
                     and the transferred scripts were ran successfully.
                   * ExecutionFailed: The last configuration scripts transfer
                     succeeded but at least one of the transferred scripts
                     failed to run.
                   * TransferFailed: At least one of the last configuration
                     scripts transfer failed.


                 "
   ::= { scriptsStatsGroup 800 }

  -- Scalar:Last Successful Transfer Date and Time

  scriptsStatsLastTransferDateTime OBJECT-TYPE
   SYNTAX        OCTET STRING ( SIZE(0..255) )
   MAX-ACCESS    read-only
   STATUS        current
   DESCRIPTION " Last Successful Transfer Date and Time

                 Date and time of the last successful configuration script
                 transfer and execution command since the last reset to default
                 settings.
                 "
   ::= { scriptsStatsGroup 900 }

  -- Scalar:Current Script Export State

  scriptsStatsCurrentExportState OBJECT-TYPE
   SYNTAX        INTEGER { idle(100) , transfering(200) , exporting(300) }
   MAX-ACCESS    read-only
   STATUS        current
   DESCRIPTION " Current Script Export State

                 The current state of the configuration script exportation.

                   * Idle: No configuration script is currently exporting.
                   * Exporting: A configuration script exportation is currently
                     in progress.
                   * Transfering: The exported configuration script is
                     currently being transferred.


                 "
   DEFVAL        { idle }
   ::= { scriptsStatsGroup 1000 }

  -- Scalar:Last Export Result

  scriptsStatsLastExportResult OBJECT-TYPE
   SYNTAX        INTEGER { none(100) , success(200) , exportationFailed(300) ,
                 transferFailed(400) }
   MAX-ACCESS    read-only
   STATUS        current
   DESCRIPTION " Last Export Result

                 Result of the last configuration script exportation command.

                   * None: No configuration script exportation performed since
                     the last reset to default settings.
                   * Success: The last configuration script exportation
                     succeeded and has been transferred successfully.
                   * ExportationFailed: The last configuration script
                     exportation failed.
                   * TransferFailed: The last configuration script exportation
                     succeeded but the script failed to transfer.


                 "
   ::= { scriptsStatsGroup 1100 }

  -- Scalar:Last Successful Export Date and Time

  scriptsStatsLastExportDateTime OBJECT-TYPE
   SYNTAX        OCTET STRING ( SIZE(0..255) )
   MAX-ACCESS    read-only
   STATUS        current
   DESCRIPTION " Last Successful Export Date and Time

                 Date and time of the last successful configuration script
                 exportation and transfer command since the last reset to
                 default settings.
                 "
   ::= { scriptsStatsGroup 1200 }

 -- End of group:Configuration Script Statistics

-- End of group:Configuration Scripts

-- ****************************************************************************

-- Group:Configuration Backup File

-- ****************************************************************************

imageGroup OBJECT IDENTIFIER
 ::= { confMIBObjects 200 }
 -- Scalar:File Name

 imageFileName OBJECT-TYPE
  SYNTAX        OCTET STRING ( SIZE(0..255) )
  MAX-ACCESS    read-write
  STATUS        current
  DESCRIPTION " File Name

                Name of the file used to backup (save) and restore (load) the
                unit's configuration. The macros used in this field are
                replaced by the unit's MAC address or MFP version right before
                backing up or restoring the unit's configuration.

                The supported macros are:

                  * %mac% - the MAC address of the unit.
                  * %version% - the MFP version of the unit.


                "
  DEFVAL        { "" }
  ::= { imageGroup 100 }

 -- Scalar:File Location (Path)

 imageLocation OBJECT-TYPE
  SYNTAX        OCTET STRING ( SIZE(0..255) )
  MAX-ACCESS    read-write
  STATUS        current
  DESCRIPTION " File Location (Path)

                Path to the location of the configuration image file. The path
                is relative to the root of the transfer server. Use '/' to
                separate subdirectories. When the Transfer Protocol is 'File',
                this may be prefixed by one of the following to indicate
                storage media:

                  * 'Persistent:' for onboard persistent storage - this is the
                    default.
                  * 'Volatile:' for onboard non-persistent storage.


                "
  DEFVAL        { "" }
  ::= { imageGroup 200 }

 -- Scalar:Backup Content

 imageBackupContent OBJECT-TYPE
  SYNTAX        INTEGER { config(100) , configAndCertificates(200) }
  MAX-ACCESS    read-write
  STATUS        current
  DESCRIPTION " Backup Content

                Defines what to include in the backup.

                  * Config: Only the unit's configuration is included in the
                    backup image.
                  * ConfigAndCertificates: The unit's configuration and
                    certificates are included in the backup image. It is
                    strongly recommended to activate encryption (see
                    ImagePrivacyAlgo and ImageSecretKey) when including
                    certificates in the backup image because host certificates
                    include the private key.


                "
  DEFVAL        { configAndCertificates }
  ::= { imageGroup 250 }

 -- ***************************************************************************
 
 -- Group:Configuration Image Transfer

 -- ***************************************************************************
 
 imageTransferGroup OBJECT IDENTIFIER
  ::= { imageGroup 300 }
  -- Scalar:Image Transfer Protocol

  imageTransferProtocol OBJECT-TYPE
   SYNTAX        INTEGER { http(100) , https(200) , tftp(300) , ftp(400) , file
                 (500) }
   MAX-ACCESS    read-write
   STATUS        current
   DESCRIPTION " Image Transfer Protocol

                 Protocol used to upload a configuration image during backup
                 and transfer during restore.

                   * HTTP: Hypertext Transfer Protocol.
                   * HTTPS: Hypertext Transfer Protocol over Transport Layer
                     Security.
                   * TFTP: Trivial File Transfer Protocol.
                   * FTP: File Transfer Protocol.
                   * File: Complete path to a configuration image in an onboard
                     storage.


                 "
   DEFVAL        { https }
   ::= { imageTransferGroup 100 }

  -- Scalar:User Name

  imageTransferUsername OBJECT-TYPE
   SYNTAX        OCTET STRING ( SIZE(0..63) )
   MAX-ACCESS    read-write
   STATUS        current
   DESCRIPTION " User Name

                 User name used to transfer the configuration image, if the
                 protocol selected by the variable ImageTransferProtocol
                 requires it.
                 "
   DEFVAL        { "" }
   ::= { imageTransferGroup 200 }

  -- Scalar:Password

  imageTransferPassword OBJECT-TYPE
   SYNTAX        OCTET STRING ( SIZE(0..63) )
   MAX-ACCESS    read-write
   STATUS        current
   DESCRIPTION " Password

                 Password used to transfer the configuration image, if the
                 protocol selected by the variable ImageTransferProtocol
                 requires it.
                 "
   DEFVAL        { "" }
   ::= { imageTransferGroup 300 }

  -- Scalar:Server Hostname and port

  imageTransferSrvHostname OBJECT-TYPE
   SYNTAX        MxIpHostNamePort
   MAX-ACCESS    read-write
   STATUS        current
   DESCRIPTION " Server Hostname and port

                 Configuration backup/restore server hostname and port. Use the
                 special value zero to indicate the protocol default.
                 "
   DEFVAL        { "0.0.0.0:0" }
   ::= { imageTransferGroup 400 }

 -- End of group:Configuration Image Transfer

 -- ***************************************************************************
 
 -- Group:Privacy

 -- ***************************************************************************
 
 imagePrivacyGroup OBJECT IDENTIFIER
  ::= { imageGroup 400 }
  -- Scalar:Privacy Enable

  imagePrivacyAlgo OBJECT-TYPE
   SYNTAX        INTEGER { none(100) , defaultAlgo(200) }
   MAX-ACCESS    read-write
   STATUS        current
   DESCRIPTION " Privacy Enable

                 Defines the encryption method to use for backup operations.
                 This variable is not used for restore operations.

                   * None: Backup images are not encrypted.
                   * DefaultAlgo: Backup images are encrypted with the default
                     algorithm.


                 "
   DEFVAL        { none }
   ::= { imagePrivacyGroup 100 }

  -- Scalar:Decryption Key

  imageSecretKey OBJECT-TYPE
   SYNTAX        OCTET STRING ( SIZE(0..255) )
   MAX-ACCESS    read-write
   STATUS        current
   DESCRIPTION " Decryption Key

                 Key used for backup operations to encrypt backup images when
                 the variable ImagePrivacyAlgo is not set to 'None'.

                 The key is also used when performing an image restore. In that
                 case, the encryption algorithm is auto-detected therefore
                 ImagePrivacyAlgo is ignored.


                 "
   DEFVAL        { "" }
   ::= { imagePrivacyGroup 200 }

 -- End of group:Privacy

 -- Scalar:Last Backup Result

 imageBackupStatus OBJECT-TYPE
  SYNTAX        INTEGER { none(100) , success(200) , failed(300) }
  MAX-ACCESS    read-only
  STATUS        current
  DESCRIPTION " Last Backup Result

                Result of the last configuration backup command.

                  * None: No configuration backup operation has been performed
                    since the last reset to default settings.
                  * Success: Last configuration backup operation succeeded.
                  * Failed: Last configuration backup operation failed.


                "
  ::= { imageGroup 600 }

 -- Scalar:Last Restore Result

 imageRestoreStatus OBJECT-TYPE
  SYNTAX        INTEGER { none(100) , success(200) , applyFailed(300) ,
                loadFailed(400) }
  MAX-ACCESS    read-only
  STATUS        current
  DESCRIPTION " Last Restore Result

                Result of the last configuration restore command.

                  * None: No configuration restore has been performed since
                    the last reset to default settings.
                  * Success: The last configuration restore succeeded.
                  * ApplyFailed: The configuration load succeeded but
                    restoring failed during the last configuration restore
                    command execution.
                  * LoadFailed: The configuration load failed during the last
                    configuration restore command.


                "
  ::= { imageGroup 800 }

-- End of group:Configuration Backup File

-- ***************************************************************************

-- Group:Configuration Alias

-- ***************************************************************************

aliasGroup OBJECT IDENTIFIER
         ::= { confMIBObjects 300 }
         -- ******************************************************************
         
         -- Table:Macro

         -- ******************************************************************
         
         macrosTable OBJECT-TYPE
          SYNTAX        SEQUENCE OF MacrosEntry
          MAX-ACCESS    not-accessible
          STATUS        current
          DESCRIPTION " Macro

                        This table contains information about macro
                        functions.
                        "
          ::= { aliasGroup 100 }
          macrosEntry OBJECT-TYPE
           SYNTAX        MacrosEntry
           MAX-ACCESS    not-accessible
           STATUS        current
           DESCRIPTION " A row in table Macro. "
           INDEX         {
                           macrosName
                         }

           ::= { macrosTable 1 }

          MacrosEntry ::= SEQUENCE
          {
            macrosName        OCTET STRING,
            macrosDescription OCTET STRING
          }

          -- Index:Macro Name

          macrosName OBJECT-TYPE
           SYNTAX        OCTET STRING
           MAX-ACCESS    read-only
           STATUS        current
           DESCRIPTION " Macro Name

                         Displays the macro name.
                         "
           DEFVAL        { "" }
           ::= { macrosEntry 100 }

          -- Columnar:Macro Desciption

          macrosDescription OBJECT-TYPE
           SYNTAX        OCTET STRING
           MAX-ACCESS    read-only
           STATUS        current
           DESCRIPTION " Macro Desciption

                         Shows the macro description.
                         "
           DEFVAL        { "" }
           ::= { macrosEntry 200 }


         -- End of table:Macro

         -- ******************************************************************
         
         -- Table:Alias

         -- ******************************************************************
         
         aliasTable OBJECT-TYPE
          SYNTAX          SEQUENCE OF AliasEntry
          MAX-ACCESS      not-accessible
          STATUS          current
          DESCRIPTION  "  Alias

                          This table contains information about alias.
                          "
          ::= { aliasGroup 200 }
          aliasEntry OBJECT-TYPE
           SYNTAX        AliasEntry
           MAX-ACCESS    not-accessible
           STATUS        current
           DESCRIPTION " A row in table Alias. "
           INDEX         {
                           aliasName
                         }

           ::= { aliasTable 1 }

          AliasEntry ::= SEQUENCE
          {
            aliasName    OCTET STRING,
            aliasEntity  OCTET STRING,
            aliasType    INTEGER,
            aliasContext OCTET STRING
          }

          -- Index:Alias Name

          aliasName OBJECT-TYPE
           SYNTAX        OCTET STRING
           MAX-ACCESS    read-only
           STATUS        current
           DESCRIPTION " Alias Name

                         Displays the alias name.
                         "
           DEFVAL        { "" }
           ::= { aliasEntry 100 }

          -- Columnar:Alias Value

          aliasEntity OBJECT-TYPE
           SYNTAX        OCTET STRING
           MAX-ACCESS    read-only
           STATUS        current
           DESCRIPTION " Alias Value

                         Shows the alias value.
                         "
           ::= { aliasEntry 200 }

          -- Columnar:Alias Type

          aliasType OBJECT-TYPE
           SYNTAX        INTEGER { module(100) , object(200) , columnar(300)
                         }
           MAX-ACCESS    read-only
           STATUS        current
           DESCRIPTION " Alias Type

                         Shows the alias type.
                         "
           DEFVAL        { module }
           ::= { aliasEntry 300 }

          -- Columnar:Alias Context

          aliasContext OBJECT-TYPE
           SYNTAX        OCTET STRING
           MAX-ACCESS    read-only
           STATUS        current
           DESCRIPTION " Alias Context

                         Shows the alias context.
                         "
           ::= { aliasEntry 400 }


         -- End of table:Alias

-- End of group:Configuration Alias

-- ****************************************************************************

-- Group:Notification Messages Configuration

-- ****************************************************************************

notificationsGroup OBJECT IDENTIFIER
 ::= { confMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { confMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
