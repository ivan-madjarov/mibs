-- ****************************************************************************
-- ****************************************************************************
--
--             Copyright(c) 2001-2002 Mediatrix Telecom, Inc.
--
--  NOTICE:
--   This document contains information that is confidential and proprietary
--   to Mediatrix Telecom, Inc.
--
--   Mediatrix Telecom, Inc. reserves all rights to this document as well as
--   to the Intellectual Property of the document and the technology and
--   know how that it includes and represents.
--
--   This publication cannot be reproduced, neither in whole nor in part in
--   any form whatsoever without written prior approval by
--   Mediatrix Telecom, Inc.
--
--   Mediatrix Telecom, Inc. reserves the right to revise this publication
--   and make changes at any time and without the obligation to notify any
--   person and/or entity of such revisions and/or changes.
--
-- ****************************************************************************
-- ****************************************************************************

MGCP42-MX-NAT-SIP-MIB
DEFINITIONS ::= BEGIN

IMPORTS
        MODULE-IDENTITY,
        OBJECT-IDENTITY,
        OBJECT-TYPE,
        Unsigned32
    FROM SNMPv2-SMI
        OBJECT-GROUP,
        MODULE-COMPLIANCE
    FROM SNMPv2-CONF
        MxIpHostName
    FROM MX-TC
        mediatrixExperimental
    FROM MX-SMI;

natSipMIB MODULE-IDENTITY
    LAST-UPDATED "0207050000Z"
    ORGANIZATION "Mediatrix Telecom, Inc."
    CONTACT-INFO "Mediatrix Telecom, Inc.
                  4229, Garlock Street
                  Sherbrooke (Quebec)
                  Canada
                  Phone: (819) 829-8749
                  "
    DESCRIPTION "This MIB contains SIP NAT traversal configuration objects."

    -- ************************************************************************
    -- Revision history
    -- ************************************************************************
    REVISION    "0207050000Z"
    DESCRIPTION "July 05, 2002
                    Renamed natSipMidcom            to natSipNortelPing
                            natSipMidcomTimeout     to natSipNortelPingTimeout
                            natSipMidcomGroupVer1   to natSipNortelPingGroupVer1
                    Edited different comments.
                 February 13, 2002
                 Creation"
    ::= { mediatrixExperimental 10 }

natSipMIBObjects  OBJECT IDENTIFIER ::= { natSipMIB 1 }
natSipConformance OBJECT IDENTIFIER ::= { natSipMIB 2 }

-- ************************************************************************
-- Custom solution Group
-- ************************************************************************
natSipCustom OBJECT IDENTIFIER ::= { natSipMIBObjects 5 }

    natSipCustomEnable OBJECT-TYPE
        SYNTAX      INTEGER {
                            disable(0),
                            enable(1)
                           }
        MAX-ACCESS  read-write
        STATUS      current
        DESCRIPTION "Enable/disable the NAT traversal scheme."
        DEFVAL { disable }
        ::=  { natSipCustom 5 }

    natSipCustomPublicAddress OBJECT-TYPE
        SYNTAX      MxIpHostName
        MAX-ACCESS  read-write
        STATUS      current
        DESCRIPTION "The public IP address used as Contact address by outgoing
                     SIP packets crossing a NAT system."
        DEFVAL      { "0.0.0.0" }
        ::=  { natSipCustom 10 }


-- ************************************************************************
-- NortelPing Group
-- ************************************************************************
natSipNortelPing OBJECT IDENTIFIER ::= { natSipMIBObjects 10 }

    natSipNortelPingTimeout OBJECT-TYPE
        SYNTAX      Unsigned32 (0..600)
        MAX-ACCESS  read-write
        STATUS      current
        DESCRIPTION "PING request refresh timeout in seconds. Feature used
                     under licence from Nortel Networks Inc."
        DEFVAL { 0 }
        ::=  { natSipNortelPing 1 }


    -- ************************************************************************
    -- Conformance information
    -- ************************************************************************
    natSipCompliances OBJECT IDENTIFIER ::= { natSipConformance 1 }

    natSipBasicComplVer1 MODULE-COMPLIANCE
        STATUS      current
        DESCRIPTION "Minimal definitions for the SIP NAT group"
        MODULE -- This Module
            MANDATORY-GROUPS {
                                natSipCustomGroupVer1,
                                natSipNortelPingGroupVer1
                             }
        ::= { natSipCompliances 1 }

    -- ************************************************************************
    -- MIB variable grouping
    -- ************************************************************************
    natSipGroups OBJECT IDENTIFIER ::= { natSipConformance 2 }

    natSipCustomGroupVer1 OBJECT-GROUP
        OBJECTS {
                    natSipCustomPublicAddress,
                    natSipCustomEnable
                }
        STATUS      current
        DESCRIPTION "This group holds the objects that define the
                     Custom NAT traversal group."
        ::= { natSipGroups 5 }

    natSipNortelPingGroupVer1 OBJECT-GROUP
        OBJECTS {
                    natSipNortelPingTimeout
                }
        STATUS      current
        DESCRIPTION "This group holds the objects related to the NAT traversal
                     scheme defined in draft-sen-midcom-fw-nat-00.txt. Feature
                     used under licence from Nortel Networks Inc."
        ::= { natSipGroups 10 }

END
