-- ****************************************************************************
-- ****************************************************************************
--
--             Copyright(c) 2001 Mediatrix Telecom, Inc. 
--
--  NOTICE:
--   This document contains information that is confidential and proprietary
--   to Mediatrix Telecom, Inc. 
--
--   Mediatrix Telecom, Inc. reserves all rights to this document as well as
--   to the Intellectual Property of the document and the technology and
--   know how that it includes and represents. 
--
--   This publication cannot be reproduced, neither in whole nor in part in
--   any form whatsoever without written prior approval by
--   Mediatrix Telecom, Inc. 
--
--   Mediatrix Telecom, Inc. reserves the right to revise this publication
--   and make changes at any time and without the obligation to notify any
--   person and/or entity of such revisions and/or changes. 
--
-- ****************************************************************************
-- ****************************************************************************

MGCP42-MX-DATAIF-MIB
DEFINITIONS ::= BEGIN

IMPORTS
        MODULE-IDENTITY,
        OBJECT-TYPE,
        Unsigned32
    FROM SNMPv2-SMI
        ifIndex
    FROM RFC1213-MIB
        OBJECT-GROUP,
        MODULE-COMPLIANCE
    FROM SNMPv2-CONF
        mediatrixConfig 
    FROM MX-SMI;

dataIfMIB MODULE-IDENTITY
    LAST-UPDATED "0207240000Z"
    ORGANIZATION "Mediatrix Telecom, Inc."
    CONTACT-INFO "Mediatrix Telecom, Inc.
                  4229, Garlock Street
                  Sherbrooke (Quebec)
                  Canada
                  Phone: (819) 829-8749
                  "
    DESCRIPTION  "This MIB provides information to configure data interface 
                  (such as T38, Fax, etc.) on a per interface basis."
    -- ************************************************************************
    -- Revision history
    -- ************************************************************************
    REVISION    "0207240000Z"
    DESCRIPTION "July 24, 2002
                    Specified that dataIfCodecMediaTypeImageEnable applies only
                    to MGCP and NCS.
                 August 22, 2001
                    Creation"
    ::= { mediatrixConfig 35 }

dataIfMIBObjects OBJECT IDENTIFIER ::= { dataIfMIB 1 }
dataIfConformance OBJECT IDENTIFIER ::= { dataIfMIB 2 }

    -- ************************************************************************
    -- Data interface codec configuration table parameters
    -- ************************************************************************
    dataIfCodecTable OBJECT-TYPE
        SYNTAX      SEQUENCE OF DataIfCodecEntry
        MAX-ACCESS  not-accessible
        STATUS      current
        DESCRIPTION "Table that contains data interface configuration parameters."
        ::= { dataIfMIBObjects 20 }

        dataIfCodecEntry OBJECT-TYPE
            SYNTAX      DataIfCodecEntry
            MAX-ACCESS  not-accessible
            STATUS      current
            DESCRIPTION "Table entry of the data interface table."
            INDEX       {
                         ifIndex
                        }
            ::= { dataIfCodecTable 1 }

            DataIfCodecEntry ::= SEQUENCE 
                {
                    dataIfCodecT38Enable             INTEGER,
                    dataIfCodecMediaTypeImageEnable  INTEGER,
                    dataIfCodecT38ProtectionLevel    Unsigned32
               }    

            dataIfCodecMediaTypeImageEnable OBJECT-TYPE
                SYNTAX      INTEGER  {
                             disable(0),
                             pcmu(1),
                             pcma(2),
                             pcmu-pcma(3)
                            }
                MAX-ACCESS  read-write
                STATUS      current
                DESCRIPTION "disable   : image media type is not present in the SDP.
                             pcmu      : image media type is present in the SDP for PCMU only.
                             pcma      : image media type is present in the SDP for PCMA only.
                             pcmu-pcma : image media type is present in the SDP for PCMU and PCMA.

                             Note : This variable only applies when using MGCP or NCS as the
                             signaling protocol. When using SIP, clear channel faxes are always
                             done in PCMU."
                DEFVAL      { pcmu-pcma }
                ::= { dataIfCodecEntry 1 }     

            dataIfCodecT38Enable OBJECT-TYPE
                SYNTAX      INTEGER {
                             disable(0),
                             enable(1)
                            }
                MAX-ACCESS  read-write
                STATUS      current
                DESCRIPTION "If enabled, the T.38 protocol will be used for Fax transmission."
                DEFVAL      { enable }
                ::= { dataIfCodecEntry 5 }     

            dataIfCodecT38ProtectionLevel OBJECT-TYPE
                SYNTAX      Unsigned32 (1..5)
                MAX-ACCESS  read-write
                STATUS      current
                DESCRIPTION "The number of redundancy packets."
                DEFVAL      { 3 }
                ::=    { dataIfCodecEntry  6 }

    -- ************************************************************************
    -- Conformance information
    -- ************************************************************************
    dataIfCompliances OBJECT IDENTIFIER ::= { dataIfConformance 1 }

    dataIfComplVer1 MODULE-COMPLIANCE
        STATUS      current
        DESCRIPTION     
            "Basic data interface requirements."
        MODULE -- This Module
            MANDATORY-GROUPS {
                              dataIfGroupVer1 
                             }
        ::= { dataIfCompliances 1 }

    -- ************************************************************************
    -- MIB variable grouping
    -- ************************************************************************
    dataIfGroups OBJECT IDENTIFIER ::= { dataIfConformance 2 }

    dataIfGroupVer1 OBJECT-GROUP
        OBJECTS {
                 dataIfCodecT38Enable,
                 dataIfCodecMediaTypeImageEnable,
                 dataIfCodecT38ProtectionLevel
                }
        STATUS current
        DESCRIPTION
            "This group holds the objects necessary to control data transmission."
        ::= { dataIfGroups 1 }
                                      
END
