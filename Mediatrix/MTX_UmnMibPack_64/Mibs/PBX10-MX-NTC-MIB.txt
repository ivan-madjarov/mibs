-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


PBX10-MX-NTC-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

ntcMIB MODULE-IDENTITY
 LAST-UPDATED   "0906100000Z"
 ORGANIZATION " Mediatrix Telecom, Inc. "
 CONTACT-INFO " Mediatrix Telecom, Inc.
                4229, Garlock Street
                Sherbrooke (Quebec)
                Canada
                Phone: (819) 829-8749
                "
 DESCRIPTION  " Network Traffic Control

                The Network Traffic Control service allows the administrator to
                apply a bandwidth limitation on the network interfaces.
                "
 -- ****************************************************************************
 
 -- Revision history
 -- ****************************************************************************
 REVISION       "0906100000Z"
 DESCRIPTION  " Initial Revision "
 ::= { mediatrixServices 3700 }

ntcMIBObjects OBJECT IDENTIFIER ::= { ntcMIB 1 }

-- *****************************************************************************

-- Table:Bandwidth Control Table

-- *****************************************************************************

linkBandwidthControlTable OBJECT-TYPE
 SYNTAX        SEQUENCE OF LinkBandwidthControlEntry
 MAX-ACCESS    not-accessible
 STATUS        current
 DESCRIPTION " Bandwidth Control Table

               This table shows the bandwidth limitation applied on the network
               interfaces.
               "
 ::= { ntcMIBObjects 100 }
 linkBandwidthControlEntry OBJECT-TYPE
  SYNTAX        LinkBandwidthControlEntry
  MAX-ACCESS    not-accessible
  STATUS        current
  DESCRIPTION " A row in table Bandwidth Control Table. "
  INDEX         {
                  linkBandwidthControlLinkName
                }

  ::= { linkBandwidthControlTable 1 }

 LinkBandwidthControlEntry ::= SEQUENCE
 {
   linkBandwidthControlLinkName    OCTET STRING,
   linkBandwidthControlEgressLimit Integer32
 }

 -- Index:Link Name

 linkBandwidthControlLinkName OBJECT-TYPE
  SYNTAX        OCTET STRING
  MAX-ACCESS    read-only
  STATUS        current
  DESCRIPTION " Link Name

                Name of the Ethernet link over which the bandwidth limitation
                is applied.
                "
  ::= { linkBandwidthControlEntry 100 }

 -- Columnar:Egress Bandwidth Limit

 linkBandwidthControlEgressLimit OBJECT-TYPE
  SYNTAX        Integer32 ( 0..0 | 64..4096 )
  MAX-ACCESS    read-write
  STATUS        current
  DESCRIPTION " Egress Bandwidth Limit

                Indicates the egress bandwidth limitation for the selected link
                interface. The range is from 64 to 4096 kilobits per second.
                The value 0 means no bandwidth limitation.
                "
  DEFVAL        { 0 }
  ::= { linkBandwidthControlEntry 200 }


-- End of table:Bandwidth Control Table

-- ****************************************************************************

-- Group:Notification Messages Configuration

-- ****************************************************************************

notificationsGroup OBJECT IDENTIFIER
 ::= { ntcMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { ntcMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
