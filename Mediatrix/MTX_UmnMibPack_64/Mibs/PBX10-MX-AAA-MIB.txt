-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


PBX10-MX-AAA-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

aaaMIB MODULE-IDENTITY
 LAST-UPDATED   "0511080000Z"
 ORGANIZATION " Mediatrix Telecom, Inc. "
 CONTACT-INFO " Mediatrix Telecom, Inc.
                4229, Garlock Street
                Sherbrooke (Quebec)
                Canada
                Phone: (819) 829-8749
                "
 DESCRIPTION  " Authentication, Authorization and Accounting

                The AAA service administers the user name database and grants
                or denies access to various functionalities.
                "
 -- ****************************************************************************
 
 -- Revision history
 -- ****************************************************************************
 REVISION       "0511080000Z"
 DESCRIPTION  " Initial Revision "
 REVISION       "0901160000Z"
 DESCRIPTION  " Added Radius related variables. "
 REVISION       "1009130000Z"
 DESCRIPTION  " Added UsersStatus table, added the columnar Users.Delete,
                modified Users.UserName range and added command InsertUser. "
 ::= { mediatrixServices 1000 }

aaaMIBObjects OBJECT IDENTIFIER ::= { aaaMIB 1 }

-- *****************************************************************************

-- Table:Users

-- *****************************************************************************

usersTable OBJECT-TYPE
 SYNTAX        SEQUENCE OF UsersEntry
 MAX-ACCESS    not-accessible
 STATUS        current
 DESCRIPTION " Users

               This table contains the users that are allowed in the system.
               "
 ::= { aaaMIBObjects 100 }
 usersEntry OBJECT-TYPE
  SYNTAX        UsersEntry
  MAX-ACCESS    not-accessible
  STATUS        current
  DESCRIPTION " A row in table Users. "
  INDEX         {
                  usersUserName
                }

  ::= { usersTable 1 }

 UsersEntry ::= SEQUENCE
 {
   usersUserName OCTET STRING,
   usersPassword OCTET STRING,
   usersDelete   INTEGER
 }

 -- Index:User Name

 usersUserName OBJECT-TYPE
  SYNTAX        OCTET STRING ( SIZE(0..50) )
  MAX-ACCESS    read-only
  STATUS        current
  DESCRIPTION " User Name

                Contains the user name. Cannot be empty.
                "
  DEFVAL        { "" }
  ::= { usersEntry 100 }

 -- Columnar:Password

 usersPassword OBJECT-TYPE
  SYNTAX        OCTET STRING
  MAX-ACCESS    read-write
  STATUS        current
  DESCRIPTION " Password

                Contains the user's password.
                "
  DEFVAL        { "" }
  ::= { usersEntry 200 }

 -- Row command:Delete

 usersDelete OBJECT-TYPE
  SYNTAX        INTEGER { noOp(0), delete(10) }
  MAX-ACCESS    read-write
  STATUS        current
  DESCRIPTION " Delete

                Deletes this row.

                Note: a system restart is required to completely remove the
                user. The current activities of this user are not terminated on
                removal.


                "
  DEFVAL        { noOp }
  ::= { usersEntry 300 }


-- End of table:Users

-- *************************************************************************

-- Table:Users Status

-- *************************************************************************

usersStatusTable OBJECT-TYPE
 SYNTAX        SEQUENCE OF UsersStatusEntry
 MAX-ACCESS    not-accessible
 STATUS        current
 DESCRIPTION " Users Status

               This table displays the list of all currently allowed users.
               "
 ::= { aaaMIBObjects 150 }
 usersStatusEntry OBJECT-TYPE
  SYNTAX        UsersStatusEntry
  MAX-ACCESS    not-accessible
  STATUS        current
  DESCRIPTION " A row in table Users Status. "
  INDEX         {
                  usersStatusUserName
                }

  ::= { usersStatusTable 1 }

 UsersStatusEntry ::= SEQUENCE
 {
   usersStatusUserName OCTET STRING,
   usersStatusPassword OCTET STRING
 }

 -- Index:User Name

 usersStatusUserName OBJECT-TYPE
  SYNTAX        OCTET STRING
  MAX-ACCESS    read-only
  STATUS        current
  DESCRIPTION " User Name

                Contains the user name.
                "
  ::= { usersStatusEntry 100 }

 -- Columnar:Password

 usersStatusPassword OBJECT-TYPE
  SYNTAX        OCTET STRING
  MAX-ACCESS    read-only
  STATUS        current
  DESCRIPTION " Password

                Contains the user's password.
                "
  ::= { usersStatusEntry 200 }


-- End of table:Users Status

-- Scalar:Batch User

batchUser OBJECT-TYPE
 SYNTAX        OCTET STRING
 MAX-ACCESS    read-write
 STATUS        current
 DESCRIPTION " Batch User

               User name that is used for scheduled tasks.
               "
 DEFVAL        { "" }
 ::= { aaaMIBObjects 200 }

-- *****************************************************************************

-- Table:Services Aaa Type

-- *****************************************************************************

servicesAaaTypeTable OBJECT-TYPE
 SYNTAX                       SEQUENCE OF ServicesAaaTypeEntry
 MAX-ACCESS                   not-accessible
 STATUS                       current
 DESCRIPTION               "  Services Aaa Type

                              Aaa type used by services.
                              "
 ::= { aaaMIBObjects 300 }
 servicesAaaTypeEntry OBJECT-TYPE
  SYNTAX        ServicesAaaTypeEntry
  MAX-ACCESS    not-accessible
  STATUS        current
  DESCRIPTION " A row in table Services Aaa Type. "
  INDEX         {
                  servicesAaaTypeService
                }

  ::= { servicesAaaTypeTable 1 }

 ServicesAaaTypeEntry ::= SEQUENCE
 {
   servicesAaaTypeService            OCTET STRING,
   servicesAaaTypeAuthenticationType INTEGER,
   servicesAaaTypeAccountingType     INTEGER
 }

 -- Index:Service Name

 servicesAaaTypeService OBJECT-TYPE
  SYNTAX        OCTET STRING
  MAX-ACCESS    read-only
  STATUS        current
  DESCRIPTION " Service Name

                Service name for which the Aaa types are configured.
                "
  DEFVAL        { "" }
  ::= { servicesAaaTypeEntry 100 }

 -- Columnar:Authentication Type

 servicesAaaTypeAuthenticationType OBJECT-TYPE
  SYNTAX        INTEGER { local(100) , radius(200) }
  MAX-ACCESS    read-write
  STATUS        current
  DESCRIPTION " Authentication Type

                Authentication type a service uses for incoming authentication
                requests.

                  * Local: Incoming authentication attempts are validated
                    against the user names and passwords stored in the
                    Aaa.Users table.
                  * Radius: Incoming authentication attempts are validated
                    against the first responding Radius server configured in
                    the Aaa.RadiusServers table. When no servers reply or when
                    no server is configured in the Aaa.RadiusServers table, an
                    authentication attempt of type Local is performed against
                    the user names and passwords stored in the Aaa.Users table.


                "
  DEFVAL        { local }
  ::= { servicesAaaTypeEntry 200 }

 -- Columnar:Accounting Type

 servicesAaaTypeAccountingType OBJECT-TYPE
  SYNTAX        INTEGER { none(100) , radius(200) }
  MAX-ACCESS    read-write
  STATUS        current
  DESCRIPTION " Accounting Type

                Accounting type a service uses once a user is successfully
                authenticated on the unit. Accounting starts once users are
                successfully authenticated and stops when their session is
                over.

                  * None: Accounting is disabled.
                  * Radius: Accounting is done by the first responding Radius
                    server configured in the Aaa.RadiusServers table.


                "
  DEFVAL        { none }
  ::= { servicesAaaTypeEntry 300 }


-- End of table:Services Aaa Type

-- ****************************************************************************

-- Group:Radius Configuration

-- ****************************************************************************

radiusGroup OBJECT IDENTIFIER
 ::= { aaaMIBObjects 10000 }
 -- Scalar:Radius Servers Requests Timeout

 radiusServersTimeoutS OBJECT-TYPE
  SYNTAX        Unsigned32 ( 1..5 )
  MAX-ACCESS    read-write
  STATUS        current
  DESCRIPTION " Radius Servers Requests Timeout

                Maximum time, in seconds, the unit waits for a reply from a
                Radius server. When the timeout is reached, the request is
                sent to the next configured server in the Aaa.RadiusServers
                table.
                "
  DEFVAL        { 5 }
  ::= { radiusGroup 100 }

 -- ***************************************************************************
 
 -- Table:Radius Servers

 -- ***************************************************************************
 
 radiusServersTable OBJECT-TYPE
  SYNTAX                  SEQUENCE OF RadiusServersEntry
  MAX-ACCESS              not-accessible
  STATUS                  current
  DESCRIPTION           " Radius Servers

                          Radius servers used by services.
                          "
  ::= { radiusGroup 1000 }
  radiusServersEntry OBJECT-TYPE
   SYNTAX        RadiusServersEntry
   MAX-ACCESS    not-accessible
   STATUS        current
   DESCRIPTION " A row in table Radius Servers. "
   INDEX         {
                   radiusServersService,
                   radiusServersPriority
                 }

   ::= { radiusServersTable 1 }

  RadiusServersEntry ::= SEQUENCE
  {
    radiusServersService              OCTET STRING,
    radiusServersPriority             Unsigned32,
    radiusServersAuthenticationHost   MxIpHostNamePort,
    radiusServersAuthenticationSecret OCTET STRING,
    radiusServersAccountingHost       MxIpHostNamePort,
    radiusServersAccountingSecret     OCTET STRING
  }

  -- Index:Service Name

  radiusServersService OBJECT-TYPE
   SYNTAX        OCTET STRING
   MAX-ACCESS    read-only
   STATUS        current
   DESCRIPTION " Service Name

                 Name of the service for which Radius servers are configured.
                 "
   ::= { radiusServersEntry 100 }

  -- Index:Radius Server Priority

  radiusServersPriority OBJECT-TYPE
   SYNTAX        Unsigned32
   MAX-ACCESS    read-only
   STATUS        current
   DESCRIPTION " Radius Server Priority

                 Radius server priority determining their usage order for Aaa
                 requests.
                 "
   ::= { radiusServersEntry 200 }

  -- Columnar:Radius Host for Authentication

  radiusServersAuthenticationHost OBJECT-TYPE
   SYNTAX        MxIpHostNamePort
   MAX-ACCESS    read-write
   STATUS        current
   DESCRIPTION " Radius Host for Authentication

                 Hostname and port of a Radius server used for authentication
                 requests.
                 "
   DEFVAL        { "" }
   ::= { radiusServersEntry 300 }

  -- Columnar:Radius Authentication Server Secret Key

  radiusServersAuthenticationSecret OBJECT-TYPE
   SYNTAX        OCTET STRING ( SIZE(0..512) )
   MAX-ACCESS    read-write
   STATUS        current
   DESCRIPTION " Radius Authentication Server Secret Key

                 Secret key shared between the Radius server and the unit. The
                 AuthenticationSecret key must be the same as the secret key
                 stored on the Radius authentication server set in the
                 RadiusServers.AuthenticationHost column.
                 "
   DEFVAL        { "" }
   ::= { radiusServersEntry 400 }

  -- Columnar:Radius Host for Accounting

  radiusServersAccountingHost OBJECT-TYPE
   SYNTAX        MxIpHostNamePort
   MAX-ACCESS    read-write
   STATUS        current
   DESCRIPTION " Radius Host for Accounting

                 Hostname and port of a Radius server used for accounting
                 requests.
                 "
   DEFVAL        { "" }
   ::= { radiusServersEntry 500 }

  -- Columnar:Radius Accounting Server Secret Key

  radiusServersAccountingSecret OBJECT-TYPE
   SYNTAX        OCTET STRING ( SIZE(0..512) )
   MAX-ACCESS    read-write
   STATUS        current
   DESCRIPTION " Radius Accounting Server Secret Key

                 Secret key shared between the Radius server and the unit. The
                 AccountingSecret key must be the same as the secret key
                 stored on the Radius accounting server set in the
                 RadiusServers.AccountingHost column.
                 "
   DEFVAL        { "" }
   ::= { radiusServersEntry 600 }


 -- End of table:Radius Servers

-- End of group:Radius Configuration

-- ****************************************************************************

-- Group:Notification Messages Configuration

-- ****************************************************************************

notificationsGroup OBJECT IDENTIFIER
 ::= { aaaMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { aaaMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
