-- **SDOC**********************************************************************
-- ****************************************************************************
--
--             Copyright(c) 2001-2003 Mediatrix Telecom, Inc.
--
--  NOTICE:
--   This document contains information that is confidential and proprietary
--   to Mediatrix Telecom, Inc.
--
--   Mediatrix Telecom, Inc. reserves all rights to this document as well as
--   to the Intellectual Property of the document and the technology and
--   know-how that it includes and represents.
--
--   This publication cannot be reproduced, neither in whole nor in part, in
--   any form whatsoever without written prior approval by
--   Mediatrix Telecom, Inc.
--
--   Mediatrix Telecom, Inc. reserves the right to revise this publication
--   and make changes at any time and without the obligation to notify any
--   person and/or entity of such revisions and/or changes.
--
-- ****************************************************************************
-- ****************************************************************************
--
-- Root for modules used to configure the H.323 signaling protocol.
--
-- ****************************************************************************
-- **EDOC**********************************************************************

MGCP44-MX-H323-MIB
DEFINITIONS ::= BEGIN

IMPORTS
        OBJECT-TYPE,
        MODULE-IDENTITY,
        OBJECT-IDENTITY
    FROM SNMPv2-SMI
        OBJECT-GROUP,
        NOTIFICATION-GROUP,
        MODULE-COMPLIANCE
    FROM SNMPv2-CONF
        mediatrixIpTelephonySignaling,
        ipAddressStatus,
        ipAddressConfig        
    FROM MX-SMI
        MxIpConfigSource,
        MxIpSelectConfigSource
    FROM MX-TC
        ifIndex
    FROM RFC1213-MIB;

h323 OBJECT-IDENTITY
    STATUS      current
    DESCRIPTION "Root for MIBs that contain H.323 configuration objects."
    ::= { mediatrixIpTelephonySignaling 30 }

    -- *************************************************************************
    -- From a MIB browser point of view:
    --
    --  - The IP addresses are configured through
    --    mediatrix.mediatrixMgmt.ipAddressConfig
    --
    --  - The actual IP addresses are displayed through
    --    mediatrix.mediatrixMgmt.ipAddressStatus.
    --
    -- *************************************************************************

    ipAddressStatusH323 OBJECT IDENTIFIER ::= { ipAddressStatus 90 }
    ipAddressConfigH323 OBJECT IDENTIFIER ::= { ipAddressConfig 90 }
    ipAddressConfigH323Static OBJECT IDENTIFIER ::= { ipAddressConfigH323 10 }
    ipAddressConfigH323Dhcp OBJECT IDENTIFIER ::= { ipAddressConfigH323 15 }

    -- *************************************************************************
    -- Registration status variables
    -- *************************************************************************

    h323ConfigSource OBJECT-TYPE
        SYNTAX      MxIpConfigSource
        MAX-ACCESS  read-only
        STATUS      current
        DESCRIPTION "The actual source of IP addresses used by the unit.

                     For the gatekeeper registration, this variable indicates the source for the
                     gatekeeper IP addresses.

                     static : the IP addresses were specified by the administrator.

                     dhcp   : the IP addresses were provided by a DHCP server."
        DEFVAL { dhcp }
        ::= { ipAddressStatusH323 5 }

    -- *************************************************************************
    -- Registration config variables
    -- *************************************************************************

    h323SelectConfigSource OBJECT-TYPE
        SYNTAX      MxIpSelectConfigSource
        MAX-ACCESS  read-write
        STATUS      current
        DESCRIPTION "Selection of the configuration source for IP addresses.

                     For the gatekeeper registration, this variable indicates the source for the
                     gatekeeper IP addresses.

                     static : the IP addresses are specified by the administrator.

                     dhcp   : the IP addresses are provided by a DHCP server.

                     This configuration applies to all the lines/groups of lines."
        DEFVAL { dhcp }
        ::= { ipAddressConfigH323 5 }


END
