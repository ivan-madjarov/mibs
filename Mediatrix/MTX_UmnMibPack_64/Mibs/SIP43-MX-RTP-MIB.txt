-- ****************************************************************************
-- ****************************************************************************
--
--             Copyright(c) 2001 Mediatrix Telecom, Inc. 
--
--  NOTICE:
--   This document contains information that is confidential and proprietary
--   to Mediatrix Telecom, Inc. 
--
--   Mediatrix Telecom, Inc. reserves all rights to this document as well as
--   to the Intellectual Property of the document and the technology and
--   know-how that it includes and represents. 
--
--   This publication cannot be reproduced, neither in whole nor in part in
--   any form whatsoever without written prior approval by
--   Mediatrix Telecom, Inc. 
--
--   Mediatrix Telecom, Inc. reserves the right to revise this publication
--   and make changes at any time and without the obligation to notify any
--   person and/or entity of such revisions and/or changes. 
--
-- ****************************************************************************
-- ****************************************************************************

SIP43-MX-RTP-MIB
DEFINITIONS ::= BEGIN

IMPORTS
        MODULE-IDENTITY,
        OBJECT-TYPE,
        Integer32,
        Unsigned32
    FROM SNMPv2-SMI
        OBJECT-GROUP,
        MODULE-COMPLIANCE
    FROM SNMPv2-CONF
        mediatrixMgmt
    FROM MX-SMI;

rtpMIB MODULE-IDENTITY
    LAST-UPDATED "0108020000Z"
    ORGANIZATION "Mediatrix Telecom, Inc."
    CONTACT-INFO "Mediatrix Telecom, Inc. 
                  4229, Garlock Street
                  Sherbrooke (Quebec)
                  Canada
                  Phone: (819) 829-8749
                  "
    DESCRIPTION "This MIB contains RTP statistics data."

    -- ************************************************************************
    -- Revision history
    -- ************************************************************************
    REVISION    "0108020000Z"
    DESCRIPTION "August 02, 2001
                    Creation"
    ::= { mediatrixMgmt 50 }

rtpMIBObjects               OBJECT IDENTIFIER ::= { rtpMIB 1 }
rtpConformance              OBJECT IDENTIFIER ::= { rtpMIB 2 }

rtpStats                    OBJECT IDENTIFIER ::= { rtpMIBObjects 2 }

rtpStatsLastConnectionStatistics OBJECT IDENTIFIER ::= { rtpStats 5 }   
rtpStatsCurrentStatistics        OBJECT IDENTIFIER ::= { rtpStats 10 }   
rtpStatsCumulatedStatistics      OBJECT IDENTIFIER ::= { rtpStats 15 }   

  -- RTP LastConnection Statistics

    rtpStatsLastConnNumberOctetsTransmitted OBJECT-TYPE
        SYNTAX      Unsigned32
        MAX-ACCESS  read-only
        STATUS      current
        DESCRIPTION "Number of octets transmitted during the last connection."
        ::= { rtpStatsLastConnectionStatistics 1 }

    rtpStatsLastConnNumberOctetsReceived OBJECT-TYPE
        SYNTAX      Unsigned32
        MAX-ACCESS  read-only
        STATUS      current
        DESCRIPTION "Number of octets received during the last connection."
        ::= { rtpStatsLastConnectionStatistics 2 }
    
    rtpStatsLastConnNumberPacketsTransmitted OBJECT-TYPE
        SYNTAX      Unsigned32
        MAX-ACCESS  read-only
        STATUS      current
        DESCRIPTION "Number of packets transmitted during the last connection."
        ::= { rtpStatsLastConnectionStatistics 3 }
    
    rtpStatsLastConnNumberPacketsReceived OBJECT-TYPE
        SYNTAX      Unsigned32
        MAX-ACCESS  read-only
        STATUS      current
        DESCRIPTION "Number of packets received during the last connection."
        ::= { rtpStatsLastConnectionStatistics 4 }
    
    rtpStatsLastConnNumberPacketsLost OBJECT-TYPE
        SYNTAX      Integer32
        MAX-ACCESS  read-only
        STATUS      current
        DESCRIPTION "Number of packets lost during the last connection."
        ::= { rtpStatsLastConnectionStatistics 5 }
    
    rtpStatsLastConnPercentPacketsLost OBJECT-TYPE
        SYNTAX      Unsigned32 (0..100)
        MAX-ACCESS  read-only
        STATUS      current
        DESCRIPTION "Percentage of packets lost during the last connection."
        ::= { rtpStatsLastConnectionStatistics 6 }


  -- RTP Current Statistics

    rtpStatsCurrentTotalOctetsTransmitted OBJECT-TYPE
        SYNTAX      Unsigned32
        MAX-ACCESS  read-only
        STATUS      current
        DESCRIPTION "Total number of octets transmitted so far in the current 
                     statistics period."
        ::= { rtpStatsCurrentStatistics 1 }

    rtpStatsCurrentTotalOctetsReceived OBJECT-TYPE
        SYNTAX      Unsigned32
        MAX-ACCESS  read-only
        STATUS      current
        DESCRIPTION "Total number of octets received so far in the current 
                     statistics period."
        ::= { rtpStatsCurrentStatistics 2 }
    
    rtpStatsCurrentTotalPacketsTransmitted OBJECT-TYPE
        SYNTAX      Unsigned32
        MAX-ACCESS  read-only
        STATUS      current
        DESCRIPTION "Total number of packets transmitted so far in the current 
                     statistics period."
        ::= { rtpStatsCurrentStatistics 3 }
    
    rtpStatsCurrentTotalPacketsReceived OBJECT-TYPE
        SYNTAX      Unsigned32
        MAX-ACCESS  read-only
        STATUS      current
        DESCRIPTION "Total number of packets received so far in the current 
                     statistics period."
        ::= { rtpStatsCurrentStatistics 4 }
    
    rtpStatsCurrentTotalPacketsLost OBJECT-TYPE
        SYNTAX      Integer32
        MAX-ACCESS  read-only
        STATUS      current
        DESCRIPTION "Total number of packets lost so far in the current 
                     statistics period."
        ::= { rtpStatsCurrentStatistics 5 }
    
    rtpStatsCurrentTotalPercentPacketsLost OBJECT-TYPE
        SYNTAX      Unsigned32 (0..100)
        MAX-ACCESS  read-only
        STATUS      current
        DESCRIPTION "Percentage of packets lost so far in the current 
                     statistics period."
        ::= { rtpStatsCurrentStatistics 6 }


  -- RTP Cumulated Statistics

    rtpStatsCumulatedTotalOctetsTransmitted OBJECT-TYPE
        SYNTAX      Unsigned32
        MAX-ACCESS  read-only
        STATUS      current
        DESCRIPTION "Cumulated total of octets transmitted during the last connection."
        ::= { rtpStatsCumulatedStatistics 1 }

    rtpStatsCumulatedTotalOctetsReceived OBJECT-TYPE
        SYNTAX      Unsigned32
        MAX-ACCESS  read-only
        STATUS      current
        DESCRIPTION "Cumulated total of octets received during the last connection."
        ::= { rtpStatsCumulatedStatistics 2 }
    
    rtpStatsCumulatedTotalPacketsTransmitted OBJECT-TYPE
        SYNTAX      Unsigned32
        MAX-ACCESS  read-only
        STATUS      current
        DESCRIPTION "Cumulated total of packets transmitted during the last connection."
        ::= { rtpStatsCumulatedStatistics 3 }
    
    rtpStatsCumulatedTotalPacketsReceived OBJECT-TYPE
        SYNTAX      Unsigned32
        MAX-ACCESS  read-only
        STATUS      current
        DESCRIPTION "Cumulated total of packets received during the last connection."
        ::= { rtpStatsCumulatedStatistics 4 }
    
    rtpStatsCumulatedTotalPacketsLost OBJECT-TYPE
        SYNTAX      Integer32
        MAX-ACCESS  read-only
        STATUS      current
        DESCRIPTION "Cumulated total of packets lost during the last connection."
        ::= { rtpStatsCumulatedStatistics 5 }
    
    rtpStatsCumulatedTotalPercentPacketsLost OBJECT-TYPE
        SYNTAX      Unsigned32 (0..100)
        MAX-ACCESS  read-only
        STATUS      current
        DESCRIPTION "Percentage of packets lost during the cumulated period."
        DEFVAL      { 0 }
        ::= { rtpStatsCumulatedStatistics 6 }


    -- ************************************************************************
    -- Conformance information
    -- ************************************************************************
    rtpCompliances OBJECT IDENTIFIER ::= { rtpConformance 1 }

    rtpBasicComplVer1 MODULE-COMPLIANCE
        STATUS      current
        DESCRIPTION "Minimal definitions for the RTP group."
        MODULE -- This Module
            MANDATORY-GROUPS { 
                                rtpStatsBasicGroupVer1 
                             }
        ::= { rtpCompliances 1 }

    -- ************************************************************************
    -- MIB variable grouping
    -- ************************************************************************
    rtpGroups OBJECT IDENTIFIER ::= {rtpConformance 2 }

    rtpStatsBasicGroupVer1 OBJECT-GROUP
        OBJECTS { 
                  rtpStatsLastConnNumberOctetsTransmitted,
                  rtpStatsLastConnNumberOctetsReceived,
                  rtpStatsLastConnNumberPacketsTransmitted,
                  rtpStatsLastConnNumberPacketsReceived,
                  rtpStatsLastConnNumberPacketsLost,
                  rtpStatsLastConnPercentPacketsLost,
                  rtpStatsCurrentTotalOctetsTransmitted,
                  rtpStatsCurrentTotalOctetsReceived,
                  rtpStatsCurrentTotalPacketsTransmitted,
                  rtpStatsCurrentTotalPacketsReceived,
                  rtpStatsCurrentTotalPacketsLost,
                  rtpStatsCurrentTotalPercentPacketsLost,
                  rtpStatsCumulatedTotalOctetsTransmitted,
                  rtpStatsCumulatedTotalOctetsReceived,
                  rtpStatsCumulatedTotalPacketsTransmitted,
                  rtpStatsCumulatedTotalPacketsReceived,
                  rtpStatsCumulatedTotalPacketsLost,
                  rtpStatsCumulatedTotalPercentPacketsLost
                }

        STATUS current
        DESCRIPTION "This group holds the objects that define the basic
                     statistics group."
        ::= { rtpGroups 1 }

END
