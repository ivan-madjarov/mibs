-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


PBX10-MX-IPROUTING-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

ipRoutingMIB MODULE-IDENTITY
 LAST-UPDATED   "0906110000Z"
 ORGANIZATION " Mediatrix Telecom, Inc. "
 CONTACT-INFO " Mediatrix Telecom, Inc.
                4229, Garlock Street
                Sherbrooke (Quebec)
                Canada
                Phone: (819) 829-8749
                "
 DESCRIPTION  " IP routing

                The IP routing service allows the user to configure the unit's
                routing table.
                "
 -- ****************************************************************************
 
 -- Revision history
 -- ****************************************************************************
 REVISION       "0906110000Z"
 DESCRIPTION  " Initial Revision "
 ::= { mediatrixServices 3500 }

ipRoutingMIBObjects OBJECT IDENTIFIER ::= { ipRoutingMIB 1 }

-- *****************************************************************************

-- Table:IP routes

-- *****************************************************************************

advancedIpRoutesTable OBJECT-TYPE
 SYNTAX            SEQUENCE OF AdvancedIpRoutesEntry
 MAX-ACCESS        not-accessible
 STATUS            current
 DESCRIPTION     " IP routes

                   This table shows the configured routes in the table.
                   "
 ::= { ipRoutingMIBObjects 200 }
 advancedIpRoutesEntry OBJECT-TYPE
  SYNTAX        AdvancedIpRoutesEntry
  MAX-ACCESS    not-accessible
  STATUS        current
  DESCRIPTION " A row in table IP routes. "
  INDEX         {
                  advancedIpRoutesPriority
                }

  ::= { advancedIpRoutesTable 1 }

 AdvancedIpRoutesEntry ::= SEQUENCE
 {
   advancedIpRoutesPriority         Unsigned32,
   advancedIpRoutesActivation       MxEnableState,
   advancedIpRoutesSourceAddress    OCTET STRING,
   advancedIpRoutesSourceLink       OCTET STRING,
   advancedIpRoutesForwardToNetwork OCTET STRING,
   advancedIpRoutesUp               INTEGER,
   advancedIpRoutesDown             INTEGER,
   advancedIpRoutesInsert           INTEGER,
   advancedIpRoutesDelete           INTEGER
 }

 -- Index:Priority

 advancedIpRoutesPriority OBJECT-TYPE
  SYNTAX        Unsigned32
  MAX-ACCESS    read-only
  STATUS        current
  DESCRIPTION " Priority

                Unique identifier of the row in the table.
                "
  ::= { advancedIpRoutesEntry 100 }

 -- Columnar:Activation

 advancedIpRoutesActivation OBJECT-TYPE
  SYNTAX        MxEnableState
  MAX-ACCESS    read-write
  STATUS        current
  DESCRIPTION " Activation

                Activates this route.

                  * Enable: Activate this route.
                  * Disable: Do not activate this route.


                "
  DEFVAL        { disable }
  ::= { advancedIpRoutesEntry 200 }

 -- Columnar:Source Address

 advancedIpRoutesSourceAddress OBJECT-TYPE
  SYNTAX        OCTET STRING ( SIZE(0..51) )
  MAX-ACCESS    read-write
  STATUS        current
  DESCRIPTION " Source Address

                Specifies the source IP address criteria an incoming packet
                must have to match this rule. When left empty, any source
                address matches this rule. The supported format for the source
                network is: IP address[/mask].

                When specifying a network name, it is mandatory to use the '/'
                format.

                Example: 192.168.1.0 Example: 192.168.1.0/24 Example: Lan1/


                "
  DEFVAL        { "" }
  ::= { advancedIpRoutesEntry 300 }

 -- Columnar:Source Link

 advancedIpRoutesSourceLink OBJECT-TYPE
  SYNTAX        OCTET STRING ( SIZE(0..51) )
  MAX-ACCESS    read-write
  STATUS        current
  DESCRIPTION " Source Link

                Specifies the source link criteria an incoming packet must have
                to match this rule. When left empty, packets received on any
                link match this rule.
                "
  DEFVAL        { "" }
  ::= { advancedIpRoutesEntry 400 }

 -- Columnar:Forward To Network

 advancedIpRoutesForwardToNetwork OBJECT-TYPE
  SYNTAX        OCTET STRING ( SIZE(0..51) )
  MAX-ACCESS    read-write
  STATUS        current
  DESCRIPTION " Forward To Network

                Network on which the packet is forwarded.
                "
  DEFVAL        { "" }
  ::= { advancedIpRoutesEntry 500 }

 -- Row command:Up

 advancedIpRoutesUp OBJECT-TYPE
  SYNTAX        INTEGER { noOp(0), up(10) }
  MAX-ACCESS    read-write
  STATUS        current
  DESCRIPTION " Up

                Moves the current row upside.
                "
  DEFVAL        { noOp }
  ::= { advancedIpRoutesEntry 600 }

 -- Row command:Down

 advancedIpRoutesDown OBJECT-TYPE
  SYNTAX        INTEGER { noOp(0), down(10) }
  MAX-ACCESS    read-write
  STATUS        current
  DESCRIPTION " Down

                Moves the current row downside.
                "
  DEFVAL        { noOp }
  ::= { advancedIpRoutesEntry 700 }

 -- Row command:Insert

 advancedIpRoutesInsert OBJECT-TYPE
  SYNTAX        INTEGER { noOp(0), insert(10) }
  MAX-ACCESS    read-write
  STATUS        current
  DESCRIPTION " Insert

                Inserts a new row before this row.
                "
  DEFVAL        { noOp }
  ::= { advancedIpRoutesEntry 800 }

 -- Row command:Delete

 advancedIpRoutesDelete OBJECT-TYPE
  SYNTAX        INTEGER { noOp(0), delete(10) }
  MAX-ACCESS    read-write
  STATUS        current
  DESCRIPTION " Delete

                Deletes this row.
                "
  DEFVAL        { noOp }
  ::= { advancedIpRoutesEntry 900 }


-- End of table:IP routes

-- ****************************************************************************

-- Group:Status Group

-- ****************************************************************************

statusGroup OBJECT IDENTIFIER
 ::= { ipRoutingMIBObjects 10000 }
 -- Scalar:Configuration Modified Status

 configModifiedStatus OBJECT-TYPE
  SYNTAX        INTEGER { yes(100) , no(200) }
  MAX-ACCESS    read-only
  STATUS        current
  DESCRIPTION " Configuration Modified Status

                Shows whether or not the routing table configuration has been
                modified without being applied.

                 1. Yes: The configuration has been modified but it has not
                    been applied.
                 2. No: The IP routing service uses the configured rules.

                Use the command 'IpRouting.ApplyConfig' to apply the
                configuration.


                "
  ::= { statusGroup 100 }

 -- ***************************************************************************
 
 -- Table:Advanced IP Routes Status

 -- ***************************************************************************
 
 advancedIpRoutesStatusTable OBJECT-TYPE
  SYNTAX        SEQUENCE OF AdvancedIpRoutesStatusEntry
  MAX-ACCESS    not-accessible
  STATUS        current
  DESCRIPTION " Advanced IP Routes Status

                This table shows the current advanced routes used by the unit.
                "
  ::= { statusGroup 200 }
  advancedIpRoutesStatusEntry OBJECT-TYPE
   SYNTAX        AdvancedIpRoutesStatusEntry
   MAX-ACCESS    not-accessible
   STATUS        current
   DESCRIPTION " A row in table Advanced IP Routes Status. "
   INDEX         {
                   advancedIpRoutesStatusPriority
                 }

   ::= { advancedIpRoutesStatusTable 1 }

  AdvancedIpRoutesStatusEntry ::= SEQUENCE
  {
    advancedIpRoutesStatusPriority         Unsigned32,
    advancedIpRoutesStatusSourceAddress    OCTET STRING,
    advancedIpRoutesStatusSourceLink       OCTET STRING,
    advancedIpRoutesStatusForwardToNetwork OCTET STRING,
    advancedIpRoutesStatusStatus           INTEGER
  }

  -- Index:Priority

  advancedIpRoutesStatusPriority OBJECT-TYPE
   SYNTAX        Unsigned32
   MAX-ACCESS    read-only
   STATUS        current
   DESCRIPTION " Priority

                 Unique identifier of the row in the table.
                 "
   ::= { advancedIpRoutesStatusEntry 100 }

  -- Columnar:Source Address

  advancedIpRoutesStatusSourceAddress OBJECT-TYPE
   SYNTAX        OCTET STRING
   MAX-ACCESS    read-only
   STATUS        current
   DESCRIPTION " Source Address

                 Source address[/mask] criteria used to match the rule.
                 "
   ::= { advancedIpRoutesStatusEntry 200 }

  -- Columnar:Source Link

  advancedIpRoutesStatusSourceLink OBJECT-TYPE
   SYNTAX        OCTET STRING
   MAX-ACCESS    read-only
   STATUS        current
   DESCRIPTION " Source Link

                 Source link criteria used to match the rule.
                 "
   ::= { advancedIpRoutesStatusEntry 300 }

  -- Columnar:Forward To Network

  advancedIpRoutesStatusForwardToNetwork OBJECT-TYPE
   SYNTAX        OCTET STRING
   MAX-ACCESS    read-only
   STATUS        current
   DESCRIPTION " Forward To Network

                 Network on which the packet is forwarded.
                 "
   ::= { advancedIpRoutesStatusEntry 350 }

  -- Columnar:Status

  advancedIpRoutesStatusStatus OBJECT-TYPE
   SYNTAX        INTEGER { disabled(100) , invalidConfig(200) , active(300) }
   MAX-ACCESS    read-only
   STATUS        current
   DESCRIPTION " Status

                 Status of the rule

                   * Disabled: The advanced IP route is disabled.
                   * InvalidConfig: The advanced IP route cannot be applied.
                   * Active: The advanced IP route is currently active.


                 "
   ::= { advancedIpRoutesStatusEntry 400 }


 -- End of table:Advanced IP Routes Status

-- End of group:Status Group

-- ****************************************************************************

-- Group:Notification Messages Configuration

-- ****************************************************************************

notificationsGroup OBJECT IDENTIFIER
 ::= { ipRoutingMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { ipRoutingMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
