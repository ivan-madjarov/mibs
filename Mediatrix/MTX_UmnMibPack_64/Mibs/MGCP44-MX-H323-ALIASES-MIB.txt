-- **SDOC***********************************************************************
-- *****************************************************************************
--
--             Copyright(c) 2003 Mediatrix Telecom, Inc.
--
--  NOTICE:
--   This document contains information that is confidential and proprietary
--   to Mediatrix Telecom, Inc.
--
--   Mediatrix Telecom, Inc. reserves all rights to this document as well as
--   to the Intellectual Property of the document and the technology and
--   know-how that it includes and represents.
--
--   This publication cannot be reproduced, neither in whole nor in part, in
--   any form whatsoever without written prior approval by
--   Mediatrix Telecom, Inc.
--
--   Mediatrix Telecom, Inc. reserves the right to revise this publication
--   and make changes at any time and without the obligation to notify any
--   person and/or entity of such revisions and/or changes.
--
-- *****************************************************************************
-- *****************************************************************************
--
-- Alias configuration of a H.323 unit. Applies to H.323 terminals and H.323
-- gateways.
--
-- A H.323 terminal is a unit with only FXS ports. A H.323 gateway is a unit
-- with only FXO ports.
--
-- *****************************************************************************
-- **EDOC***********************************************************************


MGCP44-MX-H323-ALIASES-MIB
DEFINITIONS ::= BEGIN

IMPORTS
        MODULE-IDENTITY,
        OBJECT-IDENTITY,
        OBJECT-TYPE,
        Unsigned32
    FROM SNMPv2-SMI
        OBJECT-GROUP,
        MODULE-COMPLIANCE
    FROM SNMPv2-CONF
        ifIndex
    FROM RFC1213-MIB
        groupIndex
    FROM MX-LINE-GROUPING-MIB
        h323
    FROM MX-H323-MIB;


h323AliasesMIB MODULE-IDENTITY
    LAST-UPDATED "0303030000Z"
    ORGANIZATION "Mediatrix Telecom, Inc."
    CONTACT-INFO "Mediatrix Telecom, Inc.
                  4229, Garlock Street
                  Sherbrooke (Quebec)
                  Canada
                  Phone: (819) 829-8749"
    DESCRIPTION  "This MIB contains configuration objects for H.323."

    -- *************************************************************************
    -- Revision history
    -- *************************************************************************
    REVISION    "0303030000Z"
    DESCRIPTION "March 3, 2003
                    Creation."
    ::= { h323 15 }

h323AliasesMIBObjects  OBJECT IDENTIFIER ::= { h323AliasesMIB 1 }
h323AliasesConformance OBJECT IDENTIFIER ::= { h323AliasesMIB 2 }

    -- *************************************************************************
    -- Line aliases table
    -- *************************************************************************
    h323AliasesIfAliasesTable OBJECT-TYPE
        SYNTAX      SEQUENCE OF H323AliasesIfAliasesEntry
        MAX-ACCESS  not-accessible
        STATUS      current
        DESCRIPTION "This table holds the aliases of the H.323 unit.

                     Each row is used to configure the aliases of one line."
        ::= { h323AliasesMIBObjects 5 }

        h323AliasesIfAliasesEntry OBJECT-TYPE
            SYNTAX      H323AliasesIfAliasesEntry
            MAX-ACCESS  not-accessible
            STATUS      current
            DESCRIPTION "Each row is used to configure the aliases of one line."
            INDEX       { ifIndex }
            ::= { h323AliasesIfAliasesTable 1 }

            H323AliasesIfAliasesEntry ::= SEQUENCE
                {
                    h323AliasesGroupIndex Unsigned32,
                    h323AliasesConfigured OCTET STRING,
                    h323AliasesCurrent    OCTET STRING
                }

        h323AliasesGroupIndex OBJECT-TYPE
            SYNTAX      Unsigned32 (0..24)
            MAX-ACCESS  read-only
            STATUS      current
            DESCRIPTION "Indicates which group is associated with this line.

                         A value different than 0 indicates that the aliases configuration for this line
                         is superceded by the corresponding entry in the h323AliasesGroupAliasesTable.

                         A value of 0 means this line is not part of a group and that it can be
                         configured by using this entry."
            DEFVAL { 0 }
            ::=  {  h323AliasesIfAliasesEntry 5 }

        h323AliasesConfigured OBJECT-TYPE
            SYNTAX      OCTET STRING (SIZE (0..63))
            MAX-ACCESS  read-write
            STATUS      current
            DESCRIPTION "The aliases that uniquely identify the line. These are the configured aliases.
                         This variable only applies to unit of type terminal.

                         Each line must be configured with unique aliases.

                         A line can be configured with zero, one or two aliases. A line can be
                         configured with two aliases of the same type or two aliases of different types.

                         A line can be configured with E.164 aliases, H.323 ID aliases and party number
                         aliases. Transport ID aliases (IP addresses) are not allowed. The local IP
                         address of the unit is configured through ipAddressConfigLocalHost.

                         The configured aliases are included in the terminalAlias field of the
                         gatekeeperRequest and registrationRequest messages.

                         As an example, a line is configured with two aliases, '3460707' as E.164 alias
                         and 'user1' as H.323 ID alias. The following string is used to describe these
                         aliases:

                            E164=3460707;H323ID=user1

                         Each line must have at least one current alias (either configured or
                         confirmed). If a line has no alias, the unit locks this line. When a line is
                         locked, no call can be made/received from/to this line.

                         Refer to the administrator documentation for the description of the aliases
                         syntax.

                         Refer to the administrator documentation for the description of the configured,
                         confirmed and current aliases."
            DEFVAL { "" }
            ::=  {  h323AliasesIfAliasesEntry 10 }

        h323AliasesCurrent OBJECT-TYPE
            SYNTAX      OCTET STRING (SIZE (0..255))
            MAX-ACCESS  read-only
            STATUS      current
            DESCRIPTION "The aliases currently used by the line. This variable only applies to unit of
                         type terminal.


                         Each line must have at least one current alias (either configured or
                         confirmed). If a line has no alias, the unit locks this line. When a line
                         is locked, no call can be made/received from/to this line.

                         Refer to the administrator documentation for the description of the aliases syntax.

                         Refer to the administrator documentation for the description of the configured,
                         confirmed and current aliases."
            DEFVAL { "" }
            ::=  {  h323AliasesIfAliasesEntry 15 }

    -- *************************************************************************
    -- Group aliases table
    -- *************************************************************************
    h323AliasesGroupAliasesTable OBJECT-TYPE
        SYNTAX      SEQUENCE OF H323AliasesGroupAliasesEntry
        MAX-ACCESS  not-accessible
        STATUS      current
        DESCRIPTION "This table holds the aliases of the unit.

                     Each row is used to configure the aliases of one group of lines."
        ::= { h323AliasesMIBObjects 10 }

        h323AliasesGroupAliasesEntry OBJECT-TYPE
            SYNTAX      H323AliasesGroupAliasesEntry
            MAX-ACCESS  not-accessible
            STATUS      current
            DESCRIPTION "Each row is used to configure the aliases of one group of lines."
            INDEX       { groupIndex }
            ::= { h323AliasesGroupAliasesTable 1 }

            H323AliasesGroupAliasesEntry ::= SEQUENCE
                {
                    h323GroupAliasesConfigured OCTET STRING,
                    h323GroupAliasesCurrent    OCTET STRING
                }

        h323GroupAliasesConfigured OBJECT-TYPE
            SYNTAX      OCTET STRING (SIZE (0..63))
            MAX-ACCESS  read-write
            STATUS      current
            DESCRIPTION "The aliases that uniquely identify a group of lines. These are the configured
                         aliases.

                         Each group must be configured with unique aliases.

                         A group can be configured with zero, one or two aliases. A group can be
                         configured with two aliases of the same type or two aliases of different types.

                         A group can be configured with E.164 aliases, H.323 ID aliases and party number
                         aliases. Transport ID aliases (IP addresses) are not allowed. The local IP
                         address of the unit is configured through ipAddressConfigLocalHost.

                         The configured aliases are included in the terminalAlias field of the
                         gatekeeperRequest and registrationRequest messages. If the unit is a H.323
                         gateway, the E.164 aliases (considered as voice supported prefixes) are also
                         included in the supportedPrefixes field of the gatekeeperRequest and
                         registrationRequest messages.

                         As an example, a group is configured with two aliases, '3460707' as E.164 alias
                         and 'user1' as H.323 ID alias. The following string is used to describe these
                         aliases:

                            E164=3460707;H323ID=user1

                         Each group must have at least one current alias (either configured or
                         confirmed). If a group has no alias, the unit locks the lines associated with
                         that group. When a line is locked, no call can be made/received from/to this
                         line.

                         Refer to the administrator documentation for the description of the aliases
                         syntax.

                         Refer to the administrator documentation for the description of the configured,
                         confirmed and current aliases."
            DEFVAL { "" }
            ::=  {  h323AliasesGroupAliasesEntry 5 }

        h323GroupAliasesCurrent OBJECT-TYPE
            SYNTAX      OCTET STRING (SIZE (0..255))
            MAX-ACCESS  read-only
            STATUS      current
            DESCRIPTION "The aliases currently used by the group of lines.

                         Each group must have at least one current alias (either configured or
                         confirmed). If a group has no alias, the unit locks the lines associated with
                         this group. When a line is locked, no call can be made/received from/to this
                         line.

                         Refer to the administrator documentation for the description of the aliases
                         syntax.

                         Refer to the administrator documentation for the description of the configured,
                         confirmed and current aliases."
            DEFVAL { "" }
            ::=  {  h323AliasesGroupAliasesEntry 10 }


    -- *************************************************************************
    -- Conformance information
    -- *************************************************************************
    h323AliasesCompliances OBJECT IDENTIFIER ::= { h323AliasesConformance 1 }

        h323AliasesBasicComplVer1 MODULE-COMPLIANCE
            STATUS      current
            DESCRIPTION "This is a list of conformance groups. These conformance groups contain the name
                         of objects necessary to adequately configure a H.323 unit."
            MODULE      -- MGCP44-MX-H323-ALIASES-MIB
            MANDATORY-GROUPS {
                               h323AliasesLineAliasesGroupVer1,
                               h323AliasesGroupAliasesGroupVer1
                             }
            ::= { h323AliasesCompliances 5 }

    -- *************************************************************************
    -- MIB variable grouping
    -- *************************************************************************
    h323AliasesGroups OBJECT IDENTIFIER ::= { h323AliasesConformance 2 }

        h323AliasesLineAliasesGroupVer1 OBJECT-GROUP
            OBJECTS {
                       h323AliasesConfigured,
                       h323AliasesCurrent
                    }
            STATUS      current
            DESCRIPTION "A list of objects used to configure the aliases of a H.323 unit."
            ::= { h323AliasesGroups 5 }

        h323AliasesGroupAliasesGroupVer1 OBJECT-GROUP
            OBJECTS {
                       h323GroupAliasesConfigured,
                       h323GroupAliasesCurrent
                    }
            STATUS      current
            DESCRIPTION "A list of objects used to configure the aliases of a H.323 unit."
            ::= { h323AliasesGroups 10 }

END
