-- ****************************************************************************
-- ****************************************************************************
--
--             Copyright(c) 2002 Mediatrix Telecom, Inc. 
--
--  NOTICE:
--   This document contains information that is confidential and proprietary
--   to Mediatrix Telecom, Inc. 
--
--   Mediatrix Telecom, Inc. reserves all rights to this document as well as
--   to the Intellectual Property of the document and the technology and
--   know how that it includes and represents. 
--
--   This publication cannot be reproduced, neither in whole nor in part in
--   any form whatsoever without written prior approval by
--   Mediatrix Telecom, Inc. 
--
--   Mediatrix Telecom, Inc. reserves the right to revise this publication
--   and make changes at any time and without the obligation to notify any
--   person and/or entity of such revisions and/or changes. 
--
-- ****************************************************************************
-- ****************************************************************************

MGCP42-MX-NCS-COMPATIBILITY-MIB
DEFINITIONS ::= BEGIN

IMPORTS
        MODULE-IDENTITY,
        OBJECT-TYPE
    FROM SNMPv2-SMI
        MODULE-COMPLIANCE,
        OBJECT-GROUP
    FROM SNMPv2-CONF
        mediatrixExperimental
    FROM MX-SMI;

ncsCompatibilityMIB MODULE-IDENTITY
    LAST-UPDATED "0208280000Z"
    ORGANIZATION "Mediatrix Telecom, Inc."
    CONTACT-INFO "Mediatrix Telecom, Inc. 
                  4229, Garlock Street
                  Sherbrooke (Quebec)
                  Canada
                  Phone: (819) 829-8749
                  "
    DESCRIPTION "This MIB contains objects for NCS compatibility of the 
                 Mediatrix products."

    -- ************************************************************************
    -- Revision history
    -- ************************************************************************
    REVISION    "0208280000Z"
    DESCRIPTION "August 28, 2002
                    Creation"
    ::= { mediatrixExperimental 15 }

ncsCompatibilityMIBObjects  OBJECT IDENTIFIER ::= { ncsCompatibilityMIB 1 }
ncsCompatibilityConformance OBJECT IDENTIFIER ::= { ncsCompatibilityMIB 2 }

    ncsCompatibilityRtpPayloadType18EncodingName OBJECT-TYPE
        SYNTAX      INTEGER {
                              g729(0),
                              g729A(1)
                            }
        MAX-ACCESS  read-write
        STATUS      current
        DESCRIPTION "Literal name of the compression algorithm corresponding
                     to the RTP payload type 18."
        DEFVAL      { g729 }
        ::=  {  ncsCompatibilityMIBObjects  5  }


    -- ************************************************************************
    -- Conformance information
    -- ************************************************************************
    ncsCompatibilityCompliances OBJECT IDENTIFIER ::= { ncsCompatibilityConformance 1 }

    ncsCompatibilityComplVer1 MODULE-COMPLIANCE
        STATUS      current
        DESCRIPTION
            "List of groups required to support NCS compatibility parameters."
        MODULE -- This Module
            MANDATORY-GROUPS { 
                                 ncsCompatibilityBasicGroupVer1
                             }
        ::= { ncsCompatibilityCompliances 10 }

    -- ************************************************************************
    -- MIB variable grouping
    -- ************************************************************************
    ncsCompatibilityGroups OBJECT IDENTIFIER ::= { ncsCompatibilityConformance 2 }

    ncsCompatibilityBasicGroupVer1 OBJECT-GROUP
        OBJECTS {
                    ncsCompatibilityRtpPayloadType18EncodingName
                }
        STATUS current
        DESCRIPTION
            "This group holds the objects that define the basic NCS compatibility group."
        ::= { ncsCompatibilityGroups 10 }

END
