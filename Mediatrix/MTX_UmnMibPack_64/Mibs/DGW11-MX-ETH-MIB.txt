-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


DGW11-MX-ETH-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

ethMIB MODULE-IDENTITY
 LAST-UPDATED   "0606140000Z"
 ORGANIZATION " Mediatrix Telecom, Inc. "
 CONTACT-INFO " Mediatrix Telecom, Inc.
                4229, Garlock Street
                Sherbrooke (Quebec)
                Canada
                Phone: (819) 829-8749
                "
 DESCRIPTION  " Ethernet Manager

                The Ethernet Manager service allows the administrator to
                configure the system's Ethernet ports parameters.
                "
 -- ****************************************************************************
 
 -- Revision history
 -- ****************************************************************************
 REVISION       "0606140000Z"
 DESCRIPTION  " Initial Revision "
 ::= { mediatrixServices 2400 }

ethMIBObjects OBJECT IDENTIFIER ::= { ethMIB 1 }

-- *****************************************************************************

-- Table:Ethernet Ports Status

-- *****************************************************************************

portsStatusTable OBJECT-TYPE
 SYNTAX        SEQUENCE OF PortsStatusEntry
 MAX-ACCESS    not-accessible
 STATUS        current
 DESCRIPTION " Ethernet Ports Status

               This table displays the status of all Ethernet connectors of the
               mainboard.
               "
 ::= { ethMIBObjects 100 }
 portsStatusEntry OBJECT-TYPE
  SYNTAX        PortsStatusEntry
  MAX-ACCESS    not-accessible
  STATUS        current
  DESCRIPTION " A row in table Ethernet Ports Status. "
  INDEX         {
                  portsStatusName
                }

  ::= { portsStatusTable 1 }

 PortsStatusEntry ::= SEQUENCE
 {
   portsStatusName       OCTET STRING,
   portsStatusLinkName   OCTET STRING,
   portsStatusConnection INTEGER
 }

 -- Index:Port Name

 portsStatusName OBJECT-TYPE
  SYNTAX        OCTET STRING
  MAX-ACCESS    read-only
  STATUS        current
  DESCRIPTION " Port Name

                The name of the Ethernet port.
                "
  ::= { portsStatusEntry 100 }

 -- Columnar:Link Name

 portsStatusLinkName OBJECT-TYPE
  SYNTAX        OCTET STRING
  MAX-ACCESS    read-only
  STATUS        current
  DESCRIPTION " Link Name

                The link interface associated with this port.
                "
  ::= { portsStatusEntry 200 }

 -- Columnar:Speed

 portsStatusConnection OBJECT-TYPE
  SYNTAX        INTEGER { disconnected(0) , half10(100) , full10(200) , half100
                (300) , full100(400) }
  MAX-ACCESS    read-only
  STATUS        current
  DESCRIPTION " Speed

                Indicates the speed, duplex, and state of the connection.

                  * Disconnected: This port is physically disconnected.
                  * Half10: This port is connected at 10 Mbit/s Half-duplex.
                  * Full10: This port is connected at 10 Mbit/s Full-duplex.
                  * Half100: This port is connected at 100 Mbit/s Half-duplex.
                  * Full100: This port is connected at 100 Mbit/s Full-duplex.


                "
  ::= { portsStatusEntry 300 }


-- End of table:Ethernet Ports Status

-- *****************************************************************************

-- Table:Ethernet Ports Settings

-- *****************************************************************************

portsTable OBJECT-TYPE
 SYNTAX        SEQUENCE OF PortsEntry
 MAX-ACCESS    not-accessible
 STATUS        current
 DESCRIPTION " Ethernet Ports Settings

               This table configures the Ethernet ports of the mainboard.
               "
 ::= { ethMIBObjects 200 }
 portsEntry OBJECT-TYPE
  SYNTAX        PortsEntry
  MAX-ACCESS    not-accessible
  STATUS        current
  DESCRIPTION " A row in table Ethernet Ports Settings. "
  INDEX         {
                  portsName
                }

  ::= { portsTable 1 }

 PortsEntry ::= SEQUENCE
 {
   portsName  OCTET STRING,
   portsSpeed INTEGER
 }

 -- Index:Port Name

 portsName OBJECT-TYPE
  SYNTAX        OCTET STRING
  MAX-ACCESS    read-only
  STATUS        current
  DESCRIPTION " Port Name

                The name of the Ethernet port.
                "
  ::= { portsEntry 100 }

 -- Columnar:Speed

 portsSpeed OBJECT-TYPE
  SYNTAX        INTEGER { auto(100) , half10(200) , full10(300) , half100(400)
                , full100(500) }
  MAX-ACCESS    read-write
  STATUS        current
  DESCRIPTION " Speed

                Configures the speed and duplex of the connection.

                  * Auto: Automatic negociation of speed and duplex.
                  * Half10: 10 Mbit/s Half-duplex.
                  * Full10: 10 Mbit/s Full-duplex.
                  * Half100: 100 Mbit/s Half-duplex.
                  * Full100: 100 Mbit/s Full-duplex.


                "
  DEFVAL        { auto }
  ::= { portsEntry 200 }


-- End of table:Ethernet Ports Settings

-- *****************************************************************************

-- Table:Ethernet VLAN Settings

-- *****************************************************************************

vlanTable OBJECT-TYPE
 SYNTAX        SEQUENCE OF VlanEntry
 MAX-ACCESS    not-accessible
 STATUS        current
 DESCRIPTION " Ethernet VLAN Settings

               This table configures the Ethernet Virtual LAN interfaces of the
               system.
               "
 ::= { ethMIBObjects 300 }
 vlanEntry OBJECT-TYPE
  SYNTAX        VlanEntry
  MAX-ACCESS    not-accessible
  STATUS        current
  DESCRIPTION " A row in table Ethernet VLAN Settings. "
  INDEX         {
                  vlanLinkName,
                  vlanId
                }

  ::= { vlanTable 1 }

 VlanEntry ::= SEQUENCE
 {
   vlanLinkName            OCTET STRING,
   vlanId                  Unsigned32,
   vlanDefaultUserPriority Unsigned32,
   vlanDelete              INTEGER
 }

 -- Index:Link Name

 vlanLinkName OBJECT-TYPE
  SYNTAX        OCTET STRING
  MAX-ACCESS    read-only
  STATUS        current
  DESCRIPTION " Link Name

                Name of the Ethernet link over which the VLAN interface is
                built.
                "
  ::= { vlanEntry 100 }

 -- Index:Vlan ID

 vlanId OBJECT-TYPE
  SYNTAX        Unsigned32 ( 1..4094 )
  MAX-ACCESS    read-only
  STATUS        current
  DESCRIPTION " Vlan ID

                VLAN ID used by the VLAN interface.
                "
  ::= { vlanEntry 200 }

 -- Columnar:Default User Priority

 vlanDefaultUserPriority OBJECT-TYPE
  SYNTAX        Unsigned32 ( 0..7 )
  MAX-ACCESS    read-write
  STATUS        current
  DESCRIPTION " Default User Priority

                Default User Priority value the interface uses when tagging
                packets. Specific service class values may be set in the Local
                Quality of Service (LQos) ServiceClasses table.
                "
  DEFVAL        { 0 }
  ::= { vlanEntry 300 }

 -- Row command:Delete

 vlanDelete OBJECT-TYPE
  SYNTAX        INTEGER { noOp(0), delete(10) }
  MAX-ACCESS    read-write
  STATUS        current
  DESCRIPTION " Delete

                Deletes the VLAN interface and removes it from the system.
                "
  DEFVAL        { noOp }
  ::= { vlanEntry 400 }


-- End of table:Ethernet VLAN Settings

-- ****************************************************************************

-- Group:Notification Messages Configuration

-- ****************************************************************************

notificationsGroup OBJECT IDENTIFIER
 ::= { ethMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { ethMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
