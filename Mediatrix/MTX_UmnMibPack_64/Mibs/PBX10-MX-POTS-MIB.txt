-- ****************************************************************************
-- ****************************************************************************
--             Copyright(c) 2004 Mediatrix Telecom, Inc.
--  NOTICE:
--   This document contains information that is confidential and proprietary
--   to Mediatrix Telecom, Inc.
--   Mediatrix Telecom, Inc. reserves all rights to this document as well as
--   to the Intellectual Property of the document and the technology and
--   know-how that it includes and represents.
--   This publication cannot be reproduced, neither in whole nor in part in
--   any form whatsoever without written prior approval by
--   Mediatrix Telecom, Inc.
--   Mediatrix Telecom, Inc. reserves the right to revise this publication
--   and make changes at any time and without the obligation to notify any
--   person and/or entity of such revisions and/or changes.
-- ****************************************************************************
-- ****************************************************************************


PBX10-MX-POTS-MIB
DEFINITIONS ::= BEGIN

IMPORTS
        MODULE-IDENTITY,
        OBJECT-TYPE,
        Unsigned32,
        Integer32
    FROM SNMPv2-SMI
        MODULE-COMPLIANCE,
        OBJECT-GROUP
    FROM SNMPv2-CONF
        MxEnableState,
        MxActivationState,
        MxIpHostName,
        MxIpPort,
        MxAdvancedIpPort,
        MxIpSubnetMask,
        MxDigitMap
    FROM MX-TC
        MxUInt64,
        MxFloat32,
        MxIpHostNamePort,
        MxIpAddr,
        MxIpAddrPort,
        MxIpAddrMask,
        MxUri,
        MxUrl
    FROM MX-TC2
        mediatrixServices
    FROM MX-SMI2;

potsMIB MODULE-IDENTITY
 LAST-UPDATED   "0805050000Z"
 ORGANIZATION " Mediatrix Telecom, Inc. "
 CONTACT-INFO " Mediatrix Telecom, Inc.
                4229, Garlock Street
                Sherbrooke (Quebec)
                Canada
                Phone: (819) 829-8749
                "
 DESCRIPTION  " Plain Old Telephony System Line

                The POTS (Plain Old Telephony System) line service allows to
                configure the analog specification of each line.
                "
 -- ****************************************************************************
 
 -- Revision history
 -- ****************************************************************************
 REVISION       "0805050000Z"
 DESCRIPTION  " Initial Revision "
 REVISION       "0811280000Z"
 DESCRIPTION  " Modified description of the FxsCountryCustomizationOverride "
 REVISION       "0812300000Z"
 DESCRIPTION  " Added column Line.State, the scalar FxsShutdownBehavior and the
                table FxsBypass. "
 REVISION       "0901150000Z"
 DESCRIPTION  " Added FxsPowerDropOnDisconnectDuration "
 REVISION       "0904270000Z"
 DESCRIPTION  " Added FXO group of variables. "
 REVISION       "1002240000Z"
 DESCRIPTION  " Added FxsServiceActivation. "
 REVISION       "1003290000Z"
 DESCRIPTION  " Added group FxsMessageWaitingIndicatorGroup. "
 REVISION       "1004070000Z"
 DESCRIPTION  " Added variable DtmfMapDigitDetection. "
 REVISION       "1004260000Z"
 DESCRIPTION  " Added variable VocalUnitInformation. "
 REVISION       "1009220000Z"
 DESCRIPTION  " Added variable FxsCallerIdPrivateCallingPartyName. "
 REVISION       "1102170000Z"
 DESCRIPTION  " Added variable CallerIdTransmission. "
 ::= { mediatrixServices 1800 }

potsMIBObjects OBJECT IDENTIFIER ::= { potsMIB 1 }

-- *****************************************************************************

-- Table:Line Table

-- *****************************************************************************

lineTable OBJECT-TYPE
 SYNTAX        SEQUENCE OF LineEntry
 MAX-ACCESS    not-accessible
 STATUS        current
 DESCRIPTION " Line Table

               This table shows the current available lines and allows their
               basic configuration.
               "
 ::= { potsMIBObjects 100 }
 lineEntry OBJECT-TYPE
  SYNTAX        LineEntry
  MAX-ACCESS    not-accessible
  STATUS        current
  DESCRIPTION " A row in table Line Table. "
  INDEX         {
                  lineId
                }

  ::= { lineTable 1 }

 LineEntry ::= SEQUENCE
 {
   lineId          OCTET STRING,
   lineTypeStatus  INTEGER,
   lineState       INTEGER
 }

 -- Index:Line Identifier

 lineId OBJECT-TYPE
  SYNTAX        OCTET STRING
  MAX-ACCESS    read-only
  STATUS        current
  DESCRIPTION " Line Identifier

                String that identifies a line in other tables.
                "
  ::= { lineEntry 100 }

 -- Columnar:Line Type Status

 lineTypeStatus OBJECT-TYPE
  SYNTAX        INTEGER { fxs(100) , fxo(200) }
  MAX-ACCESS    read-only
  STATUS        current
  DESCRIPTION " Line Type Status

                The status POTS type of the line.
                "
  ::= { lineEntry 200 }

 -- Columnar:State

 lineState OBJECT-TYPE
  SYNTAX        INTEGER { idle(100) , inUse(200) , disabled(300) , bypass(400)
                , down(500) }
  MAX-ACCESS    read-only
  STATUS        current
  DESCRIPTION " State

                The current call control state for this channel:

                  * Idle: The line is available
                  * InUse: The line is currently used
                  * Disabled: The line is disabled
                  * Bypass: The line is on bypass
                  * Down: The power of the line is down


                "
  ::= { lineEntry 300 }


-- End of table:Line Table

-- Scalar:Caller ID Customization

callerIdCustomization OBJECT-TYPE
 SYNTAX        INTEGER { country(100) , etsiDtmf(200) , etsiFsk(300) }
 MAX-ACCESS    read-write
 STATUS        current
 DESCRIPTION " Caller ID Customization

               The caller ID customization allows to select the detection/
               generation method of caller ID.

                 * Country: Use the default caller ID of the country defined in
                   the TelIf.CountrySelection variable.
                 * EtsiDtmf: ETSI 300 659-1 (DTMF string sent between first and
                   second ring)
                 * EtsiFsk: ETSI 300 659-1 (FSK (V.21) sent between first and
                   second ring)


               "
 DEFVAL        { country }
 ::= { potsMIBObjects 200 }

-- Scalar:DTMF Map Digit Detection

dtmfMapDigitDetection OBJECT-TYPE
 SYNTAX        INTEGER { whenPressed(100) , whenReleased(200) }
 MAX-ACCESS    read-write
 STATUS        current
 DESCRIPTION " DTMF Map Digit Detection

               Determines when a digit is processed through the DTMF maps.

                 * WhenPressed : Digits are processed as soon as they are
                   pressed. This can lead to a digit leak in the RTP at the
                   beginning of a call if the voice stream is established
                   before the last digit is released.
                 * WhenReleased : Digits are processed only when released. This
                   option increases the delay needed to match a dialed string
                   to a DTMF map. There is also an impact on
                   'EpServ.DtmfMapTimeoutInterDtmf',
                   'EpServ.DtmfMapTimeoutFirstDtmf' and
                   'EpServ.DtmfMapTimeoutCompletion' since the timers are
                   stopped at the end of a digit instead of the beginning.


               "
 DEFVAL        { whenPressed }
 ::= { potsMIBObjects 300 }

-- Scalar:Enable/Disable Vocal Unit Information

vocalUnitInformation OBJECT-TYPE
 SYNTAX        INTEGER { none(100) , all(200) }
 MAX-ACCESS    read-write
 STATUS        current
 DESCRIPTION " Enable/Disable Vocal Unit Information

               Determines the type of vocal information that can be obtained by
               dialing a pre-defined digit map.

                 * None: The vocal information feature is disabled.
                 * All: Enable all vocal information digit maps.

               The supported vocal information digit maps are:

                 * '*#*0': The list of IP addresses of the device.
                 * '*#*1': The MAC address of the device.


               "
 DEFVAL        { all }
 ::= { potsMIBObjects 400 }

-- Scalar:Caller ID Transmission

callerIdTransmission OBJECT-TYPE
 SYNTAX        INTEGER { country(100) , firstRing(200) , ringPulse(300) ,
               lineReversalRingPulse(400) , dtAs(500) , lineReversalDtAs(600) ,
               noRingPulse(700) }
 MAX-ACCESS    read-write
 STATUS        current
 DESCRIPTION " Caller ID Transmission

               The caller ID transmission allows selecting the transmission
               type of the caller ID.

                 * Country : Use the default caller ID of the country defined
                   in the TelIf.CountrySelection variable.
                 * FirstRing : Caller ID is sent after the first ring.
                 * RingPulse : Caller ID is sent between a brief ring pulse and
                   the first ring.
                 * LineReversalRingPulse : Caller ID is sent between a brief
                   ring pulse and the first ring on an inverted polarity line.
                 * DtAs : Caller ID is sent after the dual tone alerting state
                   tone.
                 * LineReversalDtAs : Caller ID is sent after the dual tone
                   alerting state tone on an inverted polarity line.
                 * NoRingPulse : Caller ID is sent before the first ring.


               "
 DEFVAL        { country }
 ::= { potsMIBObjects 500 }

-- ****************************************************************************

-- Group:FXS

-- ****************************************************************************

fxsGroup OBJECT IDENTIFIER
 ::= { potsMIBObjects 10000 }
 -- Scalar:FXS Line Supervision Mode

 fxsLineSupervisionMode OBJECT-TYPE
  SYNTAX        INTEGER { none(100) , dropOnDisconnect(200) , reversalOnIdle
                (300) , reversalOnEstablished(400) }
  MAX-ACCESS    read-write
  STATUS        current
  DESCRIPTION " FXS Line Supervision Mode

                Determines how the power drop and line polarity are used to
                signal the state of a line.

                  * None: Don't use power drop or polarity reversal to signal
                    the state of the line.
                  * DropOnDisconnect: Activates the Power Drop on Disconnect
                    feature. A short power drop is made at the end of a call
                    when the call is disconnected by the remote party. The
                    drop duration can be configured in the variable
                    FxsPowerDropOnDisconnectDuration.
                  * ReversalOnIdle: Activates the Polarity Reversal on Idle
                    feature. The polarity of the line is initially in reversed
                    state. The polarity of the line returns to the normal
                    state when the user seizes the line or when the line rings
                    for an incoming call. The polarity of the line is reversed
                    again when the call is disconnected.
                  * ReversalOnEstablished: Activates the Polarity Reversal on
                    Established option. The polarity of the line is initially
                    in the normal state. The polarity of the line is reversed
                    when the call is established and returns to the normal
                    state when the call is disconnected.

                Note: Power drop and polarity reversal are also called battery
                drop and battery reversal.


                "
  DEFVAL        { dropOnDisconnect }
  ::= { fxsGroup 100 }

 -- Scalar:FXS Disconnect Delay

 fxsDisconnectDelay OBJECT-TYPE
  SYNTAX        Unsigned32 ( 0..300 )
  MAX-ACCESS    read-write
  STATUS        current
  DESCRIPTION " FXS Disconnect Delay

                Determines whether or not call clearing occurs as soon as the
                called user is the first to hang up a received call. This
                variable has no effect when the user acts as the calling
                party.

                If the value is set to 0, the call is disconnected as soon as
                the called user hangs up the call.

                If the value is greater than 0, that value is the amount of
                time, in seconds, the unit waits after the called user hangs
                up before signalling the end of the call.


                "
  DEFVAL        { 0 }
  ::= { fxsGroup 200 }

 -- Scalar:FXS Inband Ringback

 fxsInbandRingback OBJECT-TYPE
  SYNTAX        MxEnableState
  MAX-ACCESS    read-write
  STATUS        current
  DESCRIPTION " FXS Inband Ringback

                Determines whether or not the FXS endpoint needs to generate a
                ringback for incoming ringing call.

                  * Disable: The FXS endpoint does not play local ringback to
                    the remote party.
                  * Enable: The FXS endpoint plays local ringback to the
                    remote party via the negotiated media stream.


                "
  DEFVAL        { disable }
  ::= { fxsGroup 300 }

 -- Scalar:FXS Shutdown Behavior

 fxsShutdownBehavior OBJECT-TYPE
  SYNTAX        INTEGER { disabledTone(100) , powerDrop(200) }
  MAX-ACCESS    read-write
  STATUS        current
  DESCRIPTION " FXS Shutdown Behavior

                Determines the FXS endpoint behavior when it becomes shut
                down.

                  * DisabledTone: A disabled tone is played when the user
                    picks up the telephone and the FXS endpoint is shut down.
                  * PowerDrop: The loop current is interupted when the FXS
                    endpoint is shut down and no tone is played when the user
                    picks up the telephone.

                A FXS endpoint becomes shut down when the operational state of
                the endpoint becomes 'Disabled' (see EpAdm.OperationalState)
                and the EpAdm.EndpointAutomaticShutdownEnable is set to
                'Enable'.

                This variable is not used by FXS endpoints related to bypass
                when the variable FxsBypass.Activation is set to
                'EndpointDisabled'.


                "
  DEFVAL        { disabledTone }
  ::= { fxsGroup 400 }

 -- Scalar:FXS Power Drop On Disconnect Duration

 fxsPowerDropOnDisconnectDuration OBJECT-TYPE
  SYNTAX        Unsigned32 ( 100..5000 )
  MAX-ACCESS    read-write
  STATUS        current
  DESCRIPTION " FXS Power Drop On Disconnect Duration

                Determines the power drop duration that is made at the end of
                a call when the call is disconnected by the remote party.

                This value is expressed in milliseconds (ms).

                This variable only has an effect when the variable
                FxsLineSupervisionMode is set to 'DropOnDisconnect'.


                "
  DEFVAL        { 1000 }
  ::= { fxsGroup 500 }

 -- Scalar:FXS Service Activation

 fxsServiceActivation OBJECT-TYPE
  SYNTAX        INTEGER { flashHook(100) , flashHookAndDigit(200) }
  MAX-ACCESS    read-write
  STATUS        current
  DESCRIPTION " FXS Service Activation

                Selects the method used by the user to activate supplementary
                services like call hold, second call, call waiting, call
                transfer and conference call.

                  * FlashHook: Service activation is performed by flash hook
                    or hanging up.
                  * FlashHookAndDigit: Service activation is performed by
                    flash hook, flash hook followed by a digit or hanging up.


                "
  DEFVAL        { flashHook }
  ::= { fxsGroup 600 }

 -- Scalar:Fxs Caller ID Private Calling Party Name

 fxsCallerIdPrivateCallingPartyName OBJECT-TYPE
  SYNTAX        OCTET STRING ( SIZE(0..50) )
  MAX-ACCESS    read-write
  STATUS        current
  DESCRIPTION " Fxs Caller ID Private Calling Party Name

                Sets the Calling Party Name of the caller ID (CLIP) when the
                calling party is tagged as private.

                  * When empty, no Calling Party Name parameter is sent.
                  * When set to 'P', no Calling Party Name parameter is sent
                    but a Reason for Absence of Caller Party Name parameter is
                    sent with the value 0x50 (Private).


                "
  DEFVAL        { "Anonymous" }
  ::= { fxsGroup 700 }

 -- ***************************************************************************
 
 -- Group:FXS Country Customization

 -- ***************************************************************************
 
 fxsCountryCustomizationGroup OBJECT IDENTIFIER
  ::= { fxsGroup 10000 }
  -- Scalar:FXS Override Country Configuration

  fxsCountryCustomizationOverride OBJECT-TYPE
   SYNTAX        MxEnableState
   MAX-ACCESS    read-write
   STATUS        current
   DESCRIPTION " FXS Override Country Configuration

                 Allows to override FXS-related default country settings.

                   * Disable: The line uses the default country FXS settings.
                   * Enable: The line uses the FXS country configuration set in
                     the variables FxsCountryCustomizationLoopCurrent and
                     FxsCountryCustomizationFlashHookDetectionRange.


                 "
   DEFVAL        { disable }
   ::= { fxsCountryCustomizationGroup 100 }

  -- Scalar:FXS Country Override Loop Current

  fxsCountryCustomizationLoopCurrent OBJECT-TYPE
   SYNTAX        Unsigned32 ( 20..32 )
   MAX-ACCESS    read-write
   STATUS        current
   DESCRIPTION " FXS Country Override Loop Current

                 Loop current generated by the FXS port in ma.

                 This configuration is used only if the variable
                 FxsCountryCustomizationOverride is set to 'Enable'.


                 "
   DEFVAL        { 30 }
   ::= { fxsCountryCustomizationGroup 200 }

  -- Scalar:FXS Country Override Flash Hook Detection Range

  fxsCountryCustomizationFlashHookDetectionRange OBJECT-TYPE
   SYNTAX        OCTET STRING ( SIZE(5..9) )
   MAX-ACCESS    read-write
   STATUS        current
   DESCRIPTION " FXS Country Override Flash Hook Detection Range

                 The range in which the hook switch must remain pressed to
                 perform a flash hook.

                 The range consists of the minimal delay and maximal delay
                 expressed in ms separated by a '-'. The minimal value allowed
                 is 10 ms and the maximum value allowed is 1200 ms. The space
                 character is not allowed.

                 This configuration is used only if the variable
                 FxsCountryCustomizationOverride is set to 'Enable'.


                 "
   DEFVAL        { "100-1200" }
   ::= { fxsCountryCustomizationGroup 300 }

 -- End of group:FXS Country Customization

 -- ***************************************************************************
 
 -- Group:FXS Bypass

 -- ***************************************************************************
 
 fxsBypassGroup OBJECT IDENTIFIER
  ::= { fxsGroup 10100 }
  -- ***************************************************************************
  
  -- Table:FXS Bypass Table

  -- ***************************************************************************
  
  fxsBypassTable OBJECT-TYPE
   SYNTAX        SEQUENCE OF FxsBypassEntry
   MAX-ACCESS    not-accessible
   STATUS        current
   DESCRIPTION " FXS Bypass Table

                 This table shows the current available FXS bypass and allows
                 their basic configuration.
                 "
   ::= { fxsBypassGroup 1000 }
   fxsBypassEntry OBJECT-TYPE
    SYNTAX        FxsBypassEntry
    MAX-ACCESS    not-accessible
    STATUS        current
    DESCRIPTION " A row in table FXS Bypass Table. "
    INDEX         {
                    fxsBypassId
                  }

    ::= { fxsBypassTable 1 }

   FxsBypassEntry ::= SEQUENCE
   {
     fxsBypassId                  OCTET STRING,
     fxsBypassActivation          INTEGER,
     fxsBypassActivationDtmfMap   MxDigitMap,
     fxsBypassDeactivationTimeout Unsigned32
   }

   -- Index:Line Identifier

   fxsBypassId OBJECT-TYPE
    SYNTAX        OCTET STRING
    MAX-ACCESS    read-only
    STATUS        current
    DESCRIPTION " Line Identifier

                  String that identifies a line in other tables.
                  "
    ::= { fxsBypassEntry 100 }

   -- Columnar:FXS Bypass Activation

   fxsBypassActivation OBJECT-TYPE
    SYNTAX        INTEGER { powerOff(100) , endpointDisabled(200) , onDemand
                  (300) }
    MAX-ACCESS    read-write
    STATUS        current
    DESCRIPTION " FXS Bypass Activation

                  Specifies when the bypass needs to be activated.

                    * PowerOff: The bypass is activated only when the unit
                      power is off or the POTS service is not started.
                    * EndpointDisabled: The bypass is activated when the
                      operational state of the endpoint is 'Disable' and the
                      EpAdm.EndpointAutomaticShutdownEnable is set to 'Enable'.
                      The bypass is also activated for the same conditions as
                      the ones defined in 'PowerOff'.
                    * OnDemand: The bypass is activated when the user enters
                      the DTMF map configured in the
                      FxsBypass.ActivationDtmfMap variable. The bypass is
                      deactivated when the user on hooks the phone for at least
                      the number of time configured in the
                      FxsBypass.DeactivationTimeout variable. The bypass is
                      also activated for the same conditions as the ones
                      defined in 'PowerOff'.


                  "
    DEFVAL        { endpointDisabled }
    ::= { fxsBypassEntry 200 }

   -- Columnar:FXS Bypass Activation DTMF Map

   fxsBypassActivationDtmfMap OBJECT-TYPE
    SYNTAX        MxDigitMap
    MAX-ACCESS    read-write
    STATUS        current
    DESCRIPTION " FXS Bypass Activation DTMF Map

                  Specifies the DTMF to signal to enable the bypass.

                  This variable is only used when the FxsBypass.Activation
                  variable is set to 'OnDemand'.


                  "
    DEFVAL        { "" }
    ::= { fxsBypassEntry 300 }

   -- Columnar:FXS Bypass Deactivation Timeout

   fxsBypassDeactivationTimeout OBJECT-TYPE
    SYNTAX        Unsigned32 ( 0..3600 )
    MAX-ACCESS    read-write
    STATUS        current
    DESCRIPTION " FXS Bypass Deactivation Timeout

                  Specifies the delay to wait before deactivating the bypass
                  after an on hook if the bypass is activated on demand. The
                  delay is restarted after each on hook. The bypass is not
                  deactivated if the delay expires while the FXS endpoint is
                  off hook.

                  This variable is only used when the FxsBypass.Activation
                  variable is set to 'OnDemand' and the bypass is activated
                  using the DTMFs configured in the FxsBypass.ActivationDtmfMap
                  variable.

                  This value is expressed in seconds (s).


                  "
    DEFVAL        { 32 }
    ::= { fxsBypassEntry 400 }


  -- End of table:FXS Bypass Table

 -- End of group:FXS Bypass

 -- ***************************************************************************
 
 -- Group:FXS Message Waiting Indicator Group

 -- ***************************************************************************
 
 fxsMessageWaitingIndicatorGroup OBJECT IDENTIFIER
  ::= { fxsGroup 10200 }
  -- Scalar:Default FXS Message Waiting Indicator Activation.

  fxsDefaultMessageWaitingIndicatorActivation OBJECT-TYPE
   SYNTAX        INTEGER { disabled(100) , tone(200) , visual(300) ,
                 toneAndVisual(400) }
   MAX-ACCESS    read-write
   STATUS        current
   DESCRIPTION " Default FXS Message Waiting Indicator Activation.

                 Configure the Message Waiting Indicator service available on
                 FXS lines.

                 When used in conjunction with a voice-messaging system, the
                 Message Waiting Indicator allows the user to be notified when
                 new messages are awaiting attention on the messaging server.

                   * Disabled: The user is not alerted of messages awaiting
                     attention.
                   * Tone: When messages are awaiting attention, the user is
                     alerted by a message waiting tone when picking up the
                     handset.
                   * Visual: When messages are awaiting attention, the user is
                     alerted by a Visual Message Waiting Indicator such as a
                     blinking LED on the phone.
                   * ToneAndVisual: When messages are awaiting attention, the
                     user is alerted by a Visual Message Waiting Indicator such
                     as a blinking LED on the phone, and a message waiting tone
                     when picking up the handset.

                 If a specific configuration is set in the
                 FxsSpecificMessageWaitingIndicator.Activation variable and the
                 FxsSpecificMessageWaitingIndicator.EnableConfig variable is
                 set to 'Enable', then it overrides the current default
                 configuration.


                 "
   DEFVAL        { toneAndVisual }
   ::= { fxsMessageWaitingIndicatorGroup 100 }

  -- ***************************************************************************
  
  -- Table:Specific FXS Message Waiting Indicator Configuration

  -- ***************************************************************************
  
  fxsSpecificMessageWaitingIndicatorTable OBJECT-TYPE
   SYNTAX        SEQUENCE OF FxsSpecificMessageWaitingIndicatorEntry
   MAX-ACCESS    not-accessible
   STATUS        current
   DESCRIPTION " Specific FXS Message Waiting Indicator Configuration

                 This table allows to configure the message waiting indicator
                 feature for a specific FXS line.
                 "
   ::= { fxsMessageWaitingIndicatorGroup 200 }
   fxsSpecificMessageWaitingIndicatorEntry OBJECT-TYPE
    SYNTAX        FxsSpecificMessageWaitingIndicatorEntry
    MAX-ACCESS    not-accessible
    STATUS        current
    DESCRIPTION " A row in table Specific FXS Message Waiting Indicator
                  Configuration . "
    INDEX         {
                    fxsSpecificMessageWaitingIndicatorId
                  }

    ::= { fxsSpecificMessageWaitingIndicatorTable 1 }

   FxsSpecificMessageWaitingIndicatorEntry ::= SEQUENCE
   {
     fxsSpecificMessageWaitingIndicatorId           OCTET STRING,
     fxsSpecificMessageWaitingIndicatorEnableConfig MxEnableState,
     fxsSpecificMessageWaitingIndicatorActivation   INTEGER
   }

   -- Index:Line Identifier

   fxsSpecificMessageWaitingIndicatorId OBJECT-TYPE
    SYNTAX        OCTET STRING
    MAX-ACCESS    read-only
    STATUS        current
    DESCRIPTION " Line Identifier

                  String that identifies a line in other tables.
                  "
    ::= { fxsSpecificMessageWaitingIndicatorEntry 100 }

   -- Columnar:Enable Configuration

   fxsSpecificMessageWaitingIndicatorEnableConfig OBJECT-TYPE
    SYNTAX        MxEnableState
    MAX-ACCESS    read-write
    STATUS        current
    DESCRIPTION " Enable Configuration

                  Defines the configuration to use for a specific line.

                    * Disable: The line uses the default configuration as
                      defined in the
                      FxsDefaultMessageWaitingIndicatorActivation variable.
                    * Enable: The line uses the specific configuration as
                      defined in the
                      FxsSpecificMessageWaitingIndicator.Activation variable.


                  "
    DEFVAL        { disable }
    ::= { fxsSpecificMessageWaitingIndicatorEntry 200 }

   -- Columnar:Specific FXS Message Waiting Indicator Activation.

   fxsSpecificMessageWaitingIndicatorActivation OBJECT-TYPE
    SYNTAX        INTEGER { disabled(100) , tone(200) , visual(300) ,
                  toneAndVisual(400) }
    MAX-ACCESS    read-write
    STATUS        current
    DESCRIPTION " Specific FXS Message Waiting Indicator Activation.

                  Configure the Message Waiting Indicator for a specific FXS
                  line.

                  When used in conjunction with a voice-messaging system, the
                  Message Waiting Indicator allows the user to be notified when
                  new messages are awaiting attention on the messaging server.

                    * Disabled: The user is not alerted of messages awaiting
                      attention.
                    * Tone: When messages are awaiting attention, the user is
                      alerted by a message waiting tone when picking up the
                      handset.
                    * Visual: When messages are awaiting attention, the user is
                      alerted by a Visual Message Waiting Indicator such as a
                      blinking LED on the phone.
                    * ToneAndVisual: When messages are awaiting attention, the
                      user is alerted by a Visual Message Waiting Indicator
                      such as a blinking LED on the phone, and a message
                      waiting tone when picking up the handset.

                  This configuration overrides the default configuration set in
                  the FxsDefaultMessageWaitingIndicatorActivation variable if
                  the FxsSpecificMessageWaitingIndicator.EnableConfig variable
                  is set to 'Enable'.


                  "
    DEFVAL        { toneAndVisual }
    ::= { fxsSpecificMessageWaitingIndicatorEntry 300 }


  -- End of table:Specific FXS Message Waiting Indicator Configuration

 -- End of group:FXS Message Waiting Indicator Group

 -- ***************************************************************************
 
 -- Group:FXS Call Group

 -- ***************************************************************************
 
 fxsCallGroup OBJECT IDENTIFIER
  ::= { fxsGroup 10300 }
  -- Scalar:FXS Default Auto Cancel Timeout

  fxsDefaultAutoCancelTimeout OBJECT-TYPE
   SYNTAX        Unsigned32 ( 0..600 )
   MAX-ACCESS    read-write
   STATUS        current
   DESCRIPTION " FXS Default Auto Cancel Timeout

                 Time, in seconds, the endpoint rings before the call is
                 automatically cancelled.

                 Setting this variable to 0 disables the timeout. Calls will
                 not be automatically cancelled.


                 "
   DEFVAL        { 0 }
   ::= { fxsCallGroup 100 }

 -- End of group:FXS Call Group

-- End of group:FXS

-- ****************************************************************************

-- Group:FXO Group

-- ****************************************************************************

fxoGroup OBJECT IDENTIFIER
 ::= { potsMIBObjects 20000 }
 -- Scalar:FXO Pre Dial Delay

 fxoPreDialDelay OBJECT-TYPE
  SYNTAX        Unsigned32 ( 0..10000 )
  MAX-ACCESS    read-write
  STATUS        current
  DESCRIPTION " FXO Pre Dial Delay

                The delay between the time the line is successfully seized, or
                dial tone detected, and the moment the destination phone
                number is dialed.

                Some country specifications include a mandatory PreDialDelay.
                In that case, the highest value between that and
                FxoPreDialDelay is used.

                See TelIf.CountrySelection.

                This value is expressed in milliseconds (ms).


                "
  DEFVAL        { 0 }
  ::= { fxoGroup 100 }

 -- Scalar:FXO Dial Tone Detection Configuration

 fxoDialToneDetectionMode OBJECT-TYPE
  SYNTAX        INTEGER { disable(100) , countryTone(200) }
  MAX-ACCESS    read-write
  STATUS        current
  DESCRIPTION " FXO Dial Tone Detection Configuration

                When dial tone detection is enabled, the unit waits for a dial
                tone on the FXO line before initiating the dialling sequence.
                If no dial tone is detected, the line is considered as busy
                with an incoming call. This mechanism helps avoid collisions
                between incoming and outgoing calls.

                  * Disable: Dial tone detection is disabled.
                  * CountryTone: The unit tries to detect the tone specified
                    for this purpose in the current country's tone
                    specification. Some country specifications omit this
                    information. In that case, the unit behaves as if
                    FxoDialToneDetectionMode is 'disable'.

                See TelIf.CountrySelection.
                "
  DEFVAL        { countryTone }
  ::= { fxoGroup 200 }

 -- Scalar:FXO Dial Tone Detection Timeout

 fxoDialToneDetectionTimeout OBJECT-TYPE
  SYNTAX        Unsigned32 ( 1300..10000 )
  MAX-ACCESS    read-write
  STATUS        current
  DESCRIPTION " FXO Dial Tone Detection Timeout

                Indicates how long the unit waits for a dial tone before
                considering the line is busy with an incoming FXO call.

                This value is expressed in milliseconds (ms).


                "
  DEFVAL        { 3000 }
  ::= { fxoGroup 300 }

 -- ***************************************************************************
 
 -- Table:FXO Answering Delay

 -- ***************************************************************************
 
 fxoAnsweringDelayTable OBJECT-TYPE
  SYNTAX        SEQUENCE OF FxoAnsweringDelayEntry
  MAX-ACCESS    not-accessible
  STATUS        current
  DESCRIPTION " FXO Answering Delay

                This table holds the answering delay configuration. Each row
                in this table configures the answering delay of a line.
                "
  ::= { fxoGroup 5000 }
  fxoAnsweringDelayEntry OBJECT-TYPE
   SYNTAX        FxoAnsweringDelayEntry
   MAX-ACCESS    not-accessible
   STATUS        current
   DESCRIPTION " A row in table FXO Answering Delay. "
   INDEX         {
                   fxoAnsweringDelayId
                 }

   ::= { fxoAnsweringDelayTable 1 }

  FxoAnsweringDelayEntry ::= SEQUENCE
  {
    fxoAnsweringDelayId                           OCTET STRING,
    fxoAnsweringDelayWaitBeforeAnsweringDelay     Unsigned32,
    fxoAnsweringDelayAnsweringOnCallerIdDetection MxEnableState,
    fxoAnsweringDelayWaitForCalleeToAnswer        MxEnableState
  }

  -- Index:Line Identifier

  fxoAnsweringDelayId OBJECT-TYPE
   SYNTAX        OCTET STRING
   MAX-ACCESS    read-only
   STATUS        current
   DESCRIPTION " Line Identifier

                 String that identifies a FXO line.
                 "
   ::= { fxoAnsweringDelayEntry 100 }

  -- Columnar:FXO Wait Before Answering Delay

  fxoAnsweringDelayWaitBeforeAnsweringDelay OBJECT-TYPE
   SYNTAX        Unsigned32 ( 0..30000 )
   MAX-ACCESS    read-write
   STATUS        current
   DESCRIPTION " FXO Wait Before Answering Delay

                 The waiting period before answering an incoming FXO call.

                 If this delay expires before the caller ID signal is decoded,
                 the call proceeds without caller ID information.

                 If a minimal waiting period is required for the selected
                 country, the highest of both values is used. See
                 TelIf.CountrySelection.

                 This value is expressed in milliseconds (ms).


                 "
   DEFVAL        { 8000 }
   ::= { fxoAnsweringDelayEntry 200 }

  -- Columnar:FXO Answering On Caller ID Detection

  fxoAnsweringDelayAnsweringOnCallerIdDetection OBJECT-TYPE
   SYNTAX        MxEnableState
   MAX-ACCESS    read-write
   STATUS        current
   DESCRIPTION " FXO Answering On Caller ID Detection

                 Enables answering upon caller ID detection instead of the
                 waiting delay configured by WaitBeforeAnsweringDelay.

                 When enabled, an incoming FXO call is answered on the first
                 occurrence of either

                   * The reception of the caller ID signal.
                   * The expiration of the delay configured by
                     WaitBeforeAnsweringDelay and the country wait before
                     answering delay. See TelIf.CountrySelection.


                 "
   DEFVAL        { enable }
   ::= { fxoAnsweringDelayEntry 300 }

  -- Columnar:FXO Wait For Callee To Answer Enable

  fxoAnsweringDelayWaitForCalleeToAnswer OBJECT-TYPE
   SYNTAX        MxEnableState
   MAX-ACCESS    read-write
   STATUS        current
   DESCRIPTION " FXO Wait For Callee To Answer Enable

                 When the endpoint is set up for automatic call (see the
                 EpServ.DefaultAutoCallEnable variable), enabling this
                 variable makes the endpoint wait until the called the party
                 connection is established before answering the incoming call.
                 "
   DEFVAL        { disable }
   ::= { fxoAnsweringDelayEntry 400 }


 -- End of table:FXO Answering Delay

 -- ***************************************************************************
 
 -- Table:FXO Incoming Call Behavior Table

 -- ***************************************************************************
 
 fxoIncomingCallBehaviorTable OBJECT-TYPE
  SYNTAX        SEQUENCE OF FxoIncomingCallBehaviorEntry
  MAX-ACCESS    not-accessible
  STATUS        current
  DESCRIPTION " FXO Incoming Call Behavior Table

                Table that defines how each line behaves when there is an
                incoming call.
                "
  ::= { fxoGroup 5100 }
  fxoIncomingCallBehaviorEntry OBJECT-TYPE
   SYNTAX        FxoIncomingCallBehaviorEntry
   MAX-ACCESS    not-accessible
   STATUS        current
   DESCRIPTION " A row in table FXO Incoming Call Behavior Table. "
   INDEX         {
                   fxoIncomingCallBehaviorId
                 }

   ::= { fxoIncomingCallBehaviorTable 1 }

  FxoIncomingCallBehaviorEntry ::= SEQUENCE
  {
    fxoIncomingCallBehaviorId                 OCTET STRING,
    fxoIncomingCallBehaviorNotAllowedBehavior INTEGER
  }

  -- Index:Line Identifier

  fxoIncomingCallBehaviorId OBJECT-TYPE
   SYNTAX        OCTET STRING
   MAX-ACCESS    read-only
   STATUS        current
   DESCRIPTION " Line Identifier

                 String that identifies a FXO line.
                 "
   ::= { fxoIncomingCallBehaviorEntry 100 }

  -- Columnar:Not Allowed Behavior

  fxoIncomingCallBehaviorNotAllowedBehavior OBJECT-TYPE
   SYNTAX        INTEGER { doNotAnswer(100) , playCongestionTone(200) }
   MAX-ACCESS    read-write
   STATUS        current
   DESCRIPTION " Not Allowed Behavior

                 Under certain circumstances (locked port, configuration,
                 etc...), incoming FXO calls are not allowed. When that is the
                 case, the FXO endpoint behaves in one of the manners below.

                   * DoNotAnswer: The incoming call is left unanswered.
                   * PlayCongestionTone: The incoming call is answered, a
                     congestion tone is played for 10 seconds, and then the
                     call is terminated.


                 "
   DEFVAL        { playCongestionTone }
   ::= { fxoIncomingCallBehaviorEntry 200 }


 -- End of table:FXO Incoming Call Behavior Table

 -- ***************************************************************************
 
 -- Group:FXO Link State Verification Group

 -- ***************************************************************************
 
 fxoLinkStateVerificationGroup OBJECT IDENTIFIER
  ::= { fxoGroup 10100 }
  -- ***************************************************************************
  
  -- Table:FXO Link State

  -- ***************************************************************************
  
  fxoLinkStateTable OBJECT-TYPE
   SYNTAX        SEQUENCE OF FxoLinkStateEntry
   MAX-ACCESS    not-accessible
   STATUS        current
   DESCRIPTION " FXO Link State

                 A table of link state updated by the link state verification
                 mechanism.
                 "
   ::= { fxoLinkStateVerificationGroup 100 }
   fxoLinkStateEntry OBJECT-TYPE
    SYNTAX        FxoLinkStateEntry
    MAX-ACCESS    not-accessible
    STATUS        current
    DESCRIPTION " A row in table FXO Link State. "
    INDEX         {
                    fxoLinkStateId
                  }

    ::= { fxoLinkStateTable 1 }

   FxoLinkStateEntry ::= SEQUENCE
   {
     fxoLinkStateId        OCTET STRING,
     fxoLinkStateLinkState INTEGER
   }

   -- Index:Line Identifier

   fxoLinkStateId OBJECT-TYPE
    SYNTAX        OCTET STRING
    MAX-ACCESS    read-only
    STATUS        current
    DESCRIPTION " Line Identifier

                  String that identifies a FXO line.
                  "
    ::= { fxoLinkStateEntry 100 }

   -- Columnar:FXO Line State

   fxoLinkStateLinkState OBJECT-TYPE
    SYNTAX        INTEGER { unknown(100) , up(200) , down(300) }
    MAX-ACCESS    read-only
    STATUS        current
    DESCRIPTION " FXO Line State

                  Link state as reported by the link state verification
                  mechanism. The link state verification can be enabled by
                  using the FxoLinkStateVerification object.

                  The unit does not automatically detect when a previously
                  connected port has changed to the disconnected status. The
                  unit only detects the change of status when it attempts to
                  use the port or after a restart.

                  The unit automatically detects within seconds when a
                  disconnected port becomes connected.

                    * Unknown: The line fault detection is disabled.
                    * Up: When last polled, the line was connected.
                    * Down: When last polled, the line was disconnected.


                  "
    ::= { fxoLinkStateEntry 200 }


  -- End of table:FXO Link State

  -- Scalar:FXO Link State Verification

  fxoLinkStateVerification OBJECT-TYPE
   SYNTAX        MxEnableState
   MAX-ACCESS    read-write
   STATUS        current
   DESCRIPTION " FXO Link State Verification

                 The link state verification mechanism allows the detection of
                 defective or down lines based on the absence of current when
                 closing the loop. The link state is reported in the
                 LinkStateTable.
                 "
   DEFVAL        { enable }
   ::= { fxoLinkStateVerificationGroup 200 }

  -- Scalar:FXO Link State Verification Timeout

  fxoLinkStateVerificationTimeout OBJECT-TYPE
   SYNTAX        Unsigned32 ( 500..10000 )
   MAX-ACCESS    read-write
   STATUS        current
   DESCRIPTION " FXO Link State Verification Timeout

                 Indicates how long the unit waits to successfully take the
                 line before considering the line is defective or down.

                 This value is expressed in milliseconds (ms).


                 "
   DEFVAL        { 5000 }
   ::= { fxoLinkStateVerificationGroup 300 }

 -- End of group:FXO Link State Verification Group

 -- ***************************************************************************
 
 -- Group:FXO Force End Of Call Group

 -- ***************************************************************************
 
 fxoForceEndOfCallGroup OBJECT IDENTIFIER
  ::= { fxoGroup 10200 }
  -- Scalar:FXO Forced End Of Call On Call Failure Enable

  fxoFeocOnCallFailureEnable OBJECT-TYPE
   SYNTAX        MxEnableState
   MAX-ACCESS    read-write
   STATUS        current
   DESCRIPTION " FXO Forced End Of Call On Call Failure Enable

                 Enables forced-end-of-call on call failure.

                 This feature forcefully terminates a call that stayed in an
                 error state for some time. When the line falls in an error
                 state where a SIT, a ROH, a BUSY or any error tone is played
                 outbound to the FXO line, the unit waits for the timeout
                 specified by fxoFeocOnCallFailureTimeout and then hangs up.


                 "
   DEFVAL        { enable }
   ::= { fxoForceEndOfCallGroup 100 }

  -- Scalar:FXO Forced End Of Call On Call Failure Timeout

  fxoFeocOnCallFailureTimeout OBJECT-TYPE
   SYNTAX        Unsigned32 ( 0..180 )
   MAX-ACCESS    read-write
   STATUS        current
   DESCRIPTION " FXO Forced End Of Call On Call Failure Timeout

                 The waiting period before terminating a call in an error
                 state. See FxoFeocOnCallFailure.

                 This value is expressed in seconds (sec).


                 "
   DEFVAL        { 30 }
   ::= { fxoForceEndOfCallGroup 200 }

  -- Scalar:FXO Forced End Of Call On Silence Detection Mode

  fxoFeocOnSilenceDetectionMode OBJECT-TYPE
   SYNTAX        INTEGER { disable(100) , inbountAndOutboundSilent(400) }
   MAX-ACCESS    read-write
   STATUS        current
   DESCRIPTION " FXO Forced End Of Call On Silence Detection Mode

                 Enables forced-end-of-call on silence detection.

                 This feature forcefully terminates a call that stayed silent
                 for some time. When silence is detected on the inbound and/or
                 outbound media for an amount of time specified by
                 fxoFeocOnSilenceDetectionTimeout, the call is terminated.

                   * Disable: Forced-end-of-call on silence detection is
                     disabled.
                   * InbountAndOutboundSilent: The call is terminated if both
                     inbound and outbound media are silent at the same time.

                 This feature is useful to free resources in the event of a
                 network failure preventing the end-of-call to be detected or
                 when the FXO end-of-call tone was not detected.


                 "
   DEFVAL        { disable }
   ::= { fxoForceEndOfCallGroup 300 }

  -- Scalar:FXO Forced End Of Call On Silence Detection Timeout

  fxoFeocOnSilenceDetectionTimeout OBJECT-TYPE
   SYNTAX        Unsigned32 ( 1..300 )
   MAX-ACCESS    read-write
   STATUS        current
   DESCRIPTION " FXO Forced End Of Call On Silence Detection Timeout

                 Maximum amount of time that a call can remain silent, as
                 specified by FxoFeocOnSilenceDetectionMode, before it is
                 terminated and the line is released.

                 This value is expressed in seconds (sec).


                 "
   DEFVAL        { 300 }
   ::= { fxoForceEndOfCallGroup 400 }

  -- Scalar:FXO Forced End Of Call On Tone Detection Mode

  fxoFeocOnToneDetectionMode OBJECT-TYPE
   SYNTAX        INTEGER { disable(100) , countryTone(200) , customTone(300) }
   MAX-ACCESS    read-write
   STATUS        current
   DESCRIPTION " FXO Forced End Of Call On Tone Detection Mode

                 Enables forced-end-of-call upon tone detection.

                 This feature terminates a call on detection of an end-of-call
                 tone on the inbound from the FXO line.

                   * Disable: Force-end-of-call upon tone detection is
                     disabled.
                   * CountryTone: The unit tries to detect the tone specified
                     for this purpose in the current country's tone
                     specification. Some country specifications omit this
                     information. In that case, the unit behaves as if
                     fxoFeocOnToneDetectionMode is 'disable'. See
                     TelIf.CountrySelection.
                   * CustomTone: Terminates a call upon detection of a custom
                     tone. See fxoEndOfCallToneCustomSettings.


                 "
   DEFVAL        { countryTone }
   ::= { fxoForceEndOfCallGroup 500 }

  -- ***************************************************************************
  
  -- Group:FXO Force End Of Call Tone Custom Settings Group

  -- ***************************************************************************
  
  fxoForceEndOfCallToneCustomSettingsGroup OBJECT IDENTIFIER
   ::= { fxoForceEndOfCallGroup 10000 }
   -- Scalar:FXO Forced End Of Call Tone Custom Frequency

   fxoFeocToneCustomFrequency OBJECT-TYPE
    SYNTAX        Unsigned32 ( 350..620 )
    MAX-ACCESS    read-write
    STATUS        current
    DESCRIPTION " FXO Forced End Of Call Tone Custom Frequency

                  Frequency to detect in the custom cadence.

                  A customized tone detection can only detect a single
                  frequency. To detect tones made of multiple frequencies,
                  create the cadence for only one of the frequencies found in
                  the tone.

                  This value is expressed in hertz (Hz).


                  "
    DEFVAL        { 440 }
    ::= { fxoForceEndOfCallToneCustomSettingsGroup 100 }

   -- Scalar:FXO Forced End Of Call Tone Custom Cadence

   fxoFeocToneCustomCadence OBJECT-TYPE
    SYNTAX        OCTET STRING ( SIZE(0..128) )
    MAX-ACCESS    read-write
    STATUS        current
    DESCRIPTION " FXO Forced End Of Call Tone Custom Cadence

                  A cadence is a series of frequencies that are played for a
                  specified time, making up a tone. The format for a cadence is
                  'on, off, on, off, ...' where 'on' and 'off', respectively are
                  numerical values representing the time in milliseconds that
                  the frequency can and can't be detected.

                  Example: '2000, 1000, 2000, 0' is a cadence where the
                  frequency will play for 2 seconds, stop for 1 second, and play
                  for two more seconds. This example is also equivalent to
                  setting the string '2000, 1000, 2000'.

                  Up to three 'on, off' pairs can be specified. Specifying less
                  than those six values results in '0' values being added as
                  necessary. When specifying more than six, only use the six
                  first values are used.

                  A cadence starting with a value of zero (0) is invalid. The
                  first zero (0) found in the string signals the end of the
                  cadence (i.e. '200, 0, 300' is the same as '200').

                  The allowed range for the 'on' and 'off' values are 0 to
                  32767. These values are expressed in milliseconds (ms).

                  See FxoFeocToneCustomFrequency and
                  FxoFeocToneCustomRepetition.


                  "
    DEFVAL        { "" }
    ::= { fxoForceEndOfCallToneCustomSettingsGroup 200 }

   -- Scalar:FXO Forced End Of Call Tone Custom Repetition

   fxoFeocToneCustomRepetition OBJECT-TYPE
    SYNTAX        Unsigned32 ( 2..10 )
    MAX-ACCESS    read-write
    STATUS        current
    DESCRIPTION " FXO Forced End Of Call Tone Custom Repetition

                  Repetition of the cadence. See FxoFeocToneCustomCadence.

                  Number of times the custom cadence must be detected to
                  consider the custom end-of-call tone has been detected.


                  "
    DEFVAL        { 3 }
    ::= { fxoForceEndOfCallToneCustomSettingsGroup 300 }

  -- End of group:FXO Force End Of Call Tone Custom Settings Group

 -- End of group:FXO Force End Of Call Group

-- End of group:FXO Group

-- ****************************************************************************

-- Group:Notification Messages Configuration

-- ****************************************************************************

notificationsGroup OBJECT IDENTIFIER
 ::= { potsMIBObjects 60010 }
 -- Scalar:Minimal Severity of Notification

 minSeverity OBJECT-TYPE
  SYNTAX        INTEGER { disable(0) , debug(100) , info(200) , warning(300) ,
                error(400) , critical (500) }
  MAX-ACCESS    read-write
  STATUS        current
  DESCRIPTION " Minimal Severity of Notification

                Sets the minimal severity to issue a notification message
                incoming from this service.

                  * Disable: No notification is issued.
                  * Debug: All notification messages are issued.
                  * Info: Notification messages with severity 'Informational'
                    and higher are issued.
                  * Warning: Notification messages with severity 'Warning' and
                    higher are issued.
                  * Error: Notification messages with severity 'Error' and
                    higher are issued.
                  * Critical: Notification messages with severity 'Critical'
                    are issued.


                "
  DEFVAL        { warning }
  ::= { notificationsGroup 100 }

-- End of group:Notification Messages Configuration

-- ****************************************************************************

-- Group:Configuration Settings

-- ****************************************************************************

configurationGroup OBJECT IDENTIFIER
 ::= { potsMIBObjects 60020 }
 -- Scalar:Need Restart

 needRestartInfo OBJECT-TYPE
  SYNTAX        INTEGER { no(0) , yes(100) }
  MAX-ACCESS    read-only
  STATUS        current
  DESCRIPTION " Need Restart

                Indicates if the service needs to be restarted for its
                configuration to fully take effect.

                  * Yes: Service needs to be restarted.
                  * No: Service does not need to be restarted.

                Services can be restarted by using the command
                Scm.ServiceCommands.Restart.


                "
  ::= { configurationGroup 100 }

-- End of group:Configuration Settings

END
