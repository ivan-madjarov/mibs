-- *****************************************************************************
-- *****************************************************************************
--
--              Copyright(c) 2005 Mediatrix Telecom, Inc.
--              Copyright(c) 2008 Media5 Corporation ("Media5")
--
--  NOTICE:
--   This document contains information that is confidential and proprietary to
--   Media5.
--
--   Media5 reserves all rights to this document as well as to the Intellectual
--   Property of the document and the technology and know-how that it includes
--   and represents.
--
--   This publication cannot be reproduced, neither in whole nor in part, in any
--   form whatsoever without prior written approval by Media5.
--
--   Media5 reserves the right to revise this publication and make changes at
--   any time and without the obligation to notify any person and/or entity of
--   such revisions and/or changes.
--
-- *****************************************************************************
-- *****************************************************************************

DGW11-MX-PRODUCTS2-MIB
DEFINITIONS ::= BEGIN

IMPORTS
        mediatrixProducts
    FROM MX-SMI2;

    -- ************************************************************************
    -- The following are the MIB branches containing the sysObjectId of each
    -- generation 5 Mediatrix products.
    -- ************************************************************************

    mediatrix3000Series         OBJECT IDENTIFIER ::= { mediatrixProducts 100 }
    mediatrix4400Series         OBJECT IDENTIFIER ::= { mediatrixProducts 200 }
    mediatrix4100Series         OBJECT IDENTIFIER ::= { mediatrixProducts 300 }

END
