-- **SDOC***********************************************************************
-- *****************************************************************************
--
--             Copyright(c) 2003 Mediatrix Telecom, Inc.
--
--  NOTICE:
--   This document contains information that is confidential and proprietary to
--   Mediatrix Telecom, Inc.
--
--   Mediatrix Telecom, Inc. reserves all rights to this document as well as to
--   the Intellectual Property of the document and the technology and know-how
--   that it includes and represents.
--
--   This publication cannot be reproduced, neither in whole nor in part, in any
--   form whatsoever, without prior written approval by Mediatrix Telecom, Inc.
--
--   Mediatrix Telecom, Inc. reserves the right to revise this publication and
--   make changes at any time and without the obligation to notify any person
--   and/or entity of such revisions and/or changes.
--
-- *****************************************************************************
-- **EDOC***********************************************************************

MGCP44-MX-LINE-SELECTION-MIB
DEFINITIONS ::= BEGIN

IMPORTS
        MODULE-IDENTITY,
        OBJECT-TYPE,
        Unsigned32
    FROM SNMPv2-SMI
        MODULE-COMPLIANCE,
        OBJECT-GROUP
    FROM SNMPv2-CONF
        ifIndex
    FROM RFC1213-MIB
        mediatrixConfig
    FROM MX-SMI
        MxEnableState,
        MxDigitMap
    FROM MX-TC;

lineSelectionMIB MODULE-IDENTITY
    LAST-UPDATED "0303190000Z"
    ORGANIZATION "Mediatrix Telecom, Inc."
    CONTACT-INFO "Mediatrix Telecom, Inc.
                  4229, Garlock Street
                  Sherbrooke (Quebec)
                  Canada, J1L 2C8
                  Phone: (819) 829-8749
                  http://www.mediatrix.com"
    DESCRIPTION  "This MIB is used to customize the properties of line port selection."


    -- *************************************************************************
    -- Revision history
    -- *************************************************************************
    REVISION    "0303190000Z"
    DESCRIPTION "March 19, 2003
                    Creation."
    ::= { mediatrixConfig 90 }

lineSelectionMIBObjects OBJECT IDENTIFIER ::= { lineSelectionMIB 1 }
lineSelectionConformance OBJECT IDENTIFIER ::= { lineSelectionMIB 5 }

    -- *************************************************************************
    -- IfCustomizationTable
    -- *************************************************************************

    lineSelectionIfCustomizationTable OBJECT-TYPE
        SYNTAX      SEQUENCE OF LineSelectionIfCustomizationEntry
        MAX-ACCESS  not-accessible
        STATUS      current
        DESCRIPTION "A table for customizing the line selection"
        ::= { lineSelectionMIBObjects 10 }

        lineSelectionIfCustomizationEntry OBJECT-TYPE
            SYNTAX      LineSelectionIfCustomizationEntry
            MAX-ACCESS  not-accessible
            STATUS      current
            DESCRIPTION "A row in the lineSelectionIfCustomizationTable table."
            INDEX       {
                            ifIndex
                        }
            ::= { lineSelectionIfCustomizationTable 5 }

            LineSelectionIfCustomizationEntry ::= SEQUENCE
                {
                    lineSelectionEnable    MxEnableState,
                    lineSelectionDigitMap  MxDigitMap
                }

            lineSelectionEnable OBJECT-TYPE
                SYNTAX      MxEnableState
                MAX-ACCESS  read-write
                STATUS      current
                DESCRIPTION "Enable/Disable the source line selection feature.

                             This feature provides a call line selection mechanism, based on the
                             source of the call, and a per-port list of digit maps.

                             When enabled, the source of the call is compared to all the line
                             selection digit maps. The result of this comparison produces a list of
                             lines that can place the call, but which are not necessarily available
                             to do so.

                             Once the match list has been created, there are two possibilities:

                             1. The list contains one or more lines. The port selection algorithm will then
                             be used to select a line. If none of the lines in the list are available,
                             the call is rejected.

                             2. The list is empty. The port selection algorithm will then cycle through all
                             lines that do not use source line selection. If no available lines can be
                             found, the call is rejected.

                             See lineSelectionDigitMap."
                DEFVAL      { disable }
                ::= { lineSelectionIfCustomizationEntry 5 }

            lineSelectionDigitMap OBJECT-TYPE
                SYNTAX  MxDigitMap
                MAX-ACCESS  read-write
                STATUS      current
                DESCRIPTION "Call sources that match this digit map will be permitted to use this line.

                             See digitMapMIB for syntax.

                             Note that this digit map will not have any effect unless the
                             feature's status is 'enabled'.

                             See lineSelectionEnable."
                DEFVAL      { "" }
                ::= { lineSelectionIfCustomizationEntry 10 }


    -- *************************************************************************
    -- Conformance information
    -- *************************************************************************
    lineSelectionCompliances OBJECT IDENTIFIER ::= { lineSelectionConformance 1 }

    lineSelectionComplVer1 MODULE-COMPLIANCE
        STATUS      current
        DESCRIPTION
            "List of groups required to support line port selection."
        MODULE  -- This Module
            MANDATORY-GROUPS {
                                lineSelectionCustomizationVer1
                             }
        ::= { lineSelectionCompliances 1 }

    -- *************************************************************************
    --  MIB variable grouping
    -- *************************************************************************
    lineSelectionGroups OBJECT IDENTIFIER ::= { lineSelectionConformance 5 }

    lineSelectionCustomizationVer1 OBJECT-GROUP
        OBJECTS {
                    lineSelectionEnable,
                    lineSelectionDigitMap
                }
        STATUS current
        DESCRIPTION
            "A collection of objects that defines the characteristics of line
             port selection."
        ::= { lineSelectionGroups 10 }
END
