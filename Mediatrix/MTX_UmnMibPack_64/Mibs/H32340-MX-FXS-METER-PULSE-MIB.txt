-- ****************************************************************************
-- ****************************************************************************
--
--             Copyright(c) 2002 Mediatrix Telecom, Inc. 
--
--  NOTICE:
--   This document contains information that is confidential and proprietary
--   to Mediatrix Telecom, Inc. 
--
--   Mediatrix Telecom, Inc. reserves all rights to this document as well as
--   to the Intellectual Property of the document and the technology and
--   know-how that it includes and represents. 
--
--   This publication cannot be reproduced, neither in whole nor in part, in
--   any form whatsoever without written prior approval by
--   Mediatrix Telecom, Inc. 
--
--   Mediatrix Telecom, Inc. reserves the right to revise this publication
--   and make changes at any time and without the obligation to notify any
--   person and/or entity of such revisions and/or changes. 
--
-- ****************************************************************************
-- ****************************************************************************

H32340-MX-FXS-METER-PULSE-MIB
DEFINITIONS ::= BEGIN

IMPORTS
        MODULE-IDENTITY,
        OBJECT-IDENTITY,
        OBJECT-TYPE,
        Unsigned32
    FROM SNMPv2-SMI
        OBJECT-GROUP,
        MODULE-COMPLIANCE
    FROM SNMPv2-CONF
        ifIndex
    FROM RFC1213-MIB
        mediatrixExperimental
    FROM MX-SMI;

fxsMeterPulseMIB MODULE-IDENTITY
    LAST-UPDATED "0211040000Z"
    ORGANIZATION "Mediatrix Telecom, Inc."
    CONTACT-INFO "Mediatrix Telecom, Inc. 
                  4229, Garlock Street
                  Sherbrooke (Quebec)
                  Canada
                  Phone: (819) 829-8749
                  "
    DESCRIPTION "This MIB contains meter pulse configuration objects."

    -- ************************************************************************
    -- Revision history
    -- ************************************************************************
    REVISION    "0211040000Z"
    DESCRIPTION "November 4, 2002
                    Creation"
    ::= { mediatrixExperimental 30 }

fxsMeterPulseMIBObjects  OBJECT IDENTIFIER ::= { fxsMeterPulseMIB 1 }
fxsMeterPulseConformance OBJECT IDENTIFIER ::= { fxsMeterPulseMIB 2 }

    fxsMeterPulseTable OBJECT-TYPE
        SYNTAX      SEQUENCE OF FxsMeterPulseEntry
        MAX-ACCESS  not-accessible
        STATUS      current
        DESCRIPTION "Table that contains meter pulse parameters for each MGCP
                     endpoint."
        ::= { fxsMeterPulseMIBObjects  30 }

        fxsMeterPulseEntry OBJECT-TYPE
            SYNTAX      FxsMeterPulseEntry
            MAX-ACCESS  not-accessible
            STATUS      current
            DESCRIPTION "Table entry of the table that contains meter pulse
                         parameters."
            INDEX       {
                         ifIndex
                        }
            ::= { fxsMeterPulseTable 1 }

            FxsMeterPulseEntry ::= SEQUENCE
            {
                fxsMeterPulseDuration Unsigned32 (120..220),
                fxsMeterPauseDuration Unsigned32 (100..600)
            }

        fxsMeterPulseDuration OBJECT-TYPE
            SYNTAX      Unsigned32 (120..220)
            MAX-ACCESS  read-write
            STATUS      current
            DESCRIPTION "This is the pulse duration (voltage is ON) in ms.
                         
                         The clock precision is 10 ms, i.e. you can
                         request 213 ms, but the system will play each pulse
                         213 +/- 10 ms."
            DEFVAL      { 160 }
            ::=  {  fxsMeterPulseEntry 10  }
        
        fxsMeterPauseDuration OBJECT-TYPE
            SYNTAX      Unsigned32 (100..600)
            MAX-ACCESS  read-write
            STATUS      current
            DESCRIPTION "This is the pause duration (voltage is OFF) in ms.
                         
                         The clock precision is 10 ms, i.e. you can
                         request 327 ms, but the system will pause for
                         327 +/- 10 ms."
            DEFVAL      { 360 }
            ::=  {  fxsMeterPulseEntry 15 }

    fxsMeterPulseFreq OBJECT-TYPE
    SYNTAX      INTEGER {
                    freq-12-kHz(1),
                    freq-16-kHz(2)
                }
    MAX-ACCESS  read-write
    STATUS      current
    DESCRIPTION "Meter pulse may use different frequencies.
                 The selected frequency applies to ALL FXS ports."
    DEFVAL      { freq-12-kHz }
    ::= { fxsMeterPulseMIBObjects  35 }

    -- ************************************************************************
    -- Conformance information
    -- ************************************************************************
    fxsMeterPulseCompliances OBJECT IDENTIFIER ::= { fxsMeterPulseConformance 1 }

    fxsMeterPulseBasicComplVer1 MODULE-COMPLIANCE
        STATUS      current
        DESCRIPTION "Minimal definitions for the meter pulse group."
        MODULE -- This Module
            MANDATORY-GROUPS { 
                                fxsMeterPulseGroupVer1
                             }
        ::= { fxsMeterPulseCompliances 1 }

    -- ************************************************************************
    -- MIB variable grouping
    -- ************************************************************************
    fxsMeterPulseGroups OBJECT IDENTIFIER ::= {fxsMeterPulseConformance 2 }

    fxsMeterPulseGroupVer1 OBJECT-GROUP
        OBJECTS {
                  fxsMeterPulseDuration,
                  fxsMeterPauseDuration,
                  fxsMeterPulseFreq
                }
        STATUS      current
        DESCRIPTION "This group holds the objects that define the basic
                     meter pulse group."
        ::= { fxsMeterPulseGroups 1 }
    
END
