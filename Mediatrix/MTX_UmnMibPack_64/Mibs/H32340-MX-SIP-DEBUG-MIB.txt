-- ****************************************************************************
-- ****************************************************************************
--
--             Copyright(c) 2003 Mediatrix Telecom, Inc.
--
--  NOTICE:
--   This document contains information that is confidential and proprietary to
--   Mediatrix Telecom, Inc.
--
--   Mediatrix Telecom, Inc. reserves all rights to this document as well as to
--   the Intellectual Property of the document and the technology and know-how
--   that it includes and represents.
--
--   This publication cannot be reproduced, neither in whole nor in part, in any
--   form whatsoever, without prior written approval by Mediatrix Telecom, Inc.
--
--   Mediatrix Telecom, Inc. reserves the right to revise this publication and
--   make changes at any time and without the obligation to notify any person
--   and/or entity of such revisions and/or changes.
--
-- ****************************************************************************
-- ****************************************************************************

H32340-MX-SIP-DEBUG-MIB
DEFINITIONS ::= BEGIN

IMPORTS
        MODULE-IDENTITY,
        OBJECT-IDENTITY,
        OBJECT-TYPE,
        Unsigned32
    FROM SNMPv2-SMI
        OBJECT-GROUP,
        MODULE-COMPLIANCE
    FROM SNMPv2-CONF
        mediatrixExperimental
    FROM MX-SMI;

sipDebugMIB MODULE-IDENTITY
    LAST-UPDATED "0311130000Z"
    ORGANIZATION "Mediatrix Telecom, Inc."
    CONTACT-INFO "Mediatrix Telecom, Inc.
                  4229, Garlock Street
                  Sherbrooke (Quebec)
                  Canada
                  Phone: (819) 829-8749
                  "
    DESCRIPTION "This MIB contains SIP debug configuration objects."

    -- ************************************************************************
    -- Revision history
    -- ************************************************************************
    REVISION    "0311130000Z"
    DESCRIPTION "November 13th, 2003
                 Created"
    ::= { mediatrixExperimental 23 }

sipDebugMIBObjects  OBJECT IDENTIFIER ::= { sipDebugMIB 1 }
sipDebugConformance OBJECT IDENTIFIER ::= { sipDebugMIB 2 }

    -- ************************************************************************
    -- Sip Debug Variables
    -- ************************************************************************
    sipDebugContextSnapshotTime OBJECT-TYPE
        SYNTAX      Unsigned32 ( 0..10080 )
        MAX-ACCESS  read-write
        STATUS      current
        DESCRIPTION "Sets the time between snapshots.

                     The list of contexts currently in use in the sipFramework and sipApplication
                     will be periodically output as debug-level syslog messages.

                     Note that for this feature to work, syslogMsgMaxSeverity must be set to 'debug',
                     and the syslog feature must be properly configured.

                     Note that enabling this feature will also trigger an instant snapshot.

                     To disable this feature, set this variable to zero (0).

                     This value is expressed in minutes (min).

                     Also see syslogMIB and ipAddressConfigSyslog."
        DEFVAL      { 0 }
        ::= { sipDebugMIBObjects  5 }


    -- ************************************************************************
    -- Conformance information
    -- ************************************************************************
    sipDebugCompliances OBJECT IDENTIFIER ::= { sipDebugConformance 1 }

    sipDebugBasicComplVer1 MODULE-COMPLIANCE
        STATUS      current
        DESCRIPTION "Minimal definitions for the SIP protocol debug group."
        MODULE -- This Module
            MANDATORY-GROUPS {
                                sipDebugGroupVer1
                             }
        ::= { sipDebugCompliances 1 }


    -- ************************************************************************
    -- MIB variable grouping
    -- ************************************************************************
    sipDebugGroups OBJECT IDENTIFIER ::= { sipDebugConformance 2 }

    sipDebugGroupVer1 OBJECT-GROUP
        OBJECTS {
                    sipDebugContextSnapshotTime
                }
        STATUS      current
        DESCRIPTION "This group holds the objects that define the
                     sip debug group."
        ::= { sipDebugGroups 5 }
END
